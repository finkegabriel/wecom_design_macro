Attribute VB_Name = "Module1"
Public Sub CheckFileDates()
    Load UpdateVBA
    UpdateVBA.show
    Unload UpdateVBA
End Sub

Attribute VB_Name = "UpdateVBA"
Attribute VB_Base = "0{F3CEF472-AE57-4B27-8B00-ABC94D8593FE}{76EF7108-9E75-4CE0-9EDA-AC593C3BC232}"
Attribute VB_GlobalNameSpace = False
Attribute VB_Creatable = False
Attribute VB_PredeclaredId = True
Attribute VB_Exposed = False
Attribute VB_TemplateDerived = False
Attribute VB_Customizable = False
Dim strCFP, strAFP As String


Private Sub cbQuit_Click()
    Me.hide
End Sub

Private Sub cbUpdate_Click()
    Dim strFrom, strTo, strPath As String
    Dim vLine As Variant
    
    strPath = LCase(ThisDrawing.Application.VBE.ActiveVBProject.FileName)
    
    vLine = Split(strPath, "documents")
    
    strCFP = "C:\Integrity\VBA\"
    strAFP = vLine(0) & "Dropbox\UNITED COMMUNICATIONS JOB INFORMATION\VBA\Integrity\VBA\"
    
    If cbIntegrity.Value = True Then
        strFrom = strAFP & "Integrity.dvb"
        strTo = strCFP & "Integrity.dvb"
        
        FileCopy strFrom, strTo
        
        MsgBox "Integrity VBA has been updated."
    End If
    
    If cbRecords.Value = True Then
        strFrom = strAFP & "Records.dvb"
        strTo = strCFP & "Records.dvb"
        
        FileCopy strFrom, strTo
        
        MsgBox "Records VBA has been updated."
    End If
    
    If cbUnited.Value = True Then
        strFrom = strAFP & "UTC.dvb"
        strTo = strCFP & "UTC.dvb"
        
        FileCopy strFrom, strTo
        
        MsgBox "UTC VBA has been updated."
    End If
    
    Me.hide
End Sub

Private Sub UserForm_Initialize()
    Dim DateICD, DateIAD As Date
    Dim DateRCD, DateRAD As Date
    Dim DateUCD, DateUAD As Date
    
    Dim strPath As String
    Dim fName As String
    Dim strCFP, strAFP As String
    Dim strLine As String
    Dim vLine As Variant
    
    strPath = LCase(ThisDrawing.Application.VBE.ActiveVBProject.FileName)
    
    If InStr(strPath, "integrity") = 0 Then Exit Sub
    If InStr(strPath, "documents") = 0 Then Exit Sub
    
    vLine = Split(strPath, "documents")
    
    strCFP = "C:\Integrity\VBA\"
    strAFP = vLine(0) & "Dropbox\UNITED COMMUNICATIONS JOB INFORMATION\VBA\Integrity\VBA\"
    
    
    strPath = strCFP & "Integrity.dvb"
    fName = Dir(strPath)
    If fName = "" Then
        tbICD.Value = "MISSING"
    Else
        DateICD = FileDateTime(strPath)
        tbICD.Value = CStr(DateICD)
    End If
    
    '<--------------------------------------------------Current VBA Dates
    
    strPath = strCFP & "Records.dvb"
    fName = Dir(strPath)
    If fName = "" Then
        tbRCD.Value = "MISSING"
    Else
        DateRCD = FileDateTime(strPath)
        tbRCD.Value = CStr(DateRCD)
    End If
    
    
    strPath = strCFP & "UTC.dvb"
    fName = Dir(strPath)
    If fName = "" Then
        tbUCD.Value = "MISSING"
    Else
        DateUCD = FileDateTime(strPath)
        tbUCD.Value = CStr(DateUCD)
    End If
    
    '<--------------------------------------------------Available VBA Dates
    
    strPath = strAFP & "Integrity.dvb"
    fName = Dir(strPath)
    If fName = "" Then
        tbIAD.Value = "MISSING"
    Else
        DateIAD = FileDateTime(strPath)
        tbIAD.Value = CStr(DateIAD)
        
        If tbICD.Value = "MISSING" Then
            cbIntegrity.Value = True
        Else
            If DateIAD > DateICD Then cbIntegrity.Value = True
        End If
    End If
    
    
    strPath = strAFP & "Records.dvb"
    fName = Dir(strPath)
    If fName = "" Then
        tbRAD.Value = "MISSING"
    Else
        DateRAD = FileDateTime(strPath)
        tbRAD.Value = CStr(DateRAD)
        
        If tbRCD.Value = "MISSING" Then
            cbRecords.Value = True
        Else
            If DateRAD > DateRCD Then cbRecords.Value = True
        End If
    End If
    
    
    strPath = strAFP & "UTC.dvb"
    fName = Dir(strPath)
    If fName = "" Then
        tbUAD.Value = "MISSING"
    Else
        DateUAD = FileDateTime(strPath)
        tbUAD.Value = CStr(DateUAD)
        
        If tbUCD.Value = "MISSING" Then
            cbUnited.Value = True
        Else
            If DateUAD > DateUCD Then cbUnited.Value = True
        End If
    End If
End Sub
