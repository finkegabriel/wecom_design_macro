Attribute VB_Name = "AddEquipmentRecord"
Attribute VB_Base = "0{826761E4-C169-46AC-AE66-59B1E2556E49}{8B3B0AF0-40A0-4798-9466-404A6B7C0DE3}"
Attribute VB_GlobalNameSpace = False
Attribute VB_Creatable = False
Attribute VB_PredeclaredId = True
Attribute VB_Exposed = False
Attribute VB_TemplateDerived = False
Attribute VB_Customizable = False
Private Sub cbGet_Click()
    Dim objBlock As AcadBlockReference
    Dim objEntity As AcadEntity
    Dim vAttList, vReturnPnt As Variant
    Dim vLine, vTemp As Variant
    Dim iTest As Integer
    Dim strLine As String
    
    Me.Hide
    
    On Error Resume Next
    
Get_Block:
    
    Err = 0
    iTest = 0
    
    ThisDrawing.Utility.GetEntity objEntity, vReturnPnt, vbCr & "Select Block with Data:"
    If Not Err = 0 Then GoTo Exit_Sub
    
    If Not TypeOf objEntity Is AcadBlockReference Then GoTo Exit_Sub
    Set objBlock = objEntity
    
    Select Case objBlock.Name
        Case "sPole", "iPole", "iLPED"
            vAttList = objBlock.GetAttributes
            
            tbLocation.Value = vAttList(0).TextString
            
            vTemp = objBlock.InsertionPoint
            tbNorth.Value = vTemp(1)
            tbEast.Value = vTemp(0)
        Case "MW_STRUCTURES"
            vAttList = objBlock.GetAttributes
            
            tbLocation.Value = vAttList(0).TextString
            
            vTemp = objBlock.InsertionPoint
            tbNorth.Value = vTemp(1)
            tbEast.Value = vTemp(0)
        Case "terminal"
            vAttList = objBlock.GetAttributes
            
            If vAttList(0).TextString = "STRAIGHT SPLICE" Then
                iTest = 1
            Else
                strLine = Replace(vAttList(0).TextString, ": ", ",")
                strLine = Replace(strLine, "\P", "+")
                strLine = Replace(strLine, vbLf, "")
                
                tbIn.Value = strLine
                tbOut.Value = strLine
            End If
        Case "CableCounts"
            vAttList = objBlock.GetAttributes
            vLine = Split(vAttList(1).TextString, ")")
            vTemp = Split(vLine(0), "(")
            
            tbSize.Value = vTemp(1)
            
            If iTest = 1 Then
                strLine = Replace(vAttList(0).TextString, ": ", ",")
                strLine = Replace(strLine, vbCr, "+")
                strLine = Replace(strLine, vbLf, "")
                
                tbIn.Value = strLine
                tbOut.Value = strLine
            End If
        Case "Customer"
            vAttList = objBlock.GetAttributes
            
            strLine = vAttList(1).TextString & " " & vAttList(2).TextString
            tbAddress.Value = strLine
        Case "RES", "BUSINESS", "TRLR", "MDU", "CHURCH", "SCHOOL", "EXTENSTION"
            vAttList = objBlock.GetAttributes
            
            strLine = vAttList(0).TextString & " " & vAttList(1).TextString
            tbAddress.Value = strLine
        Case "iSplitter"
            vAttList = objBlock.GetAttributes
            
            tbSplitter.Value = vAttList(0).TextString
            tbName.Value = vAttList(1).TextString
        Case "MW_SUBSCRIBERS"
            vAttList = objBlock.GetAttributes
            
            tbAddress.Value = vAttList(0).TextString
    End Select
    
    GoTo Get_Block
    
Exit_Sub:
    Me.show
End Sub

Private Sub cbPlace_Click()
    Dim dInsertPnt(0 To 2) As Double
    Dim objBlock As AcadBlockReference
    Dim vAttList, vTemp As Variant
    
    dInsertPnt(0) = CDbl(tbEast.Value)
    dInsertPnt(1) = CDbl(tbNorth.Value)
    dInsertPnt(2) = 0#
    
    vTemp = Split(tbLocation.Value, "/")
    
    Set objBlock = ThisDrawing.ModelSpace.InsertBlock(dInsertPnt, "MW_EQUIPMENT", 1#, 1#, 1#, 0#)
    objBlock.Layer = "MW_Equipment"
    vAttList = objBlock.GetAttributes
    
    vAttList(0).TextString = tbLocation.Value
    vAttList(1).TextString = "5"
    vAttList(2).TextString = "LEOMA" 'WC
    If Not tbSplitter.Value = "" Then vAttList(3).TextString = tbName.Value
    vAttList(4).TextString = tbAddress.Value 'Address
    If Not tbSplitter.Value = "" Then vAttList(5).TextString = tbSplitter.Value 'model
    vAttList(6).TextString = vTemp(0) 'route
    vAttList(7).TextString = "FBR_SPLICE" 'def name
    vAttList(8).TextString = tbSize.Value 'Size
    vAttList(9).TextString = tbIn.Value 'In
    vAttList(10).TextString = tbMethod.Value    'method
    vAttList(11).TextString = tbOut.Value    'Out
    
    objBlock.Update
End Sub

Private Sub cbQuit_Click()
    Me.Hide
End Sub

Private Sub UserForm_Click()

End Sub

Attribute VB_Name = "AddSpanRecord"
Attribute VB_Base = "0{E9799B8C-8143-4390-8BC3-B4984379D39D}{A7B1C471-74EA-411E-B289-3B3AE2930480}"
Attribute VB_GlobalNameSpace = False
Attribute VB_Creatable = False
Attribute VB_PredeclaredId = True
Attribute VB_Exposed = False
Attribute VB_TemplateDerived = False
Attribute VB_Customizable = False
Private Sub cbClear_Click()
    tbLength.Value = ""
    tbCounts.Value = ""
    tbCoil1.Value = ""
    tbCoil2.Value = ""
End Sub

Private Sub cbGet_Click()
    Dim objEntity As AcadEntity
    Dim objBlock As AcadBlockReference
    Dim vAttList, vReturnPnt As Variant
    Dim strLine As String
    
    Me.Hide
    
    On Error Resume Next
    
Add_Another:
    
    Err = 0
    ThisDrawing.Utility.GetEntity objEntity, vReturnPnt, vbCr & "Select Block with Data:"
    If Not Err = 0 Then GoTo Exit_Sub
    
    If Not TypeOf objEntity Is AcadBlockReference Then GoTo Exit_Sub
    
    Set objBlock = objEntity
    
    Select Case objBlock.Name
        Case "cable_span"
            vAttList = objBlock.GetAttributes
            
            strLine = Replace(vAttList(2).TextString, "'", "")
            tbLength.Value = strLine
        Case "CableCounts"
            vAttList = objBlock.GetAttributes
            
            strLine = Replace(vAttList(0).TextString, "\P", "+")
            strLine = Replace(strLine, ": ", ",")
            tbCounts.Value = strLine
        Case "Map coil"
            vAttList = objBlock.GetAttributes
            
            strLine = CInt(Replace(vAttList(0).TextString, "'", "")) / 2
            
            If tbCoil1.Value = "" Then
                tbCoil1.Value = strLine
            Else
                tbCoil2.Value = strLine
            End If
    End Select
    
    GoTo Add_Another
    
Exit_Sub:
    Me.show
End Sub

Private Sub cbPlace_Click()
    Dim objEntity As AcadEntity
    Dim vReturnPnt As Variant
    Dim boolVal As Boolean
    Dim iLength As Integer
    
    Dim amap As AcadMap
    Dim ODRcs As ODRecords
    Dim ODRc As ODRecord
    Dim tbl As ODTable
    Dim tbls As ODTables
    
    iLength = CInt(tbLength.Value)
    If Not tbCoil1.Value = "" Then iLength = iLength + CInt(tbCoil1.Value)
    If Not tbCoil2.Value = "" Then iLength = iLength + CInt(tbCoil2.Value)
    
    Me.Hide
    
    On Error Resume Next
    
    ThisDrawing.Utility.GetEntity objEntity, vReturnPnt, vbCr & "Select Cable Span to add Data:"
    If Not Err = 0 Then GoTo Exit_Sub
    
    Set amap = ThisDrawing.Application.GetInterfaceObject("AutoCADMap.Application")
    
    Set tbls = amap.Projects(ThisDrawing).ODTables
    If tbls.Count > 0 Then
        For Each tbl In tbls
            If tbl.Name = "Spans" Then GoTo Exit_For
        Next
    End If
Exit_For:

    Set ODRcs = tbl.GetODRecords
            
    boolVal = ODRcs.Init(objEntity, True, False)
    Set ODRc = ODRcs.Record
    
    ODRc.Item(1).Value = iLength
    ODRc.Item(2).Value = tbCounts.Value
    boolVal = ODRcs.Update(ODRc)
    
Exit_Sub:
    Me.show
End Sub

Private Sub cbQuit_Click()
    Me.Hide
End Sub

Private Sub UserForm_Click()

End Sub

Attribute VB_Name = "CensusBlockProviders"
Attribute VB_Base = "0{72D2868F-FF69-42AD-BA8A-CE281C1DAC90}{03DD7236-790B-4998-B1A0-2E66AD937E1A}"
Attribute VB_GlobalNameSpace = False
Attribute VB_Creatable = False
Attribute VB_PredeclaredId = True
Attribute VB_Exposed = False
Attribute VB_TemplateDerived = False
Attribute VB_Customizable = False
Dim strFilePath As String

Private Sub cbCreateFile_Click()
    Dim vLine As Variant
    Dim vData As Variant
    Dim strFileName As String
    Dim strOutputName As String
    Dim strLine As String
    Dim fName As String
    Dim lCount As Long
    Dim iOffset As Integer
    
    lCount = 0
    
    strFileName = strFilePath & tbCSV.Value
    strOutputName = strFilePath & tbCompany.Value & " Broadband Block List.csv"
    strOutputName = Replace(strOutputName, "&", "_")
    
    fName = Dir(strFileName)
    If fName = "" Then
        MsgBox "Error finding file."
        Exit Sub
    End If
    
    Open strFileName For Input As #1
    Open strOutputName For Output As #2
    
    Line Input #1, strLine
    Print #2, strLine
    
    While Not EOF(1)
        Line Input #1, strLine
        vData = Split(strLine, ",")
        If UBound(vData) > 14 Then
            iOffset = UBound(vData) - 14
        Else
            iOffset = 0
        End If
        
        If InStr(vData(7 + iOffset), tbCompany.Value) > 0 Then
            Print #2, strLine
        End If
        lCount = lCount + 1
    Wend
Exit_Sub:
    Close #1
    Close #2
    
    MsgBox "Done."
End Sub

Private Sub cbCSV_Click()
    Dim vLine As Variant
    Dim vData As Variant
    Dim strFileName As String
    Dim strOutputName As String
    Dim strLine As String
    Dim fName As String
    Dim lCount As Long
    
    lCount = 0
    
    strFileName = strFilePath & tbCSV.Value
    strOutputName = strFilePath & tbCCode.Value & " Broadband Block List.csv"
    
    fName = Dir(strFileName)
    If fName = "" Then
        MsgBox "Error finding file."
        Exit Sub
    End If
    
    Open strFileName For Input As #1
    Open strOutputName For Output As #2
    
    Line Input #1, strLine
    Print #2, strLine
    
    While Not EOF(1)
        Line Input #1, strLine
        vData = Split(strLine, ",")
        ' vdata(3) = provider
        'vdata(9) = census block
        'If vData(10) = "60" Then GoTo Next_Line_Input
        
        If Left(vData(9), 5) = tbCCode.Value Then
            Print #2, strLine
            'lbCB.AddItem vData(9)
            'lbCB.List(lbCB.ListCount - 1, 1) = vData(10)
            'lbCB.List(lbCB.ListCount - 1, 2) = vData(12)
            'lbCB.List(lbCB.ListCount - 1, 3) = vData(13)
            'lbCB.List(lbCB.ListCount - 1, 4) = vData(7)
        End If
'Next_Line_Input:
        lCount = lCount + 1
    Wend
Exit_Sub:
    Close #1
    Close #2
    
    tbCount.Value = lbCB.ListCount
    tbFileLines.Value = lCount
    
    'For i = 0 To lbCB.ListCount - 1
        'If Not lbProviders.ListCount < 0 Then
            'For j = 0 To lbProviders.ListCount - 1
                'If lbProviders.List(j) = lbCB.List(i, 4) Then GoTo Next_Line
            'Next j
            
            'lbProviders.AddItem lbCB.List(i, 4)
        'End If
'Next_Line:
    'Next i
End Sub

Private Sub cbFilter_Click()
    If lbProviders.ListCount < 0 Then Exit Sub
    
    Dim iDown, iUp As Integer
    Dim iOffset As Integer
    Dim strCompany As String
    
    iDown = CInt(tbMinDown.Value)
    iUp = CInt(tbMinUp.Value)
    iOffset = 0
    strCompany = ""
    
    For i = 0 To lbProviders.ListCount - 1
        If lbProviders.Selected(i) Then strCompany = lbProviders.List(i)
    Next i
    
    If strCompany = "" Then GoTo Skip_Provider
    
    For i = 0 To lbCB.ListCount - 1
        If Not lbCB.List(i - iOffset, 4) = strCompany Then
            lbCB.RemoveItem i - iOffset
            iOffset = iOffset + 1
        End If
    Next i
    
Skip_Provider:
    
    iOffset = 0
    
    For i = 0 To lbCB.ListCount - 1
        If iDown > lbCB.List(i - iOffset, 2) Then
            lbCB.RemoveItem i - iOffset
            iOffset = iOffset + 1
            GoTo Next_I
        End If
        
        If iUp > lbCB.List(i - iOffset, 3) Then
            lbCB.RemoveItem i - iOffset
            iOffset = iOffset + 1
        End If
Next_I:
    Next i
    
    tbCount.Value = lbCB.ListCount
    
    lbProviders.Clear
    
    For i = 0 To lbCB.ListCount - 1
        If Not lbProviders.ListCount < 0 Then
            For j = 0 To lbProviders.ListCount - 1
                If lbProviders.List(j) = lbCB.List(i, 4) Then GoTo Next_Line
            Next j
            
            lbProviders.AddItem lbCB.List(i, 4)
        End If
Next_Line:
    Next i
    
End Sub

Private Sub cbGetList_Click()
    Dim vLine As Variant
    Dim vData As Variant
    Dim strFileName As String
    Dim strLine As String
    Dim strTemp As String
    Dim fName As String
    Dim lCount As Long
    Dim iOffset As Integer
    
    lCount = 0
    
    strFileName = strFilePath & tbCSV.Value
    
    fName = Dir(strFileName)
    If fName = "" Then
        MsgBox "Error finding file."
        Exit Sub
    End If
    
    Open strFileName For Input As #1
    
    While Not EOF(1)
        Line Input #1, strLine
        vData = Split(strLine, ",")
        If UBound(vData) > 14 Then
            iOffset = UBound(vData) - 14
        Else
            iOffset = 0
        End If
        ' vdata(3) = provider
        'vdata(9) = census block
        If vData(10 + iOffset) = "60" Then GoTo Next_Line_Input
        
        If Left(vData(9 + iOffset), 5) = tbCCode.Value Then
            lbCB.AddItem vData(9 + iOffset)
            lbCB.List(lbCB.ListCount - 1, 1) = vData(10 + iOffset)
            lbCB.List(lbCB.ListCount - 1, 2) = vData(12 + iOffset)
            lbCB.List(lbCB.ListCount - 1, 3) = vData(13 + iOffset)
            strTemp = LCase(Left(vData(7 + iOffset), 4))
            If strTemp = " inc" Or strTemp = " llc" Then
                strTemp = vData(6 + iOffset) & ", " & vData(7 + iOffset)
                lbCB.List(lbCB.ListCount - 1, 4) = Replace(strTemp, """", "")
            Else
                lbCB.List(lbCB.ListCount - 1, 4) = vData(7 + iOffset)
            End If
        End If
Next_Line_Input:
        lCount = lCount + 1
    Wend
Exit_Sub:
    Close #1
    
    tbCount.Value = lbCB.ListCount
    tbFileLines.Value = lCount
    
    For i = 0 To lbCB.ListCount - 1
        Select Case lbCB.List(i, 1)
            Case "10"
                lbCB.List(i, 1) = "A xDSL"
            Case "11"
                lbCB.List(i, 1) = "ADSL2"
            Case "12"
                lbCB.List(i, 1) = "VDSL"
            Case "20"
                lbCB.List(i, 1) = "S xDSL"
            Case "30"
                lbCB.List(i, 1) = "T-1, Other"
            Case "40"
                lbCB.List(i, 1) = "DOCSIS <1"
            Case "41"
                lbCB.List(i, 1) = "DOCSIS <=2"
            Case "42"
                lbCB.List(i, 1) = "DOCSIS 3.0"
            Case "43"
                lbCB.List(i, 1) = "DOCSIS 3.1"
            Case "50"
                lbCB.List(i, 1) = "FIBER"
            Case "60"
                lbCB.List(i, 1) = "SAT"
            Case "70"
                lbCB.List(i, 1) = "Wireless"
            Case "90"
                lbCB.List(i, 1) = "POCO"
            Case "0"
                lbCB.List(i, 1) = "Other"
        End Select
        
        If Not lbProviders.ListCount < 0 Then
            For j = 0 To lbProviders.ListCount - 1
                If lbProviders.List(j) = lbCB.List(i, 4) Then GoTo Next_Line
            Next j
            
            lbProviders.AddItem lbCB.List(i, 4)
        End If
Next_Line:
    Next i
End Sub

Private Sub cbMove_Click()
    If tbLayer.Value = "" Then tbLayer.Value = "Internet - Served"
    
    Dim objLayer As AcadLayer
    Dim strLayer, strBlockLayer As String
    Dim strCensus As String
    Dim objObject, objTemp As AcadObject
    Dim objPoly As AcadObject
    Dim objLWP, objLWP2 As AcadLWPolyline
    Dim vReturnPnt As Variant
    
    Dim amap As AcadMap
    Dim ODRcs As ODRecords
    Dim ODRc As ODRecord
    Dim tbl As ODTable
    Dim tbls As ODTables
    
    Dim filterType, filterValue As Variant
    Dim grpCode(0) As Integer
    Dim grpValue(0) As Variant
    Dim objSS2 As AcadSelectionSet
    
    On Error Resume Next
    
    Me.Hide
    
    strLayer = tbLayer.Value
    Set objLayer = ThisDrawing.Layers.Add(strLayer)
    'If Err = 0 Then
        'objLayer.TrueColor = acBlue
    'End If
    Err = 0
    
    ThisDrawing.Utility.GetEntity objPoly, vReturnPnt, "Select Census Block Layer: "
    Set objLWP = objPoly
    strBlockLayer = objLWP.Layer
    
    'MsgBox strLayer & vbCr & strBlockLayer
    
    grpCode(0) = 8
    grpValue(0) = strBlockLayer
    filterType = grpCode
    filterValue = grpValue
    
    Err = 0
    Set objSS2 = ThisDrawing.SelectionSets.Add("objSS2")
    If Not Err = 0 Then
        Set objSS2 = ThisDrawing.SelectionSets.Item("objSS2")
        objSS2.Clear
    End If
    
    objSS2.Select acSelectionSetAll, , , filterType, filterValue
    MsgBox "Census Blocks found:  " & objSS2.Count
    
    Set amap = ThisDrawing.Application.GetInterfaceObject("AutoCADMap.Application")
    
    Set tbls = amap.Projects(ThisDrawing).ODTables
    If tbls.Count > 0 Then
        For Each tbl In tbls
            If tbl.Name = strBlockLayer Then GoTo Exit_For
        Next
    End If
Exit_For:
    Set ODRcs = tbl.GetODRecords

    For Each objObject In objSS2
        Set objLWP2 = objObject.Copy
        
        boolVal = ODRcs.Init(objObject, True, False)
        Set ODRc = ODRcs.Record
        
        strCensus = ODRc.Item(5).Value
        
        For i = 0 To lbCB.ListCount - 1
            If lbCB.List(i, 0) = strCensus Then
                'ODRc.Item(8).Value = lbCB.List(i, 4)
                'ODRc.Item(9).Value = lbCB.List(i, 1)
                'ODRc.Item(10).Value = lbCB.List(i, 2) & " / " & lbCB.List(i, 3)
                'boolVal = ODRcs.Update(ODRc)
                'boolVal = ODRcs.c(ODRc)
                
                objLWP2.Layer = strLayer
                objLWP2.Update
                GoTo Next_Object
            End If
        Next i
        
        objLWP2.Delete
Next_Object:
    Next objObject
    
    grpCode(0) = 8
    grpValue(0) = strLayer
    filterType = grpCode
    filterValue = grpValue
    
    objSS2.Clear
    objSS2.Select acSelectionSetAll, , , filterType, filterValue
    
    For Each objObject In objSS2
        boolVal = ODRcs.Init(objObject, True, False)
        Set ODRc = ODRcs.Record
        
        'If ODRc.Item(8).Value = lbProviders.List(0) Then
            For i = 0 To lbCB.ListCount - 1
                If ODRc.Item(5).Value = lbCB.List(i, 0) Then
                    ODRc.Item(8).Value = lbCB.List(i, 4)
                    ODRc.Item(9).Value = lbCB.List(i, 1)
                    ODRc.Item(10).Value = lbCB.List(i, 2) & " / " & lbCB.List(i, 3)
                    boolVal = ODRcs.Update(ODRc)
                    boolVal = ODRcs.c(ODRc)
                    
                    GoTo Data_Changed
                End If
            Next i
        'End If
Data_Changed:
    Next objObject
    
    objSS2.Clear
    objSS2.Delete
    
    Me.show
End Sub

Private Sub cbQuit_Click()
    Me.Hide
End Sub

Private Sub lbProviders_Change()
    
    If lbProviders.ListIndex < 0 Then Exit Sub
    tbLayer.Value = lbProviders.List(lbProviders.ListIndex)
End Sub

Private Sub UserForm_Initialize()
    lbCB.ColumnCount = 5
    lbCB.ColumnWidths = "90;60;36;36;144"
    
    strFilePath = ThisDrawing.Path & "\"
End Sub

Attribute VB_Name = "ClosureForm"
Attribute VB_Base = "0{F21075F5-9F08-4A86-B2A1-E0F61DB95E28}{9CA409EB-B9DE-4A95-94EB-FD608B5AE957}"
Attribute VB_GlobalNameSpace = False
Attribute VB_Creatable = False
Attribute VB_PredeclaredId = True
Attribute VB_Exposed = False
Attribute VB_TemplateDerived = False
Attribute VB_Customizable = False
Dim strListbox As String

Private Sub cbAddSplice_Click()
    Dim vTemp As Variant
    Dim vFrom, vTo As Variant
    Dim strRow As String
    Dim iFrom, iTo As Integer
    
    For i = 0 To lbFrom.ListCount - 1
        If lbFrom.Selected(i) Then GoTo Found_From
    Next i
    
    Exit Sub
Found_From:
    vFrom = Split(lbFrom.List(i, 0), "-")
    
    If UBound(vFrom) = 0 Then
        iFrom = 0
    Else
        iFrom = CInt(vFrom(1)) - CInt(vFrom(0))
    End If
    
    For j = 0 To lbTo.ListCount - 1
        If lbTo.Selected(j) Then GoTo Found_To
    Next j
    
    Exit Sub
Found_To:
    vTo = Split(lbTo.List(j, 0), "-")
    If UBound(vTo) = 0 Then
        iTo = 0
    Else
        iTo = CInt(vTo(1)) - CInt(vTo(0))
    End If
    
    If Not iFrom = iTo Then
        MsgBox "Number of Fibers Not Equal"
        Exit Sub
    End If
    
    vTemp = Split(Frame2.Caption, "-")
    strRow = vTemp(1)
    lbSplices.AddItem strRow
    lbSplices.List(lbSplices.ListCount - 1, 1) = lbFrom.List(i, 0)
    
    vTemp = Split(Frame1.Caption, "-")
    lbSplices.List(lbSplices.ListCount - 1, 2) = vTemp(1)
    lbSplices.List(lbSplices.ListCount - 1, 3) = lbTo.List(j, 0)
End Sub

Private Sub cbAddToTerm_Click()
    For i = 0 To lbFrom.ListCount - 1
        If lbFrom.Selected(i) Then
            Dim iFrom, iTo As Integer
            Dim iPort As Integer
            Dim vTemp, vFrom As Variant
            
            lbFrom.List(i, 3) = "TERM"
            vTemp = Split(lbFrom.List(i, 2), "-")
            iFrom = CInt(vTemp(0))
            If UBound(vTemp) < 1 Then
                iTo = iFrom
            Else
                iTo = CInt(vTemp(1))
            End If
            iPort = lbSub.ListCount + 1
            
            For j = iFrom To iTo
                lbSub.AddItem iPort, iPort - 1
                lbSub.List(iPort - 1, 1) = lbFrom.List(i, 1)
                lbSub.List(iPort - 1, 2) = j
                'lbSub.List(iPort - 1, 3) = "TERM"
                'lbSub.List(iPort - 1, 4) = lbFrom.List(i, 4)
                iPort = iPort + 1
            Next j
    
            vTemp = Split(Frame2.Caption, "-")
            strRow = vTemp(1)
            lbSplices.AddItem strRow
            lbSplices.List(lbSplices.ListCount - 1, 1) = lbFrom.List(i, 0)
            
            lbSplices.List(lbSplices.ListCount - 1, 2) = "TERM"
            lbSplices.List(lbSplices.ListCount - 1, 3) = "1-" & lbSub.ListCount
            
        End If
    Next i
  
End Sub

Private Sub cbClosure_Change()
    If cbClosure.Value = "" Then Exit Sub
    
    
    Dim excelApp As Excel.Application
    Dim ws As Excel.Worksheet
    Dim fName As String
    Dim entPole As AcadObject
    Dim objBlock As AcadBlockReference
    Dim vAttList, basePnt As Variant
    Dim vTemp, vLine As Variant
    Dim vLast As Variant
    Dim strNext As String
    Dim strPath, strTemp As String
    Dim strPole, strType As String
    Dim lRow As Long
    Dim iI As Integer
    
    'Me.Hide
  On Error Resume Next
    
    vTemp = Split(cbClosure.Value, "~")
    lRow = CLng(vTemp(UBound(vTemp)))
    tbRow.Value = lRow
    'strNext = vTemp(UBound(vTemp))
    
    strPath = ThisDrawing.FullName
    strPath = Replace(strPath, ".dwg", ".xlsx")
    
    fName = Dir(strPath)
    If fName = "" Then
        MsgBox "There are no Records in folder."
        Exit Sub
    End If
    
    Set excelApp = CreateObject("Excel.Application")
    excelApp.Visible = False
    
    Err = 0
    Set wb = Excel.Workbooks.Open(strPath)
    If Not Err = 0 Then
        MsgBox "Error opening file"
        GoTo Exit_Sub
    End If
    
    cbType.Value = Sheets("Closures").Cells(lRow, 2).Value
    cbSize.Value = Sheets("Closures").Cells(lRow, 3).Value
    tbMaterial.Value = Sheets("Closures").Cells(lRow, 4).Value
    
    lbCables.Clear
    vTemp = Split(Sheets("Closures").Cells(lRow, 7).Value, "+")
    For x = 0 To UBound(vTemp)
        vLine = Split(vTemp(x), "~")
        lbCables.AddItem vLine(0)
        iI = lbCables.ListCount - 1
        lbCables.List(iI, 1) = vLine(1)
        lbCables.List(iI, 3) = vLine(2)
        'lbCables.List(lbCables.ListCount - 1, 3) = vLine(3)
    
        lRow = 2
        While Not Sheets("Cables").Cells(lRow, 1).Value = ""
            If Sheets("Cables").Cells(lRow, 1).Value = lbCables.List(iI, 0) Then
                If Sheets("Cables").Cells(lRow, 2).Value = lbCables.List(iI, 1) Then
                    vLast = Split(Sheets("Cables").Cells(lRow, 10).Value, "-")
                    If vLast(0) = lbCables.List(iI, 3) Then
                        lbCables.List(iI, 2) = Sheets("Cables").Cells(lRow, 7).Value & Sheets("Cables").Cells(lRow, 8).Value
                        lbCables.List(iI, 4) = lRow
                        GoTo Next_X
                    End If
                End If
            End If
            lRow = lRow + 1
        Wend
Next_X:
    Next x
    
    lbSplices.Clear
    vTemp = Split(Sheets("Closures").Cells(lRow, 8).Value, "+")
    For y = 0 To UBound(vTemp)
        vLine = Split(vTemp(y), ">>")
        
    Next y
    
    cbGetClosure.Enabled = False
    
Exit_Sub:
    'ActiveWorkbook.Save
    ActiveWorkbook.Close
    
    'Me.show
End Sub

Private Sub cbGetClosure_Click()
    If tbStructure.Value = "" Then Exit Sub
    If cbPosition.Value = "" Then Exit Sub
    If lbCables.ListCount < 1 Then Exit Sub
    
    Dim excelApp As Excel.Application
    Dim ws As Excel.Worksheet
    Dim fName As String
    Dim entPole As AcadObject
    Dim objBlock As AcadBlockReference
    Dim vAttList, basePnt As Variant
    Dim vTemp, vLine As Variant
    Dim vLast As Variant
    Dim strNext As String
    Dim strPath, strTemp As String
    Dim strPole, strType As String
    Dim strClosure As String
    Dim strChar As String
    Dim lRow As Long
    Dim lChar As Long
    Dim iI As Integer
    
    'Me.Hide
  On Error Resume Next
    
    strChar = "@"
    lChar = 64
    strClosure = tbStructure.Value & "~" & cbPosition.Value & "~"
    
    If cbClosure.ListCount = 0 Then
        strClosure = strClosure & "A"
    Else
        For i = 0 To cbClosure.ListCount - 1
            vTemp = Split(cbClosure.List(i), "~")
            If vTemp(1) = cbPosition.Value Then
                If Asc(Left(vTemp(2), 1)) > lChar Then lChar = Asc(Left(vTemp(2), 1))
            End If
        Next i
        
        lChar = lChar + 1
        strClosure = strClosure & Chr(lChar)
    End If
    
    strPath = ThisDrawing.FullName
    strPath = Replace(strPath, ".dwg", ".xlsx")
    
    fName = Dir(strPath)
    If fName = "" Then
        MsgBox "There are no Records in folder."
        Exit Sub
    End If
    
    Set excelApp = CreateObject("Excel.Application")
    excelApp.Visible = False
    
    Err = 0
    Set wb = Excel.Workbooks.Open(strPath)
    If Not Err = 0 Then
        MsgBox "Error opening file"
        GoTo Exit_Sub
    End If
    
    lRow = 2
    While Not Sheets("Closures").Cells(lRow, 1).Value = ""
        lRow = lRow + 1
    Wend
    
    Sheets("Closures").Cells(lRow, 1).Value = strClosure
    Sheets("Closures").Cells(lRow, 2).Value = cbType.Value
    Sheets("Closures").Cells(lRow, 3).Value = cbSize.Value
    Sheets("Closures").Cells(lRow, 4).Value = tbMaterial.Value
    Sheets("Closures").Cells(lRow, 5).Value = Replace(ThisDrawing.Name, ".dwg", "") '<--------------- Get Job Number
    Sheets("Closures").Cells(lRow, 6).Value = cbPosition.Value
    
    strTemp = lbCables.List(0, 0) & "~" & lbCables.List(0, 1) & "~" & lbCables.List(0, 3)
    If lbCables.ListCount > 1 Then
        For s = 1 To lbCables.ListCount - 1
            strTemp = strTemp & "+" & lbCables.List(s, 0) & "~" & lbCables.List(s, 1) & "~" & lbCables.List(s, 3)
        Next s
    End If
    Sheets("Closures").Cells(lRow, 7).Value = strTemp
    
    strClosure = strClosure & "~" & lRow
    cbClosure.AddItem strClosure
    
    ActiveWorkbook.Save
        
Exit_Sub:
    ActiveWorkbook.Close
    
    'Me.show
End Sub

Private Sub cbPosition_Change()

End Sub

Private Sub cbQuit_Click()
    Me.Hide
End Sub

Private Sub cbUpdate_Click()
    Dim iFCount, iTCount As Integer
    Dim iI, iFFiber, iTFiber As Integer
    Dim i0, i1, i2, i3, i4, i5 As Integer
    Dim vLine As Variant
    
    If strListbox = "lbFrom" Then
        GoTo lbFrom_Code
    End If
    
    iI = lbTo.ListIndex
    
    i0 = CInt(tbC0.Value)
    i1 = CInt(tbC1.Value)
    If tbC2.Value = "" Then
        i2 = 0
    Else
        i2 = CInt(tbC2.Value)
    End If
    If tbC3.Value = "" Then
        i3 = 0
    Else
        i3 = CInt(tbC3.Value)
    End If
    i4 = CInt(tbC4.Value)
    i5 = CInt(tbC5.Value)
    
    vLine = Split(lbTo.List(iI, 0), "-")
    iFFiber = CInt(vLine(0))
    
    If i0 = i1 Then
        lbTo.List(iI, 2) = i0
        lbTo.List(iI, 0) = iFFiber
        iFFiber = iFFiber + 1
    Else
        lbTo.List(iI, 2) = i0 & "-" & i1
        iTFiber = iFFiber + i1 - i0
        lbTo.List(iI, 0) = iFFiber & "-" & iTFiber
        iFFiber = iTFiber + 1
    End If
    
    If Not i3 = 0 Then
        lbTo.AddItem "", iI + 1
        lbTo.List(iI + 1, 1) = lbTo.List(iI, 1)
        If i2 = i3 Then
            lbTo.List(iI + 1, 2) = i2
            lbTo.List(iI + 1, 0) = iFFiber
            iFFiber = iFFiber + 1
        Else
            lbTo.List(iI + 1, 2) = i2 & "-" & i3
            iTFiber = iFFiber + i3 - i2
            lbTo.List(iI + 1, 0) = iFFiber & "-" & iTFiber
            iFFiber = iTFiber + 1
        End If
        lbTo.List(iI + 1, 3) = lbTo.List(iI, 3)
        lbTo.List(iI + 1, 4) = lbTo.List(iI, 4)
        
        iI = iI + 1
    End If
    
    lbTo.AddItem "", iI + 1
    lbTo.List(iI + 1, 1) = lbTo.List(iI, 1)
    If i4 = i5 Then
        lbTo.List(iI + 1, 2) = i4
        lbTo.List(iI + 1, 0) = iFFiber
    Else
        lbTo.List(iI + 1, 2) = i4 & "-" & i5
        iTFiber = iFFiber + i5 - i4
        lbTo.List(iI + 1, 0) = iFFiber & "-" & iTFiber
    End If
    lbTo.List(iI + 1, 3) = lbTo.List(iI, 3)
    
    GoTo Clear_Out_Frame
    
lbFrom_Code:
    
    iI = lbFrom.ListIndex
    
    i0 = CInt(tbC0.Value)
    i1 = CInt(tbC1.Value)
    If tbC2.Value = "" Then
        i2 = 0
    Else
        i2 = CInt(tbC2.Value)
    End If
    If tbC3.Value = "" Then
        i3 = 0
    Else
        i3 = CInt(tbC3.Value)
    End If
    i4 = CInt(tbC4.Value)
    i5 = CInt(tbC5.Value)
    
    vLine = Split(lbFrom.List(iI, 0), "-")
    iFFiber = CInt(vLine(0))
    
    If i0 = i1 Then
        lbFrom.List(iI, 2) = i0
        lbFrom.List(iI, 0) = iFFiber
        iFFiber = iFFiber + 1
    Else
        lbFrom.List(iI, 2) = i0 & "-" & i1
        iTFiber = iFFiber + i1 - i0
        lbFrom.List(iI, 0) = iFFiber & "-" & iTFiber
        iFFiber = iTFiber + 1
    End If
    
    If Not i3 = 0 Then
        lbFrom.AddItem "", iI + 1
        lbFrom.List(iI + 1, 1) = lbFrom.List(iI, 1)
        If i2 = i3 Then
            lbFrom.List(iI + 1, 2) = i2
            lbFrom.List(iI + 1, 0) = iFFiber
            iFFiber = iFFiber + 1
        Else
            lbFrom.List(iI + 1, 2) = i2 & "-" & i3
            iTFiber = iFFiber + i3 - i2
            lbFrom.List(iI + 1, 0) = iFFiber & "-" & iTFiber
            iFFiber = iTFiber + 1
        End If
        lbFrom.List(iI + 1, 3) = lbFrom.List(iI, 3)
        'lbFrom.List(iI + 1, 4) = lbFrom.List(iI, 4)
        
        iI = iI + 1
    End If
    
    lbFrom.AddItem "", iI + 1
    lbFrom.List(iI + 1, 1) = lbFrom.List(iI, 1)
    If i4 = i5 Then
        lbFrom.List(iI + 1, 2) = i4
        lbFrom.List(iI + 1, 0) = iFFiber
    Else
        lbFrom.List(iI + 1, 2) = i4 & "-" & i5
        iTFiber = iFFiber + i5 - i4
        lbFrom.List(iI + 1, 0) = iFFiber & "-" & iTFiber
    End If
    lbFrom.List(iI + 1, 3) = lbFrom.List(iI, 3)
    'lbFrom.List(iI + 1, 4) = lbFrom.List(iI, 4)

Clear_Out_Frame:
    
    tbC0.Value = ""
    tbC1.Value = ""
    tbC2.Value = ""
    tbC3.Value = ""
    tbC4.Value = ""
    tbC5.Value = ""
    cbUpdate.Enabled = False
    
    'cbUpdateRecord.Enabled = True
End Sub

Private Sub CommandButton1_Click()

End Sub

Private Sub cbUpdateClosure_Click()
    
End Sub

Private Sub Label10_Click()
    Dim excelApp As Excel.Application
    Dim ws As Excel.Worksheet
    Dim fName As String
    Dim entPole As AcadObject
    Dim objBlock As AcadBlockReference
    Dim vAttList, basePnt As Variant
    Dim vTemp As Variant
    Dim strNext As String
    Dim strPath, strTemp As String
    Dim strPole, strType As String
    Dim lRow As Long
    Dim iI As Integer
    
    Me.Hide
  On Error Resume Next
    
    ThisDrawing.Utility.GetEntity entPole, basePnt, "Select Structure: "
    If TypeOf entPole Is AcadBlockReference Then
        Set objBlock = entPole
    Else
        MsgBox "Not a valid pole."
        GoTo Exit_Sub
    End If
    
    vAttList = objBlock.GetAttributes
    
    strNext = vAttList(0).TextString
    If Not Err = 0 Then GoTo Exit_Sub
    
    tbStructure.Value = strNext
    
    cbClosure.Clear
    
    'cbClosure.AddItem strNext
    
    strPath = ThisDrawing.FullName
    strPath = Replace(strPath, ".dwg", ".xlsx")
    
    fName = Dir(strPath)
    If fName = "" Then
        MsgBox "There are no Records in folder."
        Exit Sub
    End If
    
    Set excelApp = CreateObject("Excel.Application")
    excelApp.Visible = False
    
    Err = 0
    Set wb = Excel.Workbooks.Open(strPath)
    If Not Err = 0 Then
        MsgBox "Error opening file"
        GoTo Exit_Sub
    End If
    
    lRow = 2
    While Not Sheets("Closures").Cells(lRow, 1).Value = ""
        vTemp = Split(Sheets("Closures").Cells(lRow, 1).Value, "~")
        If vTemp(0) = strNext Then
            cbClosure.AddItem Sheets("Closures").Cells(lRow, 1).Value & "~" & lRow
        End If
        
        lRow = lRow + 1
    Wend
    
    lbCables.Clear
    lCables.Caption = "Cables at Pole"
    
    lRow = 2
    While Not Sheets("Cables").Cells(lRow, 1).Value = ""
        'vTemp = Split(Sheets("Closures").Cells(lRow, 1).Value, "~")
        'If vTemp(0) = strNext Then
            'cbClosure.AddItem Sheets("Closures").Cells(lRow, 1).Value & "~" & lRow
        'End If
        If Sheets("Cables").Cells(lRow, 1).Value = strNext Or Sheets("Cables").Cells(lRow, 2).Value = strNext Then
            lbCables.AddItem Sheets("Cables").Cells(lRow, 1).Value
            iI = lbCables.ListCount - 1
            lbCables.List(iI, 1) = Sheets("Cables").Cells(lRow, 2).Value
            lbCables.List(iI, 2) = Sheets("Cables").Cells(lRow, 7).Value & Sheets("Cables").Cells(lRow, 8).Value
            
            vTemp = Split(Sheets("Cables").Cells(lRow, 10).Value, "-")
            lbCables.List(iI, 3) = vTemp(0)
            lbCables.List(iI, 4) = lRow
            
            For h = 0 To cbPosition.ListCount
                If cbPosition.List(h) = vTemp(0) Then GoTo Already_There
            Next h
            cbPosition.AddItem vTemp(0)
            
Already_There:
        End If
        
        lRow = lRow + 1
    Wend
    
    
    
Exit_Sub:
    'ActiveWorkbook.Save
    ActiveWorkbook.Close
    
    Me.show
End Sub

Private Sub lbCables_Click()
    Exit Sub
    
    Dim excelApp As Excel.Application
    Dim ws As Excel.Worksheet
    Dim fName As String
    Dim entPole As AcadObject
    Dim objBlock As AcadBlockReference
    Dim vAttList, basePnt As Variant
    Dim vTemp, vLine As Variant
    Dim vNext, vNLine As Variant
    Dim strNext As String
    Dim strPath, strTemp As String
    Dim strPole, strType As String
    Dim lRow, lCable As Long
    Dim iI, iIndex As Integer
    
    'Me.Hide
  On Error Resume Next
    
    lRow = CLng(lbCables.List(lbCables.ListIndex, 4))
    
    strPath = ThisDrawing.FullName
    strPath = Replace(strPath, ".dwg", ".xlsx")
    
    fName = Dir(strPath)
    If fName = "" Then
        MsgBox "There are no Records in folder."
        Exit Sub
    End If
    
    Set excelApp = CreateObject("Excel.Application")
    excelApp.Visible = False
    
    Err = 0
    Set wb = Excel.Workbooks.Open(strPath)
    If Not Err = 0 Then
        MsgBox "Error opening file"
        GoTo Exit_Sub
    End If
    
    lbTo.Clear
    
    'lCable = 2
    
    vTemp = Split(Sheets("Cables").Cells(lRow, 10).Value, "-")
    iI = CInt(vTemp(1))
    
    For x = 1 To iI
        vTemp = Split(Sheets("Cables").Cells(lRow, 10 + iI).Value, "++")
        vLine = Split(vTemp(UBound(vTemp)), "~")
        
        'strTemp = Sheets("Cables").Cells(lRow, 2).Value
        
        lbTo.AddItem vTemp(0)   'vLine(0)
        lbTo.List(lbTo.ListCount - 1, 1) = vLine(0)
        lbTo.List(lbTo.ListCount - 1, 2) = vLine(1) 'Sheets("Cables").Cells(lRow, 1).Value
        If vLine(2) = "" Then
            strTemp = "Unsourced"
        Else
            strTemp = vLine(2)
        End If
        lbTo.List(lbTo.ListCount - 1, 3) = strTemp
        
    Next x
    
Exit_Sub:
    'ActiveWorkbook.Save
    ActiveWorkbook.Close
End Sub

Private Sub lbCables_KeyDown(ByVal KeyCode As MSForms.ReturnInteger, ByVal Shift As Integer)
    Dim excelApp As Excel.Application
    Dim ws As Excel.Worksheet
    Dim fName As String
    Dim entPole As AcadObject
    Dim objBlock As AcadBlockReference
    Dim vAttList, basePnt As Variant
    Dim vTemp, vLine As Variant
    Dim vNext, vNLine As Variant
    Dim strNext As String
    Dim strPath, strTemp As String
    Dim strPole, strType As String
    Dim lRow, lCable As Long
    Dim iI, iIndex As Integer
    
    'Me.Hide
  On Error Resume Next
    
    lRow = CLng(lbCables.List(lbCables.ListIndex, 4))
    
    strPath = ThisDrawing.FullName
    strPath = Replace(strPath, ".dwg", ".xlsx")
    
    fName = Dir(strPath)
    If fName = "" Then
        MsgBox "There are no Records in folder."
        Exit Sub
    End If
    
    Set excelApp = CreateObject("Excel.Application")
    excelApp.Visible = False
    
    Err = 0
    Set wb = Excel.Workbooks.Open(strPath)
    If Not Err = 0 Then
        MsgBox "Error opening file"
        GoTo Exit_Sub
    End If
    
    Select Case KeyCode
        Case vbKeyDelete
            lbCables.RemoveItem lbCables.ListIndex
            GoTo Exit_Sub
        Case vbKeyLeft
            lbFrom.Clear
            strListbox = "lbFrom"
            Frame2.Caption = "From Cable Row-" & lbCables.List(lbCables.ListIndex, 4)
        Case vbKeyRight
            lbTo.Clear
            strListbox = "lbTo"
            Frame1.Caption = "To Cable Row-" & lbCables.List(lbCables.ListIndex, 4)
    End Select
    
    vTemp = Split(Sheets("Cables").Cells(lRow, 10).Value, "-")
    iI = CInt(vTemp(1))
    
    For x = 1 To iI
        vTemp = Split(Sheets("Cables").Cells(lRow, 10 + iI).Value, "++")
        vLine = Split(vTemp(UBound(vTemp)), "~")
        
        'strTemp = Sheets("Cables").Cells(lRow, 2).Value
        
        Select Case strListbox
            Case "lbTo"
                lbTo.AddItem vTemp(0)   'vLine(0)
                lbTo.List(lbTo.ListCount - 1, 1) = vLine(0)
                lbTo.List(lbTo.ListCount - 1, 2) = vLine(1) 'Sheets("Cables").Cells(lRow, 1).Value
                If vLine(2) = "" Then
                    strTemp = "Unsourced"
                Else
                    strTemp = vLine(2)
                End If
                lbTo.List(lbTo.ListCount - 1, 3) = strTemp
                
            Case "lbFrom"
                lbFrom.AddItem vTemp(0)   'vLine(0)
                lbFrom.List(lbFrom.ListCount - 1, 1) = vLine(0)
                lbFrom.List(lbFrom.ListCount - 1, 2) = vLine(1) 'Sheets("Cables").Cells(lRow, 1).Value
                If vLine(2) = "" Then
                    strTemp = "Unsourced"
                Else
                    strTemp = vLine(2)
                End If
                lbFrom.List(lbFrom.ListCount - 1, 3) = strTemp
        End Select
    Next x
    
Exit_Sub:
    'ActiveWorkbook.Save
    ActiveWorkbook.Close
End Sub

Private Sub lbFrom_Click()
    If cbUpdate.Enabled = True Then
        tbC1.Enabled = False
        'tbC2.Enabled = False
        tbC3.Enabled = False
        'tbC4.Enabled = False
        cbUpdate.Enabled = False
        
        tbC0.Value = ""
        tbC1.Value = ""
        tbC2.Value = ""
        tbC3.Value = ""
        tbC4.Value = ""
        tbC5.Value = ""
    End If
End Sub

Private Sub lbFrom_DblClick(ByVal Cancel As MSForms.ReturnBoolean)
    If lbFrom.ListCount < 1 Then Exit Sub
    
    Dim vLine As Variant
    
    strListbox = "lbFrom"
    vLine = Split(lbFrom.List(lbFrom.ListIndex, 2), "-")
    
    If UBound(vLine) = 1 Then
        tbC0.Value = vLine(0)
        tbC1.Enabled = True
        'tbC2.Enabled = True
        tbC3.Enabled = True
        'tbC4.Enabled = True
        tbC5.Value = vLine(1)
    
        cbUpdate.Enabled = True
    End If
End Sub

Private Sub lbSub_DblClick(ByVal Cancel As MSForms.ReturnBoolean)
    If lbSub.ListCount < 1 Then Exit Sub
    
    Dim iIndex As Integer
    
    For i = 0 To lbSub.ListCount - 1
        If lbSub.Selected(i) Then
            Dim entPole As AcadEntity
            Dim objBlock As AcadBlockReference
            Dim basePnt, vAttList As Variant
            Dim strTemp As String
            Dim vLine As Variant
            
            Me.Hide
            On Error Resume Next
    
            ThisDrawing.Utility.GetEntity entPole, basePnt, "Select Building: "
            If TypeOf entPole Is AcadBlockReference Then
                Set objBlock = entPole
            Else
                MsgBox "Not a valid Customer."
                'Me.show
                GoTo Exit_Sub
            End If
                
            Select Case objBlock.Name
                Case "RES"
                Case "TRLR"
                Case "MDU"
                Case "CHURCH"
                Case "SCHOOL"
                Case "BUSINESS"
                Case Else
                    'Me.show
                    GoTo Exit_Sub
            End Select
            
            vAttList = objBlock.GetAttributes
            
            iIndex = lbSub.ListIndex
            
            If InStr(vAttList(2).TextString, "++") = 0 Then
                vLine = Split(cbClosure.Value, "~")
                vLine(UBound(vLine)) = lbSub.List(iIndex, 0)
                strTemp = vLine(0)
                For d = 1 To UBound(vLine)
                    strTemp = strTemp & "~" & vLine(d)
                Next d
                vAttList(2).TextString = strTemp & "++" & vAttList(2).TextString
                objBlock.Update
            End If
            vLine = Split(vAttList(2).TextString, "++")
            
            lbSub.List(iIndex, 3) = vLine(0)
            lbSub.List(iIndex, 4) = vAttList(0).TextString
            lbSub.List(iIndex, 5) = vAttList(1).TextString
            lbSub.List(iIndex, 6) = objBlock.Name
            lbSub.List(iIndex, 7) = vLine(1)
            lbSub.List(iIndex, 8) = objBlock.InsertionPoint(0)
            lbSub.List(iIndex, 9) = objBlock.InsertionPoint(1)
            
            MsgBox vAttList(2).TextString
            
            GoTo Exit_Sub
        End If
    Next i
Exit_Sub:
    Me.show
End Sub

Private Sub lbTo_Click()
    If cbUpdate.Enabled = True Then
        tbC1.Enabled = False
        'tbC2.Enabled = False
        tbC3.Enabled = False
        'tbC4.Enabled = False
        cbUpdate.Enabled = False
        
        tbC0.Value = ""
        tbC1.Value = ""
        tbC2.Value = ""
        tbC3.Value = ""
        tbC4.Value = ""
        tbC5.Value = ""
    End If
End Sub

Private Sub lbTo_DblClick(ByVal Cancel As MSForms.ReturnBoolean)
    If lbTo.ListCount < 1 Then Exit Sub
    
    Dim vLine As Variant
    
    strListbox = "lbTo"
    vLine = Split(lbTo.List(lbTo.ListIndex, 2), "-")
    
    If UBound(vLine) = 1 Then
        tbC0.Value = vLine(0)
        tbC1.Enabled = True
        'tbC2.Enabled = True
        tbC3.Enabled = True
        'tbC4.Enabled = True
        tbC5.Value = vLine(1)
    
        cbUpdate.Enabled = True
    End If
End Sub

Private Sub tbC1_Change()
    Dim iFiber As Integer
    
    If tbC1.Value = "" Then
        tbC4.Value = ""
        Exit Sub
    End If
    
    iFiber = CInt(tbC1.Value)
    
    If iFiber < CInt(tbC0.Value) Then
        'tbC1.Value = ""
        Exit Sub
    End If
    
    If tbC3.Value = "" Then
        If iFiber > CInt(tbC5.Value) - 1 Then
            tbC1.Value = ""
            tbC2.Value = ""
            Exit Sub
        End If
        tbC4.Value = iFiber + 1
    Else
        If iFiber > CInt(tbC3.Value) - 1 Then
            tbC1.Value = ""
            Exit Sub
        End If
        tbC2.Value = iFiber + 1
    End If
    
    If tbC2.Value = "" Then
        tbC4.Value = iFiber + 1
    End If
End Sub

Private Sub tbC3_Change()
    Dim iFiber As Integer
    
    If tbC3.Value = "" Then
        tbC4.Value = ""
        Exit Sub
    End If
    
    iFiber = CInt(tbC3.Value)
    
    If iFiber > CInt(tbC5.Value) - 1 Then
        tbC3.Value = ""
        Exit Sub
    End If
    tbC4.Value = iFiber + 1
    
    If tbC1.Value = "" Then
        If iFiber < CInt(tbC0.Value) + 1 Then
            'tbC3.Value = ""
            Exit Sub
        End If
        tbC2.Value = iFiber
        tbC1.Value = iFiber - 1
    Else
        If iFiber < CInt(tbC1.Value) + 1 Then
            tbC3.Value = ""
            Exit Sub
        End If
        tbC2.Value = CInt(tbC1.Value) + 1
    End If
End Sub

Private Sub UserForm_Initialize()
    cbType.AddItem ""
    cbType.AddItem "CO"
    cbType.AddItem "BFO"
    cbType.AddItem "UO"
    
    cbSize.AddItem ""
    cbSize.AddItem "12"
    cbSize.AddItem "24"
    cbSize.AddItem "36"
    cbSize.AddItem "48"
    cbSize.AddItem "72"
    cbSize.AddItem "96"
    cbSize.AddItem "144"
    cbSize.AddItem "216"
    cbSize.AddItem "288"
    cbSize.AddItem "360"
    cbSize.AddItem "432"
    
    cbSplitter.AddItem "1x32"
    cbSplitter.AddItem "1x16"
    cbSplitter.AddItem "1x8"
    cbSplitter.AddItem "1x4"
    cbSplitter.AddItem "1x2"
    
    lbFrom.ColumnCount = 4
    lbFrom.ColumnWidths = "48;48;48;72"
    
    lbTo.ColumnCount = 4
    lbTo.ColumnWidths = "48;48;48;72"
    
    lbCables.ColumnCount = 5
    lbCables.ColumnWidths = "48;48;72;48;36"
    
    lbSplices.ColumnCount = 5
    lbSplices.ColumnWidths = "42;48;42;48;48"
    
    lbSub.ColumnCount = 10
    lbSub.ColumnWidths = "36;48;36;54;48;96;36;96;57;57"
End Sub

Attribute VB_Name = "ConvertToLL"
Attribute VB_Base = "0{1EEF8C44-7227-40E6-B696-548926416535}{94641708-7945-43FD-942F-8CD92AD07214}"
Attribute VB_GlobalNameSpace = False
Attribute VB_Creatable = False
Attribute VB_PredeclaredId = True
Attribute VB_Exposed = False
Attribute VB_TemplateDerived = False
Attribute VB_Customizable = False
Private Sub cbCalcTN83F_Click()
    Dim dLat, dLong, dDLat As Double
    Dim vNE As Variant
    
    dLat = CDbl(tbLat.Value)
    dLong = CDbl(tbLong.Value)
    
    vNE = LLtoTN83F(CDbl(dLat), CDbl(dLong))
    
    Dim dDN, dDE, dDist As Double
    
    dDN = vNE(0) - CDbl(tbNorth.Value)
    dDE = vNE(1) - CDbl(tbEast.Value)
    dDist = Sqr(dDN * dDN + dDE * dDE)
    
    tbData.Value = vNE(0) & vbCr & vNE(1) & vbCr & vbCr
    tbData.Value = tbData.Value & dDN & vbCr & dDE & vbCr & dDist
End Sub

Private Sub cbCalc_Click()
    Dim dE, dN As Double
    Dim vLL As Variant
    
    dE = CDbl(tbEast.Value)
    dN = CDbl(tbNorth.Value)
    
    vLL = TN83FtoLL(CDbl(dN), CDbl(dE))
    
    tbLat.Value = vLL(0)
    tbLong.Value = vLL(1)
    
    tbScale.Value = vLL(2)
    
    tbData.Value = (tbALat.Value - tbLat.Value) & vbCr & (tbALong.Value - tbLong.Value)
    tbData.Value = tbData.Value & vbCr & vbCr & tbLat.Value & "," & tbLong.Value
    tbData.Value = tbData.Value & vbCr & vbCr & tbALat.Value & "," & tbALong.Value
    
End Sub

Private Sub cbQuit_Click()
    Me.Hide
End Sub

Private Sub Label9_Click()
    Dim objPole As AcadObject
    Dim objBlock As AcadBlockReference
    Dim vAttList, basePnt As Variant
    Dim vTemp As Variant
    Dim strNext As String
    
    Me.Hide
  On Error Resume Next
    
    ThisDrawing.Utility.GetEntity objPole, basePnt, "Select Block: "
    If TypeOf objPole Is AcadBlockReference Then
        Set objBlock = objPole
    Else
        MsgBox "Not a valid Block."
        GoTo Exit_Sub
    End If
    
    tbNorth.Value = objBlock.InsertionPoint(1)
    tbEast.Value = objBlock.InsertionPoint(0)
    
    vAttList = objBlock.GetAttributes
    vTemp = Split(vAttList(7).TextString, ",")
    
    'tbData.Value = vTemp(0) & vbCr & vTemp(1)
    tbALat.Value = vTemp(0)
    tbALong.Value = vTemp(1)
    
Exit_Sub:
    Me.show
End Sub

Private Function TN83FtoLL(dNorth As Double, dEast As Double)
    Dim dLat, dLong, dDLat As Double
    Dim dDiffE, dEast0 As Double
    Dim dDiffN, dNorth0 As Double
    Dim dR, dCAR, dCA, dU, dK As Double
    Dim LL(2) As Double
    
    dEast = dEast * 0.3048006096
    dNorth = dNorth * 0.3048006096
    
    dDiffE = dEast - 600000
    dDiffN = dNorth - 166504.1691
    
    dR = 8842127.1422 - dDiffN
    dCAR = Atn(dDiffE / dR)
    dCA = dCAR * 180 / 3.14159265359
    dLong = -86 + dCA / 0.585439726459
    
    dU = dDiffN - dDiffE * Tan(dCAR / 2)
    dDLat = dU * (0.00000901305249 + dU * (-6.77268E-15 + dU * (-3.72351E-20 + dU * -9.2828E-28)))
    dLat = 35.8340607459 + dDLat
    
    dK = 0.999948401424 + (1.23188E-14 * dU * dU) + (4.54E-22 * dU * dU * dU)
    
    LL(0) = dLat
    LL(1) = dLong
    LL(2) = dK
    
    TN83FtoLL = LL
End Function

Private Function LLtoTN83F(dLat As Double, dLong As Double)
    Dim dDLat As Double
    Dim dEast, dDiffE, dEast0 As Double
    Dim dNorth, dDiffN, dNorth0 As Double
    Dim dU, dR, dCA, dK As Double
    Dim NE(2) As Double
    
    dDLat = dLat - 35.8340607459
    dU = dDLat * (110950.2019 + dDLat * (9.25072 + dDLat * (5.64572 + dDLat * 0.017374)))
    dR = 8842127.1422 - dU
    dCA = ((86 + dLong) * 0.585439726459) * 3.14159265359 / 180
    
    dDiffE = dR * Sin(dCA)
    dDiffN = dU + dDiffE * Tan(dCA / 2)
    
    dEast = (dDiffE + 600000) / 0.3048006096
    dNorth = (dDiffN + 166504.1691) / 0.3048006096
    
    dK = 0.999948401424 + (1.23188E-14 * dU * dU) + (4.54E-22 * dU * dU * dU)
    
    NE(0) = dNorth
    NE(1) = dEast
    NE(2) = dK
    
    LLtoTN83F = NE
End Function

Private Sub UserForm_Click()

End Sub

Attribute VB_Name = "FlowerPotForm"
Attribute VB_Base = "0{49F0015B-7F77-4C2A-8969-263C0EDB705C}{F5EEA4F4-A5FF-479C-9F1D-E9DD909343B2}"
Attribute VB_GlobalNameSpace = False
Attribute VB_Creatable = False
Attribute VB_PredeclaredId = True
Attribute VB_Exposed = False
Attribute VB_TemplateDerived = False
Attribute VB_Customizable = False

Private Sub cbCombine_Click()
    Dim objSS As AcadSelectionSet
    Dim objObject As AcadObject
    Dim objEntity As AcadEntity
    Dim objBlock, objFP, objPole As AcadBlockReference
    Dim objDFP As AcadBlockReference
    Dim objPoint As AcadPoint
    Dim vFPList, vPoleList, vTemp As Variant
    Dim vBasePnt As Variant
    Dim strLat, strLong, strRoute As String
    Dim vNE, vLL As Variant
    Dim dMove(1) As Double
    Dim dFP(1) As Double
    
    Me.Hide
    On Error Resume Next
    
Do_Another:
    
    ThisDrawing.Utility.GetEntity objEntity, vBasePnt, "Select Originating Pole:"
    
    If Not Err = 0 Then
        Me.show
        Exit Sub
    End If
    
    If TypeOf objEntity Is AcadBlockReference Then
        Set objPole = objEntity
    Else
        MsgBox "Not a valid Block."
        Me.show
        Exit Sub
    End If
    
    vPoleList = objPole.GetAttributes
    
    strRoute = vPoleList(0).TextString
    
    vTemp = Split(vPoleList(7).TextString, ",")
    
    vNE = LLtoTN83F(CDbl(vTemp(0)), CDbl(vTemp(1)))
    
    dMove(0) = CDbl(vNE(1)) - objPole.InsertionPoint(0)
    dMove(1) = CDbl(vNE(0)) - objPole.InsertionPoint(1)
    
    'MsgBox dMove(0) & vbCr & dMove(1)
        
    Set objSS = ThisDrawing.SelectionSets.Add("objSS")
    If Not Err = 0 Then
        Set objSS = ThisDrawing.SelectionSets.Item("objSS")
        Err = 0
    End If
    
    objSS.SelectOnScreen
    
    If objSS.Count = 0 Then GoTo Exit_Sub
    
    
    For Each objObject In objSS
        If TypeOf objObject Is AcadBlockReference Then
            Set objDFP = objObject
            
            Select Case objDFP.Name
                Case "dFP"
                    'Set objFP = objBlock
                    vFPList = objDFP.GetAttributes
                    
                    dFP(0) = objDFP.InsertionPoint(0) + dMove(0)
                    dFP(1) = objDFP.InsertionPoint(1) + dMove(1)
                    
                    'MsgBox dFP(1) & vbCr & dFP(0)
                    
                    vLL = TN83FtoLL(CDbl(dFP(1)), CDbl(dFP(0)))
                    
                    'MsgBox vLL(0) & vbCr & vLL(1)
    
                    vFPList(2).TextString = vLL(0) & "," & vLL(1)
                    vFPList(0).TextString = strRoute & Right(vFPList(0).TextString, 1)
    
                    objDFP.Update
            End Select
        End If
        
    Next objObject
    
    objSS.Clear
    objSS.Delete
    
    GoTo Do_Another
    
Exit_Sub:
    objSS.Clear
    objSS.Delete
    Me.show
End Sub

Private Sub cbCreate_Click()
    Call CreateFPReport
End Sub

Private Sub cbQuit_Click()
    Me.Hide
End Sub

Private Sub UserForm_Initialize()
    cbExchange.AddItem "Airport"
    cbExchange.AddItem "Almaville"
    cbExchange.AddItem "Interchange"
    cbExchange.AddItem "Florence"
    cbExchange.AddItem "Lavergne"
    cbExchange.AddItem "Lewisburg"
    cbExchange.AddItem "Murfreesboro"
    'cbExchange.AddItem "Nolensville"
    cbExchange.AddItem "Smyrna"
    
    Dim vTemp As Variant
    Dim strTemp As String
    
    strTemp = Replace(ThisDrawing.Name, ".dwg", "")
    vTemp = Split(strTemp, " ")
    tbWO.Value = vTemp(0)
    
    Select Case UBound(vTemp)
        Case Is = 0
        Case Is = 1
            tbSA.Value = vTemp(1)
        Case Else
            strTemp = vTemp(1)
            For i = 2 To UBound(vTemp)
                strTemp = strTemp & " " & vTemp(i)
            Next i
            tbSA.Value = strTemp
    End Select
End Sub

Private Sub CreateFPReport()
    Dim objSS As AcadSelectionSet
    Dim filterType, filterValue As Variant
    Dim grpCode(0) As Integer
    Dim grpValue(0) As Variant
    Dim vPnt1, vPnt2 As Variant
    Dim objBlock As AcadBlockReference
    Dim vAttList As Variant
    Dim dPnt1(2), dPnt2(2) As Double
    
    Dim strFileName As String
    Dim strDWGName As String
    
    Dim vTemp As Variant
    Dim strWO, strSA, strExchange As String
    Dim strRoute, strNumber, strType As String
    Dim strSuffix, strPUnit As String
    Dim strLat, strLong, strTemp As String
    Dim iLen As Integer
    
    strWO = tbWO.Value
    strExchange = cbExchange.Value
    strSA = tbSA.Value
    
    strFileName = ThisDrawing.Path & "\" & strWO & " Records Import FP.csv"
    
    grpCode(0) = 2
    grpValue(0) = "dFP,sFP"
    filterType = grpCode
    filterValue = grpValue
    
  On Error Resume Next
    Me.Hide
    vPnt1 = ThisDrawing.Utility.GetPoint(, "Get BL Corner: ")
    vPnt2 = ThisDrawing.Utility.GetCorner(vPnt1, vbCr & "Get UR Corner: ")
    
    'dPnt1(0) = vPnt1(0)
    'dPnt1(1) = vPnt1(1)
    'dPnt1(2) = vPnt1(2)
    
    'dPnt2(0) = vPnt2(0)
    'dPnt2(1) = vPnt2(1)
    'dPnt2(2) = vPnt2(2)
  
    Err = 0
    
    Set objSS = ThisDrawing.SelectionSets.Add("objSS")
    If Not Err = 0 Then
        Set objSS = ThisDrawing.SelectionSets.Item("objSS")
        Err = 0
    End If
    objSS.Select acSelectionSetWindow, vPnt1, vPnt2, filterType, filterValue
    If Not Err = 0 Then
        MsgBox "Error: " & Err.Number & vbCr & Err.Description
        Me.show
        Exit Sub
    End If
    
    MsgBox "FlowerPots Found: " & objSS.Count
    If objSS.Count < 1 Then GoTo Exit_Sub
    
    Open strFileName For Output As #1
    
    Print #1, "Enclosure Type,Suffix,Latitude,Longitude,Exchange,Route,Service Area,Work Order,Pay Unit"

    
    For Each objBlock In objSS
        vAttList = objBlock.GetAttributes
        
        strRoute = vAttList(0).TextString
        strType = "Flower Pot"
        strSuffix = "(9x12)"
        
        Select Case objBlock.Name
            Case "dFP"
                'strRoute = vAttList(0).TextString   'vTemp(0)
                'strNumber = vTemp(1)
                
                vTemp = Split(vAttList(2).TextString, ",")
            Case "sFP"
                'iLen = Len(vAttList(0).TextString) - Len(vAttList(1).TextString)
                
                'strRoute = Left(vAttList(0).TextString, iLen)  'vTemp(0)
                
                vTemp = Split(vAttList(3).TextString, ",")
        End Select
        
        strLat = vTemp(0)
        strLong = vTemp(1)
        strPUnit = strType '& strSuffix
                
        strTemp = strType & "," & strSuffix & "," & strLat & "," & strLong & "," & strExchange & "," & strRoute
        strTemp = strTemp & "," & strSA & "," & strWO & "," & strPUnit
        Print #1, strTemp
        
Next_objBlock:
    Next objBlock
    
    MsgBox "Export Complete"
    Close #1
    
Exit_Sub:
    objSS.Clear
    objSS.Delete
    Me.show
End Sub

Private Function TN83FtoLL(dNorth As Double, dEast As Double)
    Dim dLat, dLong, dDLat As Double
    Dim dDiffE, dEast0 As Double
    Dim dDiffN, dNorth0 As Double
    Dim dR, dCAR, dCA, dU, dK As Double
    Dim LL(2) As Double
    
    dEast = dEast * 0.3048006096
    dNorth = dNorth * 0.3048006096
    
    dDiffE = dEast - 600000
    dDiffN = dNorth - 166504.1691
    
    dR = 8842127.1422 - dDiffN
    dCAR = Atn(dDiffE / dR)
    dCA = dCAR * 180 / 3.14159265359
    dLong = -86 + dCA / 0.585439726459
    
    dU = dDiffN - dDiffE * Tan(dCAR / 2)
    dDLat = dU * (0.00000901305249 + dU * (-6.77268E-15 + dU * (-3.72351E-20 + dU * -9.2828E-28)))
    dLat = 35.8340607459 + dDLat
    
    dK = 0.999948401424 + (1.23188E-14 * dU * dU) + (4.54E-22 * dU * dU * dU)
    
    LL(0) = dLat
    LL(1) = dLong
    LL(2) = dK
    
    TN83FtoLL = LL
End Function

Private Function LLtoTN83F(dLat As Double, dLong As Double)
    Dim dDLat As Double
    Dim dEast, dDiffE, dEast0 As Double
    Dim dNorth, dDiffN, dNorth0 As Double
    Dim dU, dR, dCA, dK As Double
    Dim NE(2) As Double
    
    dDLat = dLat - 35.8340607459
    dU = dDLat * (110950.2019 + dDLat * (9.25072 + dDLat * (5.64572 + dDLat * 0.017374)))
    dR = 8842127.1422 - dU
    dCA = ((86 + dLong) * 0.585439726459) * 3.14159265359 / 180
    
    dDiffE = dR * Sin(dCA)
    dDiffN = dU + dDiffE * Tan(dCA / 2)
    
    dEast = (dDiffE + 600000) / 0.3048006096
    dNorth = (dDiffN + 166504.1691) / 0.3048006096
    
    dK = 0.999948401424 + (1.23188E-14 * dU * dU) + (4.54E-22 * dU * dU * dU)
    
    NE(0) = dNorth
    NE(1) = dEast
    NE(2) = dK
    
    LLtoTN83F = NE
End Function

Attribute VB_Name = "MainMenu"
Attribute VB_Base = "0{C68C6598-E57F-4D43-949A-A90F8957C577}{9599FDEF-C87C-4253-810C-6E2AC55B3AE9}"
Attribute VB_GlobalNameSpace = False
Attribute VB_Creatable = False
Attribute VB_PredeclaredId = True
Attribute VB_Exposed = False
Attribute VB_TemplateDerived = False
Attribute VB_Customizable = False
Private Sub cbAddPole_Click()
    Me.Hide
    Load PoleForm
        PoleForm.show
    Unload PoleForm
    Me.show
End Sub

Private Sub cbAddPolesRecords_Click()
    Dim excelApp As Excel.Application
    Dim ws As Excel.Worksheet
    Dim objSS As AcadSelectionSet
    Dim objBlock As AcadBlockReference
    Dim fName As String
    Dim vAttList As Variant
    Dim vTemp As Variant
    'Dim str1, str2, strUnit As String
    Dim strPath, strTemp As String
    Dim filterType, filterValue As Variant
    Dim vPnt1, vPnt2 As Variant
    Dim grpCode(0) As Integer
    Dim grpValue(0) As Variant
    Dim dPnt1(0 To 2) As Double
    Dim dPnt2(0 To 2) As Double
    Dim lRow As Long

    grpCode(0) = 2
    grpValue(0) = "iPole"
    filterType = grpCode
    filterValue = grpValue
    
  On Error Resume Next
    Me.Hide
    vPnt1 = ThisDrawing.Utility.GetPoint(, "Get BL Corner: ")
    vPnt2 = ThisDrawing.Utility.GetCorner(vPnt1, vbCr & "Get UR Corner: ")
    
    dPnt1(0) = vPnt1(0)
    dPnt1(1) = vPnt1(1)
    dPnt1(2) = vPnt1(2)
    
    dPnt2(0) = vPnt2(0)
    dPnt2(1) = vPnt2(1)
    dPnt2(2) = vPnt2(2)
  
    Err = 0
    
    Set objSS = ThisDrawing.SelectionSets.Add("objSS")
    If Not Err = 0 Then
        Set objSS = ThisDrawing.SelectionSets.Item("objSS")
        Err = 0
    End If
    objSS.Select acSelectionSetWindow, dPnt1, dPnt2, filterType, filterValue
    
    strPath = ThisDrawing.FullName
    strPath = Replace(strPath, ".dwg", ".xlsx")
    
    fName = Dir(strPath)
    If fName = "" Then
        MsgBox "There are no Records in folder."
        GoTo Exit_Sub
    End If
    
    Set excelApp = CreateObject("Excel.Application")
    excelApp.Visible = False
    
    'Set ws = excelApp.ActiveWorkbook.Sheets("Poles")
    
    Err = 0
    Set wb = Excel.Workbooks.Open(strPath)
    If Not Err = 0 Then
        MsgBox "Error opening file"
        Exit Sub
    End If
    
    For Each objBlock In objSS
        vAttList = objBlock.GetAttributes
        
        If vAttList(0).TextString = "" Then GoTo Next_objBlock
        If vAttList(0).TextString = "POLE" Then GoTo Next_objBlock
        If Left(vAttList(0).TextString, 3) = "REF" Then GoTo Next_objBlock
        
        lRow = 2
        While Not Sheets("Poles").Cells(lRow, 1).Value = ""
            'MsgBox Sheets("Poles").Cells(lRow, 1).Value
            If Sheets("Poles").Cells(lRow, 1).Value = vAttList(0).TextString Then
                Sheets("Poles").Cells(lRow, 2).Value = vAttList(2).TextString
                Sheets("Poles").Cells(lRow, 3).Value = vAttList(5).TextString
                Sheets("Poles").Cells(lRow, 4).Value = vAttList(6).TextString
                Sheets("Poles").Cells(lRow, 5).Value = vAttList(8).TextString
                Sheets("Poles").Cells(lRow, 8).Value = objBlock.InsertionPoint(0)
                Sheets("Poles").Cells(lRow, 9).Value = objBlock.InsertionPoint(1)
                
                GoTo Next_objBlock
            End If
            lRow = lRow + 1
        Wend
        
        Sheets("Poles").Cells(lRow, 1).Value = vAttList(0).TextString
        Sheets("Poles").Cells(lRow, 2).Value = vAttList(2).TextString
        Sheets("Poles").Cells(lRow, 3).Value = vAttList(5).TextString
        Sheets("Poles").Cells(lRow, 4).Value = vAttList(6).TextString
        Sheets("Poles").Cells(lRow, 5).Value = vAttList(8).TextString
        Sheets("Poles").Cells(lRow, 8).Value = objBlock.InsertionPoint(0)
        Sheets("Poles").Cells(lRow, 9).Value = objBlock.InsertionPoint(1)
        
'Found_Empty:
        
Next_objBlock:
    Next objBlock
    
Close_Excel:
    ActiveWorkbook.Save
    ActiveWorkbook.Close
    
Exit_Sub:
    objSS.Clear
    objSS.Delete
    Me.show
End Sub

Private Sub cbAssignCounts_Click()
    Me.Hide
    Load CountsAssignForm
        CountsAssignForm.show
    Unload CountsAssignForm
    Me.show
End Sub

Private Sub cbPoleSheet_Click()
    Dim excelApp As Excel.Application
    Dim ws As Excel.Worksheet
    Dim objSS As AcadSelectionSet
    Dim objBlock As AcadBlockReference
    Dim fName As String
    Dim vAttList As Variant
    Dim vTemp As Variant
    'Dim str1, str2, strUnit As String
    Dim strPath, strTemp As String
    Dim filterType, filterValue As Variant
    Dim vPnt1, vPnt2 As Variant
    Dim grpCode(0) As Integer
    Dim grpValue(0) As Variant
    Dim dPnt1(0 To 2) As Double
    Dim dPnt2(0 To 2) As Double
    Dim lRow As Long

    grpCode(0) = 2
    grpValue(0) = "pole_unit"
    filterType = grpCode
    filterValue = grpValue
    
  On Error Resume Next
    Me.Hide
    vPnt1 = ThisDrawing.Utility.GetPoint(, "Get BL Corner: ")
    vPnt2 = ThisDrawing.Utility.GetCorner(vPnt1, vbCr & "Get UR Corner: ")
    
    dPnt1(0) = vPnt1(0)
    dPnt1(1) = vPnt1(1)
    dPnt1(2) = vPnt1(2)
    
    dPnt2(0) = vPnt2(0)
    dPnt2(1) = vPnt2(1)
    dPnt2(2) = vPnt2(2)
  
    Err = 0
    
    Set objSS = ThisDrawing.SelectionSets.Add("objSS")
    If Not Err = 0 Then
        Set objSS = ThisDrawing.SelectionSets.Item("objSS")
        Err = 0
    End If
    objSS.Select acSelectionSetWindow, dPnt1, dPnt2, filterType, filterValue
    
    strPath = ThisDrawing.FullName
    strPath = Replace(strPath, ".dwg", ".xlsx")
    
    fName = Dir(strPath)
    If fName = "" Then
        MsgBox "There are no Records in folder."
        GoTo Exit_Sub
    End If
    
    Set excelApp = CreateObject("Excel.Application")
    excelApp.Visible = False
    
    'Set ws = excelApp.ActiveWorkbook.Sheets("Poles")
    
    Err = 0
    Set wb = Excel.Workbooks.Open(strPath)
    If Not Err = 0 Then
        MsgBox "Error opening file"
        Exit Sub
    End If
    
    For Each objBlock In objSS
        vAttList = objBlock.GetAttributes
        
        If vAttList(0).TextString = "" Then GoTo Next_objBlock
        If vAttList(0).TextString = "POLE" Then GoTo Next_objBlock
        If Left(vAttList(0).TextString, 3) = "REF" Then GoTo Next_objBlock
        
        lRow = 2
        While Not Sheets("Poles").Cells(lRow, 1).Value = ""
            'MsgBox Sheets("Poles").Cells(lRow, 1).Value
            If Sheets("Poles").Cells(lRow, 1).Value = vAttList(0).TextString Then
                vTemp = Split(vAttList(3).TextString, "=")
                strTemp = Replace(vTemp(0), "+", "")
                
                If UBound(vTemp) > 0 Then
                    If Not vTemp(1) = "1" Then
                        strTemp = strTemp & "=" & vTemp(1)
                    End If
                End If
                
                If Sheets("Poles").Cells(lRow, 7).Value = "" Then
                    Sheets("Poles").Cells(lRow, 7).Value = strTemp
                Else
                    Sheets("Poles").Cells(lRow, 7).Value = Sheets("Poles").Cells(lRow, 7).Value & "**" & strTemp
                End If
                
                GoTo Next_objBlock
            End If
            lRow = lRow + 1
        Wend
        
'Found_Empty:
        
Next_objBlock:
    Next objBlock
    
Close_Excel:
    ActiveWorkbook.Save
    ActiveWorkbook.Close
    
Exit_Sub:
    objSS.Clear
    objSS.Delete
    Me.show
End Sub

Private Sub cbQuit_Click()
    Me.Hide
End Sub

Private Sub cbUpdatePoleInfo_Click()
    Dim excelApp As Excel.Application
    Dim ws As Excel.Worksheet
    Dim objSS As AcadSelectionSet
    Dim objBlock As AcadBlockReference
    Dim fName As String
    Dim vAttList As Variant
    Dim vTemp As Variant
    'Dim str1, str2, strUnit As String
    Dim strPath, strTemp As String
    Dim filterType, filterValue As Variant
    Dim vPnt1, vPnt2 As Variant
    Dim grpCode(0) As Integer
    Dim grpValue(0) As Variant
    Dim dPnt1(0 To 2) As Double
    Dim dPnt2(0 To 2) As Double
    Dim lRow As Long
    Dim strHC, strGrd As String

    grpCode(0) = 2
    grpValue(0) = "pole_info"
    filterType = grpCode
    filterValue = grpValue
    
  On Error Resume Next
    Me.Hide
    vPnt1 = ThisDrawing.Utility.GetPoint(, "Get BL Corner: ")
    vPnt2 = ThisDrawing.Utility.GetCorner(vPnt1, vbCr & "Get UR Corner: ")
    
    dPnt1(0) = vPnt1(0)
    dPnt1(1) = vPnt1(1)
    dPnt1(2) = vPnt1(2)
    
    dPnt2(0) = vPnt2(0)
    dPnt2(1) = vPnt2(1)
    dPnt2(2) = vPnt2(2)
  
    Err = 0
    
    Set objSS = ThisDrawing.SelectionSets.Add("objSS")
    If Not Err = 0 Then
        Set objSS = ThisDrawing.SelectionSets.Item("objSS")
        Err = 0
    End If
    objSS.Select acSelectionSetWindow, dPnt1, dPnt2, filterType, filterValue
    
    strPath = ThisDrawing.FullName
    strPath = Replace(strPath, ".dwg", ".xlsx")
    
    fName = Dir(strPath)
    If fName = "" Then
        MsgBox "There are no Records in folder."
        GoTo Exit_Sub
    End If
    
    Set excelApp = CreateObject("Excel.Application")
    excelApp.Visible = False
    
    'Set ws = excelApp.ActiveWorkbook.Sheets("Poles")
    
    Err = 0
    Set wb = Excel.Workbooks.Open(strPath)
    If Not Err = 0 Then
        MsgBox "Error opening file"
        Exit Sub
    End If
    
    For Each objBlock In objSS
        vAttList = objBlock.GetAttributes
        
        Select Case vAttList(1).TextString
            Case "0.1"
                strHC = vAttList(3).TextString
            Case "0.9"
                strGrd = vAttList(2).TextString
            Case Else
                GoTo Next_objBlock
        End Select
        
        lRow = 2
        While Not Sheets("Poles").Cells(lRow, 1).Value = ""
            If Sheets("Poles").Cells(lRow, 1).Value = vAttList(0).TextString Then
                If Not strHC = "" Then
                    Sheets("Poles").Cells(lRow, 3).Value = strHC
                End If
                
                If Not strGrd = "" Then
                    Sheets("Poles").Cells(lRow, 5).Value = strGrd
                End If
                
                GoTo Next_objBlock
            End If
            lRow = lRow + 1
        Wend
        
'Found_Empty:
        
Next_objBlock:
    Next objBlock
    
Close_Excel:
    ActiveWorkbook.Save
    ActiveWorkbook.Close
    
Exit_Sub:
    objSS.Clear
    objSS.Delete
    Me.show
End Sub

Private Sub UserForm_Click()

End Sub

Attribute VB_Name = "Module1"
Public Sub OpenMainMenu()
    Load MainMenu
    MainMenu.show
    Unload MainMenu
End Sub

Public Sub appRecordsExport()
    Load RecordsExport
        RecordsExport.show
    Unload RecordsExport
End Sub

Public Sub appRecordsFPExport()
    Load FlowerPotForm
        FlowerPotForm.show
    Unload FlowerPotForm
End Sub

Public Sub CreatePointsFromKml()
    'Dim objSS As AcadSelectionSet
    'Dim filterType, filterValue As Variant
    'Dim grpCode(0) As Integer
    'Dim grpValue(0) As Variant
    
    Dim objBlock As AcadBlockReference
    Dim vAtt As Variant
    
    Dim strPath, strFile As String
    Dim strLine, strTemp As String
    Dim strText As String
    Dim vFile, vLine As Variant
    
    Dim dCoords(2) As Double
    
  On Error Resume Next
    
    strPath = ThisDrawing.Path & "\"
    strFile = strPath & "Temp.csv"
    
    Open strFile For Input As #1
    If Not Err = 0 Then
        MsgBox "Error opening file."
        Exit Sub
    End If
    
    vFile = Split(Input$(LOF(1), 1), vbLf)
    Close #1
    
    strText = "<?xml version=""1.0"" encoding=""UTF-8""?><kml>"
    strText = strText & "<Document><name>MTEMC - GF</name>" & vbCr
    
    For i = 1 To UBound(vFile)
        strTemp = Replace(vFile(i), vbCr, "")
        vLine = Split(strTemp, ",")
        
        If vLine(UBound(vLine)) = "" Then GoTo Next_I
        If vLine(UBound(vLine) - 1) = "" Then GoTo Next_I
        
        dCoords(1) = CDbl(vLine(UBound(vLine) - 1))
        dCoords(0) = CDbl(vLine(UBound(vLine)))
        dCoords(2) = 0#
        
        'strText = strText & "<Placemark id=""" & UCase(vLine(0)) & """>"
        strText = strText & "<Placemark><name>" & UCase(vLine(0)) & "</name>"
        strText = strText & "<description>Address: " & UCase(vLine(1)) & "</description>" & vbCr
        strText = strText & "<Point><coordinates>" & dCoords(0) & "," & dCoords(1) & ",0.0</coordinates>"
        strText = strText & "</Point></Placemark>" & vbCr
        
        'Set objBlock = ThisDrawing.ModelSpace.InsertBlock(dCoords, "KMLpnt", 1#, 1#, 1#, 0#)
        'vAtt = objBlock.GetAttributes
        'vAtt(0).TextString = vLine(0)
        'vAtt(1).TextString = vLine(1)
        'vAtt(2).TextString = dCoords(1) & "," & dCoords(0)
        
        'objBlock.Update
        
Next_I:
    Next i
    
    strText = strText & "</Document></kml>"
    strText = Replace(strText, "&", "+")

    strFile = strPath & "MTEMC-GF.kml"
    
    Err = 0
    
    Open strFile For Output As #2
    If Not Err = 0 Then
        MsgBox "What?"
        Exit Sub
    End If
    
    Print #2, strText
    
    Close #2
    
    MsgBox "Complete"
End Sub

Private Sub AddKmlDataToPoles()
    Dim objSS As AcadSelectionSet
    Dim filterType, filterValue As Variant
    Dim grpCode(0) As Integer
    Dim grpValue(0) As Variant
    
    Dim objBlock As AcadBlockReference
    Dim vAtt As Variant
    
    Dim strPath, strFile As String
    Dim strLine As String
    Dim vFile, vLine As Variant
    
  On Error Resume Next
    
    strPath = ThisDrawing.Path & "\"
    strFile = strPath & "Pole Data.txt"
    
    Open strFile For Input As #1
    If Not Err = 0 Then
        MsgBox "Error opening file."
        Exit Sub
    End If
    
    vFile = Split(Input$(LOF(1), 1), vbLf)
    Close #1

    grpCode(0) = 2
    grpValue(0) = "iPole"
    filterType = grpCode
    filterValue = grpValue
    
    Set objSS = ThisDrawing.SelectionSets.Add("objSS")
    If Not Err = 0 Then
        Set objSS = ThisDrawing.SelectionSets.Item("objSS")
        Err = 0
    End If
    
    objSS.Select acSelectionSetAll, , , filterType, filterValue
    If Not Err = 0 Then
        MsgBox "Error: " & Err.Number & vbCr & Err.Description
        Exit Sub
    End If
    
    For Each objBlock In objSS
        vAtt = objBlock.GetAttributes
        If vAtt(0).TextString = "" Then GoTo Next_Pole
        
        For i = 0 To UBound(vFile)
            vLine = Split(vFile(i), vbTab)
            If vLine(0) = vAtt(0).TextString Then
                vAtt(5).TextString = vLine(2)
                vAtt(7).TextString = vLine(3)
                
                Select Case vLine(1)
                    Case "POLE_TEL"
                        objBlock.Layer = "Integrity Poles-UTC"
                    Case "POLE_OTHR_TEL"
                        objBlock.Layer = "Integrity Poles-Other"
                    Case "POLE_PWR_TEL"
                        objBlock.Layer = "Integrity Poles-Power"
                End Select
                
                objBlock.Update
                GoTo Next_Pole
            End If
        Next i
Next_Pole:
    Next objBlock
End Sub

Private Sub AddKmlDataToInfo()
    Dim objSS As AcadSelectionSet
    Dim filterType, filterValue As Variant
    Dim grpCode(0) As Integer
    Dim grpValue(0) As Variant
    
    Dim objBlock As AcadBlockReference
    Dim vAtt As Variant
    
    Dim strPath, strFile As String
    Dim strLine As String
    Dim vFile, vLine As Variant
    
  On Error Resume Next
    
    strPath = ThisDrawing.Path & "\"
    strFile = strPath & "Temp.csv"
    
    Open strFile For Input As #1
    If Not Err = 0 Then
        MsgBox "Error opening file."
        Exit Sub
    End If
    
    vFile = Split(Input$(LOF(1), 1), vbLf)
    Close #1

    grpCode(0) = 2
    grpValue(0) = "pole_info"
    filterType = grpCode
    filterValue = grpValue
    
    Set objSS = ThisDrawing.SelectionSets.Add("objSS")
    If Not Err = 0 Then
        Set objSS = ThisDrawing.SelectionSets.Item("objSS")
        Err = 0
    End If
    
    objSS.Select acSelectionSetAll, , , filterType, filterValue
    If Not Err = 0 Then
        MsgBox "Error: " & Err.Number & vbCr & Err.Description
        Exit Sub
    End If
    
    For Each objBlock In objSS
        vAtt = objBlock.GetAttributes
        If vAtt(0).TextString = "" Then GoTo Next_Pole
        Select Case vAtt(1).TextString
            Case "0.1", "0.2"
            Case Else
                GoTo Next_Pole
        End Select
        
        For i = 0 To UBound(vFile)
            vLine = Split(vFile(i), vbTab)
            If vLine(0) = vAtt(0).TextString Then
                Select Case vLine(1)
                    Case "POLE_TEL"
                        strLine = "UTC"
                    Case "POLE_PWR_TEL"
                        strLine = "DRE"
                    Case Else
                        strLine = "OTHER"
                End Select
                
                Select Case vAtt(1).TextString
                    Case "0.1"
                        vAtt(2).TextString = strLine
                        vAtt(3).TextString = vLine(2)
                    Case "0.2"
                        vAtt(2).TextString = strLine
                End Select
                
                objBlock.Update
                GoTo Next_Pole
            End If
        Next i
Next_Pole:
    Next objBlock
End Sub

Public Sub AddLLtoPoles()
    Dim objSS As AcadSelectionSet
    Dim filterType, filterValue As Variant
    Dim grpCode(0) As Integer
    Dim grpValue(0) As Variant
    Dim vPnt1, vPnt2 As Variant
    Dim objBlock As AcadBlockReference
    Dim vAttList As Variant
    Dim i As Integer
    
    Dim dN, dE As Double
    Dim vLL As Variant
    
    i = 0

    grpCode(0) = 2
    grpValue(0) = "iPole"
    filterType = grpCode
    filterValue = grpValue
    
  On Error Resume Next
    
    vPnt1 = ThisDrawing.Utility.GetPoint(, "Get BL Corner: ")
    vPnt2 = ThisDrawing.Utility.GetCorner(vPnt1, vbCr & "Get UR Corner: ")
  
    Err = 0
    
    Set objSS = ThisDrawing.SelectionSets.Add("objSS")
    If Not Err = 0 Then
        Set objSS = ThisDrawing.SelectionSets.Item("objSS")
        Err = 0
    End If
    
    objSS.Select acSelectionSetWindow, vPnt1, vPnt2, filterType, filterValue
    If Not Err = 0 Then
        MsgBox "Error: " & Err.Number & vbCr & Err.Description
        Exit Sub
    End If
    
    For Each objBlock In objSS
        vAttList = objBlock.GetAttributes
        'If vAttList(0).TextString = "POLE" Then GoTo Next_objBlock
        'If vAttList(0).TextString = "" Then GoTo Next_objBlock
        
        dE = objBlock.InsertionPoint(0)
        dN = objBlock.InsertionPoint(1)
        vLL = TN83FtoLL(CDbl(dN), CDbl(dE))
        
        vAttList(7).TextString = vLL(0) & "," & vLL(1)
        objBlock.Update
        i = i + 1
Next_objBlock:
    Next objBlock
    
    MsgBox "Lat/Long added to " & i & " poles."
End Sub

Public Sub AddDREdata()
    Dim objEntity As AcadEntity
    Dim objPoint As AcadPoint
    Dim objBlock As AcadBlockReference
    Dim vReturnPnt, vAttList As Variant
    
    Dim amap As AcadMap
    Dim ODRcs As ODRecords
    Dim ODRc As ODRecord
    Dim tbl As ODTable
    Dim tbls As ODTables
    Dim boolVal As Boolean
    
    Dim strOwner, strNumber, strHC As String
    'Dim strLL As String
    'Dim vLL As Variant
    
    On Error Resume Next
    
    Set amap = ThisDrawing.Application.GetInterfaceObject("AutoCADMap.Application")
    
    Set tbls = amap.Projects(ThisDrawing).ODTables
    If tbls.Count > 0 Then
        For Each tbl In tbls
            If tbl.Name = "allPoles" Then GoTo Exit_For
        Next
    End If
    
    MsgBox "Table not found"
    Exit Sub
    
Exit_For:

    Set ODRcs = tbl.GetODRecords
    
Get_Another:
    
    ThisDrawing.Utility.GetEntity objEntity, vReturnPnt, vbCr & "Select Point with Data:"
    If Not Err = 0 Then
        MsgBox "Error getting point"
        Exit Sub
    End If
            
    boolVal = ODRcs.Init(objEntity, True, False)
    Set ODRc = ODRcs.Record
    
    strOwner = ODRc.Item(6).Value
    If strOwner = "Duck River" Then strOwner = "DRE"
    
    strNumber = ODRc.Item(7).Value
    strHC = ODRc.Item(5).Value & "-" & ODRc.Item(3).Value
    
    'vLL = TN83FtoLL(dN, dE)
    
    ThisDrawing.Utility.GetEntity objEntity, vReturnPnt, vbCr & "Select Pole to add Data:"
    If Not Err = 0 Then
        MsgBox "Error getting pole"
        Exit Sub
    End If
    
    If Not TypeOf objEntity Is AcadBlockReference Then
        MsgBox "Entity is not a block"
        Exit Sub
    End If
    
    Set objBlock = objEntity
    Select Case objBlock.Name
        Case "iPole", "sPole"
        Case Else
            MsgBox "Not a valid pole"
            Exit Sub
    End Select
    
    vAttList = objBlock.GetAttributes
    vAttList(2).TextString = strOwner
    If strOwner = "DRE" Then
        vAttList(3).TextString = strNumber
    Else
        vAttList(4).TextString = "DRE=" & strNumber
    End If
    
    If Not strHC = "-" Then vAttList(5).TextString = strHC
    objBlock.Update
    
    Err = 0
    GoTo Get_Another
    
End Sub

Private Function TN83FtoLL(dNorth As Double, dEast As Double)
    Dim dLat, dLong, dDLat As Double
    Dim dDiffE, dEast0 As Double
    Dim dDiffN, dNorth0 As Double
    Dim dR, dCAR, dCA, dU, dK As Double
    Dim LL(2) As Double
    
    dEast = dEast * 0.3048006096
    dNorth = dNorth * 0.3048006096
    
    dDiffE = dEast - 600000
    dDiffN = dNorth - 166504.1691
    
    dR = 8842127.1422 - dDiffN
    dCAR = Atn(dDiffE / dR)
    dCA = dCAR * 180 / 3.14159265359
    dLong = -86 + dCA / 0.585439726459
    
    dU = dDiffN - dDiffE * Tan(dCAR / 2)
    dDLat = dU * (0.00000901305249 + dU * (-6.77268E-15 + dU * (-3.72351E-20 + dU * -9.2828E-28)))
    dLat = 35.8340607459 + dDLat
    
    dK = 0.999948401424 + (1.23188E-14 * dU * dU) + (4.54E-22 * dU * dU * dU)
    
    LL(0) = dLat
    LL(1) = dLong
    LL(2) = dK
    
    TN83FtoLL = LL
End Function

Private Function LLtoTN83F(dLat As Double, dLong As Double)
    Dim dDLat As Double
    Dim dEast, dDiffE, dEast0 As Double
    Dim dNorth, dDiffN, dNorth0 As Double
    Dim dU, dR, dCA, dK As Double
    Dim NE(2) As Double
    
    dDLat = dLat - 35.8340607459
    dU = dDLat * (110950.2019 + dDLat * (9.25072 + dDLat * (5.64572 + dDLat * 0.017374)))
    dR = 8842127.1422 - dU
    dCA = ((86 + dLong) * 0.585439726459) * 3.14159265359 / 180
    
    dDiffE = dR * Sin(dCA)
    dDiffN = dU + dDiffE * Tan(dCA / 2)
    
    dEast = (dDiffE + 600000) / 0.3048006096
    dNorth = (dDiffN + 166504.1691) / 0.3048006096
    
    dK = 0.999948401424 + (1.23188E-14 * dU * dU) + (4.54E-22 * dU * dU * dU)
    
    NE(0) = dNorth
    NE(1) = dEast
    NE(2) = dK
    
    LLtoTN83F = NE
End Function

Attribute VB_Name = "Module2"
Public Sub AddCenterlines()
    Dim lwpMain As AcadLWPolyline
    Dim vPnt1, vPnt2 As Variant
    Dim dPnt(1) As Double
    
    On Error Resume Next
    
    vPnt1 = ThisDrawing.Utility.GetPoint(, "Get Point 1: ")
    vPnt2 = ThisDrawing.Utility.GetCorner(vPnt1, vbCr & "Get Point 2: ")
    If Not Err = 0 Then Exit Sub
    
    dPnt(0) = (vPnt2(0) + vPnt1(0)) / 2
    dPnt(1) = (vPnt2(1) + vPnt1(1)) / 2
    
End Sub

Attribute VB_Name = "NewClosureForm"
Attribute VB_Base = "0{245BDADE-80E8-4E34-ACC0-A8F01BF6FFBD}{7A3F3D11-2696-4F76-B850-181312FC602B}"
Attribute VB_GlobalNameSpace = False
Attribute VB_Creatable = False
Attribute VB_PredeclaredId = True
Attribute VB_Exposed = False
Attribute VB_TemplateDerived = False
Attribute VB_Customizable = False


Private Sub cbAddToTerm_Click()
    For i = 0 To lbSplice.ListCount - 1
        If lbSplice.Selected(i) Then
            Dim iFrom, iTo As Integer
            Dim iPort As Integer
            Dim vTemp As Variant
            
            lbSplice.List(i, 3) = "TERM"
            vTemp = Split(lbSplice.List(i, 2), "-")
            iFrom = CInt(vTemp(0))
            If UBound(vTemp) < 1 Then
                iTo = iFrom
            Else
                iTo = CInt(vTemp(1))
            End If
            iPort = lbTerminal.ListCount + 1
            
            For j = iFrom To iTo
                lbTerminal.AddItem iPort, iPort - 1
                lbTerminal.List(iPort - 1, 1) = lbSplice.List(i, 1)
                lbTerminal.List(iPort - 1, 2) = j
                lbTerminal.List(iPort - 1, 3) = "TERM"
                lbTerminal.List(iPort - 1, 4) = lbSplice.List(i, 4)
                iPort = iPort + 1
            Next j
        End If
    Next i
End Sub

Private Sub cbQuit_Click()
    Me.Hide
End Sub

Private Sub cbUpdate_Click()
    Dim excelApp As Excel.Application
    Dim ws As Excel.Worksheet
    Dim fName As String
    Dim strPath, strTemp As String
    Dim entPole As AcadObject
    Dim objBlock As AcadBlockReference
    Dim vAttList, basePnt As Variant
    Dim lRow As Long
    Dim iI As Integer
    Dim strPole, strType As String
    'Dim strTemp As String
    
    Me.Hide
  On Error Resume Next
    
    strPole = tbPole.Value
    
    strPath = ThisDrawing.FullName
    strPath = Replace(strPath, ".dwg", ".xlsx")
    
    fName = Dir(strPath)
    If fName = "" Then
        MsgBox "There are no Records in folder."
        Exit Sub
    End If
    
    Set excelApp = CreateObject("Excel.Application")
    excelApp.Visible = False
    
    Err = 0
    Set wb = Excel.Workbooks.Open(strPath)
    If Not Err = 0 Then
        MsgBox "Error opening file"
        GoTo Exit_Sub
    End If
    
    lRow = 2
    While Not Sheets("Closures").Cells(lRow, 1).Value = ""
        lRow = lRow + 1
    Wend
    
    Sheets("Closures").Cells(lRow, 1).Value = strPole
    Sheets("Closures").Cells(lRow, 2).Value = cbType.Value
    Sheets("Closures").Cells(lRow, 3).Value = cbSize.Value
    Sheets("Closures").Cells(lRow, 4).Value = tbMaterial.Value
    Sheets("Closures").Cells(lRow, 5).Value = tbPosition.Value
    Sheets("Closures").Cells(lRow, 6).Value = tbJob.Value
    
    strTemp = ""
    For iI = 0 To lbSplice.ListCount - 1
        strTemp = lbSplice.List(iI, 0) & "~" & lbSplice.List(iI, 1) & "~"
        strTemp = strTemp & lbSplice.List(iI, 2) & "~" & lbSplice.List(iI, 3) & "~"
        strTemp = strTemp & lbSplice.List(iI, 4)
        
        If Not iI = lbSplice.ListCount - 1 Then strTemp = strTemp & "-&-"
    Next iI
    Sheets("Closures").Cells(lRow, 7).Value = strTemp
    
    strTemp = ""
    For iI = 0 To lbTerminal.ListCount - 1
        strTemp = strTemp & lbTerminal.List(iI, 1) & "~" & lbTerminal.List(iI, 2) & "~"
        strTemp = strTemp & lbTerminal.List(iI, 3)
        
        If Not iI = lbTerminal.ListCount - 1 Then strTemp = strTemp & "-&-"
    Next iI
    Sheets("Closures").Cells(lRow, 8).Value = strTemp
    Sheets("Closures").Cells(lRow, 9).Value = ""
    Sheets("Closures").Cells(lRow, 10).Value = ""
    
    lRow = 2
    While Not Sheets("Customers").Cells(lRow, 1).Value = ""
        lRow = lRow + 1
    Wend
    
    For iI = 0 To lbSub.ListCount - 1
        Sheets("Customers").Cells(lRow, 1).Value = lbSub.List(iI, 0)
        Sheets("Customers").Cells(lRow, 2).Value = lbSub.List(iI, 1)
        'Sheets("Customers").Cells(lRow, 3).Value = lbSub.List(iI, 0)
        Sheets("Customers").Cells(lRow, 4).Value = lbSub.List(iI, 2)
        Sheets("Customers").Cells(lRow, 5).Value = lbSub.List(iI, 3)
        Sheets("Customers").Cells(lRow, 6).Value = tbPole.Value
        Sheets("Customers").Cells(lRow, 7).Value = lbSub.List(iI, 4)
        'Sheets("Customers").Cells(lRow, 8).Value = lbSub.List(iI, 0)
        'Sheets("Customers").Cells(lRow, 9).Value = lbSub.List(iI, 0)
        Sheets("Customers").Cells(lRow, 10).Value = lbSub.List(iI, 5)
        Sheets("Customers").Cells(lRow, 11).Value = lbSub.List(iI, 6)
        
        lRow = lRow + 1
    Next iI
    
    lRow = 2
    While Not Sheets("Cables").Cells(lRow, 1).Value = ""
        lRow = lRow + 1
    Wend
    
    Sheets("Cables").Cells(lRow, 1).Value = CountsAssignForm.tbPole.Value
    If CountsAssignForm.cbType.Value = "CO" Then
        Sheets("Cables").Cells(lRow, 2).Value = "Aerial"
    Else
        Sheets("Cables").Cells(lRow, 2).Value = "Buried"
    End If
    Sheets("Cables").Cells(lRow, 3).Value = tbPole.Value
    Sheets("Cables").Cells(lRow, 4).Value = CountsAssignForm.tbCoil.Value
    Sheets("Cables").Cells(lRow, 5).Value = CountsAssignForm.tbJob.Value
    Sheets("Cables").Cells(lRow, 7).Value = CountsAssignForm.cbType.Value
    Sheets("Cables").Cells(lRow, 8).Value = CountsAssignForm.cbSize.Value
    Sheets("Cables").Cells(lRow, 9).Value = "Coil B"
    
    lRow = lRow + 1
    
    Sheets("Cables").Cells(lRow, 1).Value = tbPole.Value
    If CountsAssignForm.cbType.Value = "CO" Then
        Sheets("Cables").Cells(lRow, 2).Value = "Aerial"
    Else
        Sheets("Cables").Cells(lRow, 2).Value = "Buried"
    End If
    Sheets("Cables").Cells(lRow, 3).Value = CountsAssignForm.tbNextPole.Value
    Sheets("Cables").Cells(lRow, 4).Value = CountsAssignForm.tbCoil.Value
    Sheets("Cables").Cells(lRow, 5).Value = CountsAssignForm.tbJob.Value
    Sheets("Cables").Cells(lRow, 7).Value = CountsAssignForm.cbType.Value
    Sheets("Cables").Cells(lRow, 8).Value = CountsAssignForm.cbSize.Value
    Sheets("Cables").Cells(lRow, 9).Value = "Coil A"
    
Exit_Sub:
    ActiveWorkbook.Save
    ActiveWorkbook.Close
End Sub

Private Sub Label10_Click()
    Dim entPole As AcadObject
    Dim objBlock As AcadBlockReference
    Dim vAttList, basePnt As Variant
    Dim strNext As String
    
    Me.Hide
  On Error Resume Next
    
    ThisDrawing.Utility.GetEntity entPole, basePnt, "Select Structure: "
    If TypeOf entPole Is AcadBlockReference Then
        Set objBlock = entPole
    Else
        MsgBox "Not a valid pole."
        GoTo Exit_Sub
    End If
    
    vAttList = objBlock.GetAttributes
    
    strNext = vAttList(0).TextString
    If Not Err = 0 Then GoTo Exit_Sub
    
    tbPole.Value = strNext
    
Exit_Sub:
    Me.show
End Sub

Private Sub Label4_Click()
    Dim entPole As AcadObject
    Dim vAttList, basePnt As Variant
    Dim objBlock As AcadBlockReference
    Dim strPnt As String
    Dim iCount As Integer
    
    Me.Hide
  On Error Resume Next
    
    ThisDrawing.Utility.GetEntity entPole, basePnt, "Select Next Point: "
    If TypeOf entPole Is AcadBlockReference Then
        Set objBlock = entPole
    Else
        MsgBox "Not a valid pole."
        Exit Sub
    End If
    
    Err = 0
    vAttList = objBlock.GetAttributes
    If Not Err = 0 Then
        Me.show
        Exit Sub
    End If
    
    If UBound(vAttList) < 0 Then
        Me.show
        Exit Sub
    End If
    
    iCount = 0
    strPnt = vAttList(0).TextString
    
    For i = 0 To lbSplice.ListCount - 1
        If lbSplice.Selected(i) Then
            lbSplice.List(i, 3) = strPnt
            iCount = iCount + 1
        End If
    Next i
    
    If iCount = 0 Then
        For i = 0 To lbSplice.ListCount - 1
            lbSplice.List(i, 3) = strPnt
        Next i
    End If
        
    Me.show
End Sub

Private Sub lbSplice_Click()

End Sub

Private Sub lbTerminal_DblClick(ByVal Cancel As MSForms.ReturnBoolean)
    If lbTerminal.ListCount < 1 Then Exit Sub
    
    Dim iIndex As Integer
    
    For i = 0 To lbTerminal.ListCount - 1
        If lbTerminal.Selected(i) Then
            Dim entPole As AcadEntity
            Dim objBlock As AcadBlockReference
            Dim basePnt, vAttList As Variant
            
            Me.Hide
            On Error Resume Next
    
            ThisDrawing.Utility.GetEntity entPole, basePnt, "Select Pole: "
            If TypeOf entPole Is AcadBlockReference Then
                Set objBlock = entPole
            Else
                MsgBox "Not a valid Customer."
                Me.show
                Exit Sub
            End If
                
            Select Case objBlock.Name
                Case "RES"
                Case "TRLR"
                Case "MDU"
                Case "CHURCH"
                Case "SCHOOL"
                Case "BUSINESS"
                Case Else
                    Me.show
                    Exit Sub
            End Select
            
            vAttList = objBlock.GetAttributes
            lbTerminal.List(i, 3) = vAttList(0).TextString & "  " & vAttList(1).TextString
            
            lbSub.AddItem vAttList(0).TextString
            iIndex = lbSub.ListCount - 1
            lbSub.List(iIndex, 1) = vAttList(1).TextString
            lbSub.List(iIndex, 2) = objBlock.Name
            lbSub.List(iIndex, 3) = vAttList(2).TextString
            lbSub.List(iIndex, 4) = lbTerminal.List(i, 1) & ": " & lbTerminal.List(i, 2)
            lbSub.List(iIndex, 5) = objBlock.InsertionPoint(0)
            lbSub.List(iIndex, 6) = objBlock.InsertionPoint(1)
            
            Me.show
            GoTo Exit_Sub
        End If
    Next i
Exit_Sub:
    
End Sub

Private Sub UserForm_Initialize()
    lbSplice.ColumnCount = 5
    lbSplice.ColumnWidths = "48;48;48;72;36"
    
    lbTerminal.ColumnCount = 5
    lbTerminal.ColumnWidths = "48;48;48;72;36"
    
    lbSub.ColumnCount = 7
    lbSub.ColumnWidths = "48;48;48;48;48;48;48"
    
    cbType.AddItem ""
    cbType.AddItem "HACO"
    cbType.AddItem "HBFO"
    
    cbSize.AddItem ""
    cbSize.AddItem "12"
    cbSize.AddItem "24"
    cbSize.AddItem "36"
    cbSize.AddItem "48"
    cbSize.AddItem "72"
    cbSize.AddItem "96"
    cbSize.AddItem "144"
    cbSize.AddItem "216"
    cbSize.AddItem "288"
    cbSize.AddItem "360"
    cbSize.AddItem "432"
End Sub

Attribute VB_Name = "PlaceCableForm"
Attribute VB_Base = "0{0839C1A4-1700-4126-95EA-1E8D5820A915}{04B0C880-7044-46A8-8215-DAFE41E6EA1C}"
Attribute VB_GlobalNameSpace = False
Attribute VB_Creatable = False
Attribute VB_PredeclaredId = True
Attribute VB_Exposed = False
Attribute VB_TemplateDerived = False
Attribute VB_Customizable = False

Private Sub cbAdd_Click()
    Dim excelApp As Excel.Application
    Dim ws As Excel.Worksheet
    Dim fName As String
    Dim strPath, strTemp As String
    Dim strPole, strType As String
    Dim lRow As Long
    Dim iI As Integer
    
    Me.Hide
  On Error Resume Next
    
    strPole = tbPole.Value
    
    strPath = ThisDrawing.FullName
    strPath = Replace(strPath, ".dwg", ".xlsx")
    
    fName = Dir(strPath)
    If fName = "" Then
        MsgBox "There are no Records in folder."
        Exit Sub
    End If
    
    Set excelApp = CreateObject("Excel.Application")
    excelApp.Visible = False
    
    Err = 0
    Set wb = Excel.Workbooks.Open(strPath)
    If Not Err = 0 Then
        MsgBox "Error opening file"
        GoTo Exit_Sub
    End If
    
    lRow = 2
    While Not Sheets("Cables").Cells(lRow, 1).Value = ""
        'If Sheets("Cables").Cells(lRow, 1).Value = strPole Then GoTo Found_Row
        lRow = lRow + 1
    Wend
    
Found_Row:
    
    Sheets("Cables").Cells(lRow, 1).Value = strPole
    Sheets("Cables").Cells(lRow, 2).Value = tbNextPole.Value
    Sheets("Cables").Cells(lRow, 3).Value = tbLength.Value
    Sheets("Cables").Cells(lRow, 4).Value = tbSCoil.Value & "-" & tbECoil.Value & "-"
    Sheets("Cables").Cells(lRow, 5).Value = tbJob.Value
    Sheets("Cables").Cells(lRow, 7).Value = cbType.Value
    Sheets("Cables").Cells(lRow, 8).Value = cbSize.Value
    Sheets("Cables").Cells(lRow, 9).Value = cbSuffix.Value
    Sheets("Cables").Cells(lRow, 10).Value = tbPosition.Value & "-1"
    strTemp = "1-" & cbSize.Value & "++" & tbCount.Value & "~1-" & cbSize.Value & "~" & tbPrevious.Value & "~" & tbJob.Value
    Sheets("Cables").Cells(lRow, 11).Value = strTemp
    
    If CInt(tbECoil.Value) > 0 Then
        tbSCoil.Value = tbECoil.Value
    Else
        tbSCoil.Value = "0"
    End If
    tbECoil.Value = "0"
    
    tbPrevious.Value = tbPole.Value
    tbPole.Value = tbNextPole.Value
    tbNextPole.Value = ""
    tbLength.Value = ""
    
Exit_Sub:
    ActiveWorkbook.Save
    ActiveWorkbook.Close
    
    Me.show
End Sub

Private Sub cbGetCable_Click()
    Dim entPole As AcadObject
    Dim vAttList, basePnt As Variant
    Dim objBlock As AcadBlockReference
    Dim vLine, vItem, vTemp As Variant
    Dim strTemp, strFiber As String
    Dim strJob, strCable, strCount, strToPnt As String
    Dim iFFiber, iTFiber As Integer
    Dim iFCount, iTCount As Integer
    
    Me.Hide
  On Error Resume Next
    
    ThisDrawing.Utility.GetEntity entPole, basePnt, "Select Callout: "
    If TypeOf entPole Is AcadBlockReference Then
        Set objBlock = entPole
    Else
        MsgBox "Not a valid Structure."
        Exit Sub
    End If
    
    If Not objBlock.Name = "CableCounts" Then
        Me.show
        Exit Sub
    End If
    
    lbCounts.Clear
    
    iFFiber = 1
    vTemp = Split(ThisDrawing.Name, " ")
    strJob = Replace(vTemp(0), ".dwg", "")
    
    vAttList = objBlock.GetAttributes
    
    vItem = Split(vAttList(1).TextString, "(")
    cbType.Value = vItem(0)
    vTemp = Split(vItem(1), ")")
    cbSize.Value = vTemp(0)
    cbSuffix.Value = vTemp(1)
        
    Select Case vTemp(1)
        Case ""
            cbSuffix.Value = "E"
            tbPosition.Value = "A2"
        Case "E"
            tbPosition.Value = "A2"
        Case Else
            tbPosition.Value = "A1"
    End Select
    
End Sub

Private Sub cbQuit_Click()
    Me.Hide
End Sub

Private Sub cbType_Change()
    cbSuffix.Clear
    
    Select Case cbType.Value
        Case "CO"
            cbSuffix.AddItem ""
            cbSuffix.AddItem "E"
            cbSuffix.AddItem "6M"
            cbSuffix.AddItem "6M-EHS"
            cbSuffix.AddItem "10M"
            cbSuffix.AddItem "16M"
        Case "BFO"
            cbSuffix.AddItem ""
            cbSuffix.AddItem "I"
        Case "UO"
            cbSuffix.AddItem ""
    End Select
End Sub

Private Sub Label10_Click()
    Dim entPole As AcadObject
    Dim objBlock As AcadBlockReference
    Dim vAttList, basePnt As Variant
    Dim strNext As String
    
    Me.Hide
  On Error Resume Next
    
    ThisDrawing.Utility.GetEntity entPole, basePnt, "Select Structure: "
    If TypeOf entPole Is AcadBlockReference Then
        Set objBlock = entPole
    Else
        MsgBox "Not a valid pole."
        GoTo Exit_Sub
    End If
    
    vAttList = objBlock.GetAttributes
    
    strNext = vAttList(0).TextString
    If Not Err = 0 Then GoTo Exit_Sub
    
    tbPole.Value = strNext
    
Exit_Sub:
    Me.show
End Sub

Private Sub Label11_Click()
    Dim entPole As AcadObject
    Dim objBlock As AcadBlockReference
    Dim vAttList, basePnt As Variant
    
    Me.Hide
  On Error Resume Next
    
    ThisDrawing.Utility.GetEntity entPole, basePnt, "Select Cable Span: "
    If TypeOf entPole Is AcadBlockReference Then
        Set objBlock = entPole
    Else
        MsgBox "Not a valid pole."
        Me.show
        Exit Sub
    End If
    
    If Not objBlock.Name = "cable_span" Then
        Me.show
        Exit Sub
    End If
    
    vAttList = objBlock.GetAttributes
    
    tbLength.Value = Replace(vAttList(2).TextString, "'", "")
    
    Me.show
End Sub

Private Sub Label14_Click()
    Dim entPole As AcadObject
    Dim objBlock As AcadBlockReference
    Dim vAttList, basePnt As Variant
    Dim strNext As String
    
    Me.Hide
  On Error Resume Next
    
    ThisDrawing.Utility.GetEntity entPole, basePnt, "Select Structure: "
    If TypeOf entPole Is AcadBlockReference Then
        Set objBlock = entPole
    Else
        MsgBox "Not a valid pole."
        GoTo Exit_Sub
    End If
    
    vAttList = objBlock.GetAttributes
    
    strNext = vAttList(0).TextString
    If Not Err = 0 Then GoTo Exit_Sub
    
    tbNextPole.Value = strNext
    
Exit_Sub:
    Me.show
End Sub

Private Sub Label16_Click()
    If cbType.Value = "CO" Then
        tbECoil.Value = "50"
    Else
        tbECoil.Value = "20"
    End If
End Sub

Private Sub UserForm_Initialize()
    cbType.AddItem ""
    cbType.AddItem "CO"
    cbType.AddItem "BFO"
    cbType.AddItem "UO"
    
    cbSize.AddItem ""
    cbSize.AddItem "12"
    cbSize.AddItem "24"
    cbSize.AddItem "36"
    cbSize.AddItem "48"
    cbSize.AddItem "72"
    cbSize.AddItem "96"
    cbSize.AddItem "144"
    cbSize.AddItem "216"
    cbSize.AddItem "288"
    cbSize.AddItem "360"
    cbSize.AddItem "432"
    
    tbSCoil.Value = "50"
    tbECoil.Value = "0"
    
    Dim strDWG As String
    
    strDWG = Replace(ThisDrawing.Name, ".dwg", "")
    tbJob.Value = strDWG
End Sub

Attribute VB_Name = "PoleForm"
Attribute VB_Base = "0{1E0AE98F-9EA7-4D86-A034-34A5BEE8BC2F}{E44B4DCC-2374-432F-853D-EC50CAC0B5D2}"
Attribute VB_GlobalNameSpace = False
Attribute VB_Creatable = False
Attribute VB_PredeclaredId = True
Attribute VB_Exposed = False
Attribute VB_TemplateDerived = False
Attribute VB_Customizable = False
Private Sub cbGetPole_Click()
    Dim excelApp As Excel.Application
    Dim ws As Excel.Worksheet
    Dim fName As String
    Dim strPath, strTemp As String
    Dim entPole As AcadObject
    Dim objBlock As AcadBlockReference
    Dim vAttList, basePnt As Variant
    Dim lRow As Long
    'Dim tempFt, tempIn, iStep As Integer
    'Dim tempTotal As Double
    'Dim vItem1, vItem2 As Variant
    'Dim str1, str2, str3, strOther As String
    'Dim strTemp As String
    
    Me.Hide
  On Error Resume Next
    
    ThisDrawing.Utility.GetEntity entPole, basePnt, "Select Pole: "
    If TypeOf entPole Is AcadBlockReference Then
        Set objBlock = entPole
    Else
        MsgBox "Not a valid pole."
        Exit Sub
    End If
    
    If Not objBlock.Name = "iPole" Then
        Me.show
        Exit Sub
    End If
    
    vAttList = objBlock.GetAttributes
    
    strPath = ThisDrawing.FullName
    strPath = Replace(strPath, ".dwg", ".xlsx")
    
    fName = Dir(strPath)
    If fName = "" Then
        MsgBox "There are no Records in folder."
        Exit Sub
    End If
    
    Set excelApp = CreateObject("Excel.Application")
    excelApp.Visible = False
    
    Err = 0
    Set wb = Excel.Workbooks.Open(strPath)
    If Not Err = 0 Then
        MsgBox "Error opening file"
        GoTo Exit_Sub
    End If
    
    lRow = 2
    While Not Sheets("Poles").Cells(lRow, 1).Value = ""
        If Sheets("Poles").Cells(lRow, 1).Value = vAttList(0).TextString Then
            tbName.Value = Sheets("Poles").Cells(lRow, 1).Value
            tbOwner.Value = Sheets("Poles").Cells(lRow, 2).Value
            tbHC.Value = Sheets("Poles").Cells(lRow, 3).Value
            tbYear.Value = Sheets("Poles").Cells(lRow, 4).Value
            tbGrd.Value = Sheets("Poles").Cells(lRow, 5).Value
            
            strTemp = Replace(Sheets("Poles").Cells(lRow, 7).Value, "**", vbCr)
            tbUnits.Value = strTemp
            
            tbX.Value = Sheets("Poles").Cells(lRow, 8).Value
            tbY.Value = Sheets("Poles").Cells(lRow, 9).Value
                
            GoTo Exit_Sub
        End If
        lRow = lRow + 1
    Wend
    
Exit_Sub:
    ActiveWorkbook.Save
    ActiveWorkbook.Close
    
    Me.show
End Sub

Private Sub cbQuit_Click()
    Me.Hide
End Sub

Private Sub cbUpdate_Click()
    Dim excelApp As Excel.Application
    Dim ws As Excel.Worksheet
    Dim fName As String
    Dim strPath, strTemp As String
    Dim entPole As AcadObject
    Dim objBlock As AcadBlockReference
    Dim vAttList, basePnt As Variant
    Dim lRow As Long
    Dim strPole As String
    'Dim tempFt, tempIn, iStep As Integer
    'Dim tempTotal As Double
    'Dim vItem1, vItem2 As Variant
    'Dim str1, str2, str3, strOther As String
    'Dim strTemp As String
    
    'Me.Hide
  On Error Resume Next
    
    'ThisDrawing.Utility.GetEntity entPole, basePnt, "Select Pole: "
    'If TypeOf entPole Is AcadBlockReference Then
        'Set objBlock = entPole
    'Else
        'MsgBox "Not a valid pole."
        'Exit Sub
    'End If
    
    'If Not objBlock.Name = "iPole" Then
        'Me.show
        'Exit Sub
    'End If
    
    'vAttList = objBlock.GetAttributes
    strPole = tbName.Value
    
    strPath = ThisDrawing.FullName
    strPath = Replace(strPath, ".dwg", ".xlsx")
    
    fName = Dir(strPath)
    If fName = "" Then
        MsgBox "There are no Records in folder."
        Exit Sub
    End If
    
    Set excelApp = CreateObject("Excel.Application")
    excelApp.Visible = False
    
    Err = 0
    Set wb = Excel.Workbooks.Open(strPath)
    If Not Err = 0 Then
        MsgBox "Error opening file"
        GoTo Exit_Sub
    End If
    
    lRow = 2
    While Not Sheets("Poles").Cells(lRow, 1).Value = ""
        If Sheets("Poles").Cells(lRow, 1).Value = strPole Then
            Sheets("Poles").Cells(lRow, 1).Value = tbName.Value
            Sheets("Poles").Cells(lRow, 2).Value = tbOwner.Value
            Sheets("Poles").Cells(lRow, 3).Value = tbHC.Value
            Sheets("Poles").Cells(lRow, 4).Value = tbYear.Value
            Sheets("Poles").Cells(lRow, 5).Value = tbGrd.Value
            
            strTemp = Replace(tbUnits.Value, vbCr, "**")
            strTemp = Replace(strTemp, vbLf, "")
            Sheets("Poles").Cells(lRow, 7).Value = strTemp
            
            Sheets("Poles").Cells(lRow, 8).Value = tbX.Value
            Sheets("Poles").Cells(lRow, 9).Value = tbY.Value
                
            GoTo Exit_Sub
        End If
        lRow = lRow + 1
    Wend
    
Exit_Sub:
    ActiveWorkbook.Save
    ActiveWorkbook.Close
    
    'Me.show
End Sub

Attribute VB_Name = "RecordsConversion"
Attribute VB_Base = "0{50B97832-A33B-4C20-B9DF-FE19F7AFAAC1}{859AFBCD-34E8-4B37-8425-CCAC3538251B}"
Attribute VB_GlobalNameSpace = False
Attribute VB_Creatable = False
Attribute VB_PredeclaredId = True
Attribute VB_Exposed = False
Attribute VB_TemplateDerived = False
Attribute VB_Customizable = False

Private Sub cbCreate_Click()
    Select Case cbType.Value
        Case "Poles"
            Call CreatePoleReport
        Case "Poles (ABBV)"
            Call CreatePoleABBVReport
        Case "CustomerPoints"
            Call CreateCustomerReport
        Case "MTEMC Subs"
            Call CreatexSubsReport
        Case "Converted Subs"
            Call CreateConvertSubsReport
    End Select
End Sub

Private Sub cbExchange_Change()
    Select Case cbExchange.Value
        Case "Airport", "Interchange", "Smyrna"
            cbCity.Value = "Smyrna"
            tbZipCode.Value = "37167"
        Case "Chapel Hill"
            cbCity.Value = "Chapel Hill"
            tbZipCode.Value = "37034"
    End Select
End Sub

Private Sub cbQuit_Click()
    Me.Hide
End Sub

Private Sub UserForm_Initialize()
    cbExchange.AddItem "Airport"
    cbExchange.AddItem "Almaville"
    cbExchange.AddItem "Chapel Hill"
    cbExchange.AddItem "Interchange"
    cbExchange.AddItem "Florence"
    cbExchange.AddItem "Lavergne"
    cbExchange.AddItem "Lewisburg"
    cbExchange.AddItem "Murfreesboro"
    'cbExchange.AddItem "Nolensville"
    cbExchange.AddItem "Smyrna"
    
    cbType.AddItem "Poles"
    cbType.AddItem "Poles (ABBV)"
    cbType.AddItem "Peds"
    cbType.AddItem "Handholes"
    cbType.AddItem "Flower Pots"
    cbType.AddItem "MTEMC Subs"
    cbType.AddItem "Converted Subs"
    cbType.AddItem "CustomerPoints"
    
    Dim vTemp As Variant
    Dim strTemp As String
    
    strTemp = Replace(ThisDrawing.Name, ".dwg", "")
    vTemp = Split(strTemp, " ")
    tbWO.Value = vTemp(0)
    
    Select Case UBound(vTemp)
        Case Is = 0
        Case Is = 1
            tbSA.Value = vTemp(1)
        Case Else
            strTemp = vTemp(1)
            For i = 2 To UBound(vTemp)
                strTemp = strTemp & " " & vTemp(i)
            Next i
            tbSA.Value = strTemp
    End Select
    
End Sub

Private Sub CreatePoleReport()
    Dim objSS As AcadSelectionSet
    Dim filterType, filterValue As Variant
    Dim grpCode(0) As Integer
    Dim grpValue(0) As Variant
    Dim vPnt1, vPnt2 As Variant
    Dim objBlock As AcadBlockReference
    Dim vAttList As Variant
    Dim dPnt1(2), dPnt2(2) As Double
    
    Dim strFileName As String
    Dim strDWGName As String
    
    Dim vTemp As Variant
    Dim strWO, strSA, strExchange As String
    Dim strRoute, strNumber, strType As String
    Dim strSuffix, strPUnit As String
    Dim strLat, strLong, strTemp As String
    
    strWO = tbWO.Value
    strExchange = cbExchange.Value
    strSA = tbSA.Value
    
    strFileName = ThisDrawing.Path & "\" & strWO & " Records Import Poles.csv"
    
    Open strFileName For Output As #1
    
    Print #1, "Enclosure Type,Suffix,Latitude,Longitude,Exchange,Route,Service Area,Ped Number,Work Order,Pay Unit"

    grpCode(0) = 2
    grpValue(0) = "iPole"
    filterType = grpCode
    filterValue = grpValue
    
  On Error Resume Next
    Me.Hide
    vPnt1 = ThisDrawing.Utility.GetPoint(, "Get BL Corner: ")
    vPnt2 = ThisDrawing.Utility.GetCorner(vPnt1, vbCr & "Get UR Corner: ")
    
    'dPnt1(0) = vPnt1(0)
    'dPnt1(1) = vPnt1(1)
    'dPnt1(2) = vPnt1(2)
    
    'dPnt2(0) = vPnt2(0)
    'dPnt2(1) = vPnt2(1)
    'dPnt2(2) = vPnt2(2)
  
    Err = 0
    
    Set objSS = ThisDrawing.SelectionSets.Add("objSS")
    If Not Err = 0 Then
        Set objSS = ThisDrawing.SelectionSets.Item("objSS")
        Err = 0
    End If
    objSS.Select acSelectionSetWindow, vPnt1, vPnt2, filterType, filterValue
    If Not Err = 0 Then
        MsgBox "Error: " & Err.Number & vbCr & Err.Description
        Me.show
        Exit Sub
    End If
    
    MsgBox "Poles Found: " & objSS.Count
    
    For Each objBlock In objSS
        vAttList = objBlock.GetAttributes
        If vAttList(0).TextString = "POLE" Then GoTo Next_objBlock
        If vAttList(0).TextString = "" Then GoTo Next_objBlock
        
        vTemp = Split(vAttList(0).TextString, "/")
        strRoute = vTemp(0)
        strNumber = vTemp(1)
        strType = "A"
        If vAttList(5).TextString = "" Then
            strSuffix = "30-5"
        Else
            strSuffix = vAttList(5).TextString
        End If
        
        vTemp = Split(vAttList(7).TextString, ",")
        strLat = vTemp(0)
        strLong = vTemp(1)
        strPUnit = strType '& strSuffix
        
        strTemp = strType & "," & strSuffix & "," & strLat & "," & strLong & "," & strExchange & "," & strRoute
        strTemp = strTemp & "," & strSA & "," & strNumber & "," & strWO & "," & strPUnit
        Print #1, strTemp
        
Next_objBlock:
    Next objBlock
    
    MsgBox "Export Complete"
    Close #1
    
Exit_Sub:
    objSS.Clear
    objSS.Delete
    Me.show
End Sub

Private Sub CreatePoleABBVReport()
    Dim objSS As AcadSelectionSet
    Dim filterType, filterValue As Variant
    Dim grpCode(0) As Integer
    Dim grpValue(0) As Variant
    Dim vPnt1, vPnt2 As Variant
    Dim objBlock As AcadBlockReference
    Dim vAttList As Variant
    Dim dPnt1(2), dPnt2(2) As Double
    
    Dim strFileName As String
    Dim strDWGName As String
    
    Dim vTemp As Variant
    Dim strWO, strSA, strExchange As String
    Dim strRoute, strNumber, strType As String
    Dim strSuffix, strPUnit As String
    Dim strLat, strLong, strTemp As String
    
    strWO = tbWO.Value
    strExchange = cbExchange.Value
    strSA = tbSA.Value
    
    strFileName = ThisDrawing.Path & "\" & strWO & " Records Import Poles.csv"
    
    Open strFileName For Output As #1
    
    Print #1, "Enclosure Type,Suffix,Latitude,Longitude,Exchange,Route,Service Area,Ped Number,Work Order,Pay Unit"

    grpCode(0) = 2
    grpValue(0) = "POLE"
    filterType = grpCode
    filterValue = grpValue
    
  On Error Resume Next
    Me.Hide
    vPnt1 = ThisDrawing.Utility.GetPoint(, "Get BL Corner: ")
    vPnt2 = ThisDrawing.Utility.GetCorner(vPnt1, vbCr & "Get UR Corner: ")
    
    'dPnt1(0) = vPnt1(0)
    'dPnt1(1) = vPnt1(1)
    'dPnt1(2) = vPnt1(2)
    
    'dPnt2(0) = vPnt2(0)
    'dPnt2(1) = vPnt2(1)
    'dPnt2(2) = vPnt2(2)
  
    Err = 0
    
    Set objSS = ThisDrawing.SelectionSets.Add("objSS")
    If Not Err = 0 Then
        Set objSS = ThisDrawing.SelectionSets.Item("objSS")
        Err = 0
    End If
    objSS.Select acSelectionSetWindow, vPnt1, vPnt2, filterType, filterValue
    If Not Err = 0 Then
        MsgBox "Error: " & Err.Number & vbCr & Err.Description
        Me.show
        Exit Sub
    End If
    
    MsgBox "Poles Found: " & objSS.Count
    
    For Each objBlock In objSS
        vAttList = objBlock.GetAttributes
        If vAttList(0).TextString = "POLE" Then GoTo Next_objBlock
        If vAttList(0).TextString = "" Then GoTo Next_objBlock
        
        vTemp = Split(vAttList(0).TextString, "/")
        strRoute = vTemp(0)
        strNumber = vTemp(1)
        strType = "A"
        If vAttList(2).TextString = "" Then
            strSuffix = "30-5"
        Else
            strSuffix = vAttList(2).TextString
        End If
        
        vTemp = Split(vAttList(3).TextString, ",")
        strLat = vTemp(0)
        strLong = vTemp(1)
        strPUnit = strType '& strSuffix
        
        strTemp = strType & "," & strSuffix & "," & strLat & "," & strLong & "," & strExchange & "," & strRoute
        strTemp = strTemp & "," & strSA & "," & strNumber & "," & strWO & "," & strPUnit
        Print #1, strTemp
        
Next_objBlock:
    Next objBlock
    
    MsgBox "Export Complete"
    Close #1
    
Exit_Sub:
    objSS.Clear
    objSS.Delete
    Me.show
End Sub

Private Sub CreateCustomerReport()
    Dim objSS As AcadSelectionSet
    Dim filterType, filterValue As Variant
    Dim grpCode(0) As Integer
    Dim grpValue(0) As Variant
    Dim vPnt1, vPnt2 As Variant
    Dim objBlock As AcadBlockReference
    Dim objPoint As AcadPoint
    Dim vAttList As Variant
    Dim dPnt1(2), dPnt2(2) As Double
    
    Dim amap As AcadMap
    Dim ODRcs As ODRecords
    Dim ODRc As ODRecord
    Dim tbl As ODTable
    Dim tbls As ODTables
    
    Dim strFileName As String
    Dim strDWGName As String
    
    Dim vTemp As Variant
    Dim strWO, strSA, strExchange As String
    'Dim strRoute, strNumber, strType As String
    'Dim strSuffix, strPUnit As String
    Dim strStreet As String
    Dim strLat, strLong, strTemp As String
    Dim strCity, strState, strZip As String
    Dim strBusiness As String
    
    strWO = tbWO.Value
    strExchange = cbExchange.Value
    strSA = tbSA.Value
    
    strFileName = ThisDrawing.Path & "\" & strWO & " Records Import Customers.csv"

    grpCode(0) = 8
    grpValue(0) = "CustomerPoints"
    filterType = grpCode
    filterValue = grpValue
    
  On Error Resume Next
    Me.Hide
    vPnt1 = ThisDrawing.Utility.GetPoint(, "Get BL Corner: ")
    vPnt2 = ThisDrawing.Utility.GetCorner(vPnt1, vbCr & "Get UR Corner: ")
    
    'dPnt1(0) = vPnt1(0)
    'dPnt1(1) = vPnt1(1)
    'dPnt1(2) = vPnt1(2)
    
    'dPnt2(0) = vPnt2(0)
    'dPnt2(1) = vPnt2(1)
    'dPnt2(2) = vPnt2(2)
  
    Err = 0
    
    Set objSS = ThisDrawing.SelectionSets.Add("objSS")
    If Not Err = 0 Then
        Set objSS = ThisDrawing.SelectionSets.Item("objSS")
        Err = 0
    End If
    objSS.Select acSelectionSetWindow, vPnt1, vPnt2, filterType, filterValue
    If Not Err = 0 Then
        MsgBox "Error: " & Err.Number & vbCr & Err.Description
        Me.show
        Exit Sub
    End If
    
    MsgBox "Customers Found: " & objSS.Count
    If objSS.Count < 1 Then GoTo Exit_Sub
    
    Open strFileName For Output As #1
    
    Print #1, "Street,Latitude,Longitude,City,State,Zip Code,Exchange,Service Area,Business Name"
    
    Set amap = ThisDrawing.Application.GetInterfaceObject("AutoCADMap.Application")
    
    Set tbls = amap.Projects(ThisDrawing).ODTables
    If tbls.Count > 0 Then
        For Each tbl In tbls
            If tbl.Name = "CustomerPoints" Then GoTo Exit_For
        Next
    End If
Exit_For:

    Set ODRcs = tbl.GetODRecords
    
    For Each objPoint In objSS
        strLat = objPoint.Coordinates(1)
        strLong = objPoint.Coordinates(0)
        
        boolVal = ODRcs.Init(objPoint, True, False)
        Set ODRc = ODRcs.Record
        
        'strLat = ODRc.Item(16).Value
        'strLong = ODRc.Item(17).Value
        
        'strStreet = ODRc.Item(60).Value
        'strCity = ODRc.Item(63).Value
        'strState = ODRc.Item(64).Value
        'strZip = ODRc.Item(65).Value
        'strBusiness = ODRc.Item(66).Value
        
        strStreet = ODRc.Item(3).Value
        strCity = ODRc.Item(6).Value
        strState = ODRc.Item(7).Value
        strZip = ODRc.Item(8).Value
        strBusiness = ODRc.Item(9).Value
        
        strTemp = strStreet & "," & strLat & "," & strLong & "," & strCity & "," & strState
        strTemp = strTemp & "," & strZip & "," & strExchange & "," & strSA & "," & strBusiness
        Print #1, strTemp
    Next objPoint
    
    MsgBox "Export Complete"
    Close #1
    
Exit_Sub:
    
    objSS.Clear
    objSS.Delete
    Me.show
End Sub

Private Sub CreateConvertSubsReport()
    Dim objSS As AcadSelectionSet
    Dim filterType, filterValue As Variant
    Dim grpCode(0) As Integer
    Dim grpValue(0) As Variant
    Dim vPnt1, vPnt2 As Variant
    Dim objBlock As AcadBlockReference
    Dim objPoint As AcadPoint
    Dim vAttList As Variant
    Dim dPnt1(2), dPnt2(2) As Double
    
    Dim amap As AcadMap
    Dim ODRcs As ODRecords
    Dim ODRc As ODRecord
    Dim tbl As ODTable
    Dim tbls As ODTables
    
    Dim strFileName As String
    Dim strDWGName As String
    
    Dim vTemp As Variant
    Dim strWO, strSA, strExchange As String
    'Dim strRoute, strNumber, strType As String
    'Dim strSuffix, strPUnit As String
    Dim strStreet As String
    Dim strLat, strLong, strTemp As String
    Dim strCity, strState, strZip As String
    Dim strBusiness As String
    
    strWO = tbWO.Value
    strExchange = cbExchange.Value
    strSA = tbSA.Value
    
    strFileName = ThisDrawing.Path & "\" & strWO & " Records Import Customers.csv"

    grpCode(0) = 8
    grpValue(0) = "Customers"
    filterType = grpCode
    filterValue = grpValue
    
  On Error Resume Next
    Me.Hide
    vPnt1 = ThisDrawing.Utility.GetPoint(, "Get BL Corner: ")
    vPnt2 = ThisDrawing.Utility.GetCorner(vPnt1, vbCr & "Get UR Corner: ")
    
    'dPnt1(0) = vPnt1(0)
    'dPnt1(1) = vPnt1(1)
    'dPnt1(2) = vPnt1(2)
    
    'dPnt2(0) = vPnt2(0)
    'dPnt2(1) = vPnt2(1)
    'dPnt2(2) = vPnt2(2)
  
    Err = 0
    
    Set objSS = ThisDrawing.SelectionSets.Add("objSS")
    If Not Err = 0 Then
        Set objSS = ThisDrawing.SelectionSets.Item("objSS")
        Err = 0
    End If
    objSS.Select acSelectionSetWindow, vPnt1, vPnt2, filterType, filterValue
    If Not Err = 0 Then
        MsgBox "Error: " & Err.Number & vbCr & Err.Description
        Me.show
        Exit Sub
    End If
    
    MsgBox "Customers Found: " & objSS.Count
    If objSS.Count < 1 Then GoTo Exit_Sub
    
    Open strFileName For Output As #1
    
    Print #1, "Street,Latitude,Longitude,City,State,Zip Code,Exchange,Service Area,Business Name"
    
    Set amap = ThisDrawing.Application.GetInterfaceObject("AutoCADMap.Application")
    
    Set tbls = amap.Projects(ThisDrawing).ODTables
    If tbls.Count > 0 Then
        For Each tbl In tbls
            If tbl.Name = "Customers" Then GoTo Exit_For
        Next
    End If
Exit_For:

    Set ODRcs = tbl.GetODRecords
    
    For Each objPoint In objSS
        strLat = objPoint.Coordinates(1)
        strLong = objPoint.Coordinates(0)
        
        boolVal = ODRcs.Init(objPoint, True, False)
        Set ODRc = ODRcs.Record
        
        strStreet = ODRc.Item(1).Value & " " & ODRc.Item(2).Value
        strCity = cbCity.Value
        strState = "TN"
        strZip = tbZipCode.Value
        strBusiness = ODRc.Item(3).Value
        
        strTemp = strStreet & "," & strLat & "," & strLong & "," & strCity & "," & strState
        strTemp = strTemp & "," & strZip & "," & strExchange & "," & strSA & "," & strBusiness
        Print #1, strTemp
    Next objPoint
    
    MsgBox "Export Complete"
    Close #1
    
Exit_Sub:
    
    objSS.Clear
    objSS.Delete
    Me.show
End Sub

Private Sub CreatexSubsReport()
    Dim objSS As AcadSelectionSet
    Dim filterType, filterValue As Variant
    Dim grpCode(0) As Integer
    Dim grpValue(0) As Variant
    Dim vPnt1, vPnt2 As Variant
    Dim objBlock As AcadBlockReference
    Dim objPoint As AcadPoint
    Dim vAttList As Variant
    Dim dPnt1(2), dPnt2(2) As Double
    
    Dim amap As AcadMap
    Dim ODRcs As ODRecords
    Dim ODRc As ODRecord
    Dim tbl As ODTable
    Dim tbls As ODTables
    
    Dim strFileName As String
    Dim strDWGName As String
    
    Dim vTemp As Variant
    Dim strWO, strSA, strExchange As String
    'Dim strRoute, strNumber, strType As String
    'Dim strSuffix, strPUnit As String
    Dim strStreet As String
    Dim strLat, strLong, strTemp As String
    Dim strCity, strState, strZip As String
    Dim strBusiness As String
    
    strWO = tbWO.Value
    strExchange = cbExchange.Value
    strSA = tbSA.Value
    
    strFileName = ThisDrawing.Path & "\" & strWO & " Records Import Customers.csv"

    grpCode(0) = 8
    grpValue(0) = "CustomerPoints"
    filterType = grpCode
    filterValue = grpValue
    
  On Error Resume Next
    Me.Hide
    vPnt1 = ThisDrawing.Utility.GetPoint(, "Get BL Corner: ")
    vPnt2 = ThisDrawing.Utility.GetCorner(vPnt1, vbCr & "Get UR Corner: ")
    
    'dPnt1(0) = vPnt1(0)
    'dPnt1(1) = vPnt1(1)
    'dPnt1(2) = vPnt1(2)
    
    'dPnt2(0) = vPnt2(0)
    'dPnt2(1) = vPnt2(1)
    'dPnt2(2) = vPnt2(2)
  
    Err = 0
    
    Set objSS = ThisDrawing.SelectionSets.Add("objSS")
    If Not Err = 0 Then
        Set objSS = ThisDrawing.SelectionSets.Item("objSS")
        Err = 0
    End If
    objSS.Select acSelectionSetWindow, vPnt1, vPnt2, filterType, filterValue
    If Not Err = 0 Then
        MsgBox "Error: " & Err.Number & vbCr & Err.Description
        Me.show
        Exit Sub
    End If
    
    MsgBox "Customers Found: " & objSS.Count
    If objSS.Count < 1 Then GoTo Exit_Sub
    
    Open strFileName For Output As #1
    
    Print #1, "Street,Latitude,Longitude,City,State,Zip Code,Exchange,Service Area,Business Name"
    
    Set amap = ThisDrawing.Application.GetInterfaceObject("AutoCADMap.Application")
    
    Set tbls = amap.Projects(ThisDrawing).ODTables
    If tbls.Count > 0 Then
        For Each tbl In tbls
            If tbl.Name = "CustomerPoints" Then GoTo Exit_For
        Next
    End If
Exit_For:

    Set ODRcs = tbl.GetODRecords
    
    For Each objPoint In objSS
        'strLat = objPoint.Coordinates(1)
        'strLong = objPoint.Coordinates(0)
        
        boolVal = ODRcs.Init(objPoint, True, False)
        Set ODRc = ODRcs.Record
        
        strLat = ODRc.Item(16).Value
        strLong = ODRc.Item(17).Value
        
        strStreet = ODRc.Item(60).Value
        strCity = ODRc.Item(63).Value
        strState = ODRc.Item(64).Value
        strZip = ODRc.Item(65).Value
        strBusiness = ODRc.Item(66).Value
        
        'strStreet = ODRc.Item(1).Value & " " & ODRc.Item(2).Value
        'strCity = "Chapel Hill"
        'strState = "TN"
        'strZip = "37034"
        'strBusiness = ODRc.Item(3).Value
        
        strTemp = strStreet & "," & strLat & "," & strLong & "," & strCity & "," & strState
        strTemp = strTemp & "," & strZip & "," & strExchange & "," & strSA & "," & strBusiness
        Print #1, strTemp
    Next objPoint
    
    MsgBox "Export Complete"
    Close #1
    
Exit_Sub:
    
    objSS.Clear
    objSS.Delete
    Me.show
End Sub

Attribute VB_Name = "RecordsExport"
Attribute VB_Base = "0{C8243036-5092-4E65-B71B-8C9F4AC4390A}{892E385D-A7CB-45E8-AEC5-83D35B180E6D}"
Attribute VB_GlobalNameSpace = False
Attribute VB_Creatable = False
Attribute VB_PredeclaredId = True
Attribute VB_Exposed = False
Attribute VB_TemplateDerived = False
Attribute VB_Customizable = False
Dim vPnt1, vPnt2 As Variant
Dim strBaseName As String
Dim strItemResults As String
    
Private Sub cbExchange_Change()
    Select Case cbExchange.Value
        Case "Airport", "Interchange", "Smyrna"
            cbCity.Value = "Smyrna"
            tbZipCode.Value = "37167"
        Case "Chapel Hill"
            cbCity.Value = "Chapel Hill"
            tbZipCode.Value = "37034"
    End Select
End Sub

Private Sub cbExport_Click()
    Me.Hide
    vPnt1 = ThisDrawing.Utility.GetPoint(, "Get BL Corner: ")
    vPnt2 = ThisDrawing.Utility.GetCorner(vPnt1, vbCr & "Get UR Corner: ")
    
    
    Select Case cbVersion.Value
        Case "2.0"
            If cbPoles.Value Then CreatePoleReport20 ("sPole")
            If cbPEDs.Value Then CreateUGStructureReport20 ("sPed")
            If cbHHs.Value Then CreateUGStructureReport20 ("sHH")
            
            If cbRES.Value Then CreateCustomerReport20 ("RESIDENCE")
            If cbBUS.Value Then CreateCustomerReport20 ("BUSINESS")
            If cbSchool.Value Then CreateCustomerReport20 ("SCHOOL")
            If cbChurch.Value Then CreateCustomerReport20 ("CHURCH")
            If cbTRLR.Value Then CreateCustomerReport20 ("TRLR")
            If cbMDU.Value Then CreateCustomerReport20 ("MDU")
        Case "1.0"
            If cbPoles.Value Then CreatePoleReport ("iPole")
            If cbPEDs.Value Then CreatePoleReport ("PED")
            If cbHHs.Value Then CreatePoleReport ("dHH")
            
            If cbRES.Value Then CreateCustomerReport ("RES")
            If cbBUS.Value Then CreateCustomerReport ("BUSINESS")
            If cbSchool.Value Then CreateCustomerReport ("SCHOOL")
            If cbChurch.Value Then CreateCustomerReport ("CHURCH")
            If cbTRLR.Value Then CreateCustomerReport ("TRLR")
            If cbMDU.Value Then CreateCustomerReport ("MDU")
    End Select
    
    MsgBox strItemResults
    
    Me.show
End Sub

Private Sub cbQuit_Click()
    Me.Hide
End Sub

Private Sub UserForm_Initialize()
    cbExchange.AddItem "Airport"
    cbExchange.AddItem "Almaville"
    cbExchange.AddItem "Chapel Hill"
    cbExchange.AddItem "Interchange"
    cbExchange.AddItem "Florence"
    cbExchange.AddItem "Lavergne"
    cbExchange.AddItem "Lewisburg"
    cbExchange.AddItem "Murfreesboro"
    'cbExchange.AddItem "Nolensville"
    cbExchange.AddItem "Smyrna"
    
    cbVersion.AddItem "1.0"
    cbVersion.AddItem "2.0"
    cbVersion.Value = "1.0"
    
    Dim vTemp As Variant
    Dim strTemp As String
    
    strTemp = Replace(ThisDrawing.Name, ".dwg", "")
    vTemp = Split(strTemp, " ")
    tbWO.Value = vTemp(0)
    
    strBaseName = ThisDrawing.Path & "\Records\" & vTemp(0) & " Records Import-"
    
    Select Case UBound(vTemp)
        Case Is = 0
        Case Is = 1
            tbSA.Value = vTemp(1)
        Case Else
            strTemp = vTemp(1)
            For i = 2 To UBound(vTemp)
                strTemp = strTemp & " " & vTemp(i)
            Next i
            tbSA.Value = strTemp
    End Select
End Sub

Private Sub CreatePoleReport(strBlock As String)
    Dim objSS As AcadSelectionSet
    Dim filterType, filterValue As Variant
    Dim grpCode(0) As Integer
    Dim grpValue(0) As Variant
    Dim objBlock As AcadBlockReference
    Dim vAttList As Variant
    Dim dPnt1(2), dPnt2(2) As Double
    
    'Dim strDWGName As String
    
    Dim vTemp As Variant
    Dim strWO, strSA, strExchange As String
    Dim strRoute, strNumber, strType As String
    Dim strSuffix, strPUnit As String
    Dim strLat, strLong, strTemp As String
    Dim vNE As Variant
    Dim iCounter As Integer
    
    iCounter = 0
    strWO = tbWO.Value
    strExchange = cbExchange.Value
    strSA = tbSA.Value
    
    Select Case strBlock
        Case "iPole", "sPole"
            strFileName = strBaseName & "Poles.csv"
        Case "PED", "sPed"
            strFileName = strBaseName & "Peds.csv"
        Case "dHH", "sHH"
            strFileName = strBaseName & "HHs.csv"
        Case Else
            strFileName = strBaseName & "Other.csv"
    End Select

    grpCode(0) = 2
    grpValue(0) = strBlock
    filterType = grpCode
    filterValue = grpValue
    
  On Error Resume Next
    'dPnt1(0) = vPnt1(0)
    'dPnt1(1) = vPnt1(1)
    'dPnt1(2) = vPnt1(2)
    
    'dPnt2(0) = vPnt2(0)
    'dPnt2(1) = vPnt2(1)
    'dPnt2(2) = vPnt2(2)
  
    Err = 0
    
    Set objSS = ThisDrawing.SelectionSets.Add("objSS")
    If Not Err = 0 Then
        Set objSS = ThisDrawing.SelectionSets.Item("objSS")
        Err = 0
    End If
    objSS.Select acSelectionSetWindow, vPnt1, vPnt2, filterType, filterValue
    If Not Err = 0 Then
        MsgBox "Error: " & Err.Number & vbCr & Err.Description
        Me.show
        Exit Sub
    End If
    
    If objSS.Count < 1 Then Exit Sub
    
    Open strFileName For Output As #1
    
    Print #1, "Enclosure Type,Suffix,Latitude,Longitude,Exchange,Route,Service Area,Ped Number,Work Order,Pay Unit"
    
    For Each objBlock In objSS
        vAttList = objBlock.GetAttributes
        If vAttList(0).TextString = "POLE" Then GoTo Next_objBlock
        If vAttList(0).TextString = "PED" Then GoTo Next_objBlock
        If vAttList(0).TextString = "HH" Then GoTo Next_objBlock
        If vAttList(0).TextString = "" Then GoTo Next_objBlock
        
        vTemp = Split(vAttList(0).TextString, "/")
        strRoute = vTemp(0)
        strNumber = vTemp(1)
        strType = "A"
        If vAttList(5).TextString = "" Then
            strSuffix = "30-5"
        Else
            strSuffix = vAttList(5).TextString
        End If
        
        If Not vAttList(2).TextString = "" Then
            strWO = vAttList(2).TextString
        End If
        
        'If vAttList(7).TextString = "" Then
            vNE = TN83FtoLL(CDbl(objBlock.InsertionPoint(1)), CDbl(objBlock.InsertionPoint(0)))
            strLat = vNE(0)
            strLong = vNE(1)
        'Else
            'vTemp = Split(vAttList(7).TextString, ",")
            'strLat = vTemp(0)
            'strLong = vTemp(1)
        'End If
        
        strPUnit = strType '& strSuffix
        
        strTemp = strType & "," & strSuffix & "," & strLat & "," & strLong & "," & strExchange & "," & strRoute
        strTemp = strTemp & "," & strSA & "," & strNumber & "," & strWO & "," & strPUnit
        Print #1, strTemp
        
        iCounter = iCounter + 1
        
Next_objBlock:
    Next objBlock
    
    Close #1
    
    If strItemResults = "" Then
        strItemResults = strBlock & " Exported/Found: " & iCounter & "/" & objSS.Count
    Else
        strItemResults = strItemResults & vbCr & strBlock & " Exported/Found: " & iCounter & "/" & objSS.Count
    End If
    
Exit_Sub:
    objSS.Clear
    objSS.Delete
End Sub

Private Sub CreateUGStructureReport20(strBlock As String)
    Dim objSS As AcadSelectionSet
    Dim filterType, filterValue As Variant
    Dim grpCode(0) As Integer
    Dim grpValue(0) As Variant
    Dim objBlock As AcadBlockReference
    Dim vAttList As Variant
    Dim dPnt1(2), dPnt2(2) As Double
    
    'Dim strDWGName As String
    
    Dim vTemp As Variant
    Dim strWO, strSA, strExchange As String
    Dim strRoute, strNumber, strType As String
    Dim strSuffix, strPUnit As String
    Dim strLat, strLong, strTemp As String
    Dim strBody As String
    Dim vNE As Variant
    Dim iCounter As Integer
    
    iCounter = 0
    strWO = tbWO.Value
    strExchange = cbExchange.Value
    strSA = tbSA.Value
    
    Select Case strBlock
        Case "sPed"
            strFileName = strBaseName & "Peds.csv"
        Case "sHH"
            strFileName = strBaseName & "HHs.csv"
        Case Else
            strFileName = strBaseName & "Other.csv"
    End Select

    grpCode(0) = 2
    grpValue(0) = strBlock
    filterType = grpCode
    filterValue = grpValue
    
  On Error Resume Next
  
    Err = 0
    
    Set objSS = ThisDrawing.SelectionSets.Add("objSS")
    If Not Err = 0 Then
        Set objSS = ThisDrawing.SelectionSets.Item("objSS")
        Err = 0
    End If
    objSS.Select acSelectionSetWindow, vPnt1, vPnt2, filterType, filterValue
    If Not Err = 0 Then
        MsgBox "Error: " & Err.Number & vbCr & Err.Description
        Me.show
        Exit Sub
    End If
    
    If objSS.Count < 1 Then Exit Sub
    
    strBody = ""
    
    For Each objBlock In objSS
        vAttList = objBlock.GetAttributes
        If vAttList(0).TextString = "PED" Then GoTo Next_objBlock
        If vAttList(0).TextString = "HH" Then GoTo Next_objBlock
        If vAttList(0).TextString = "" Then GoTo Next_objBlock
        
        vTemp = Split(vAttList(0).TextString, "/")
        strRoute = vTemp(0)
        strNumber = vTemp(1)
        strType = vAttList(2).TextString
        strSuffix = ""
        
        vNE = TN83FtoLL(CDbl(objBlock.InsertionPoint(1)), CDbl(objBlock.InsertionPoint(0)))
        strLat = vNE(0)
        strLong = vNE(1)
        
        strPUnit = strType
        
        strTemp = strType & "," & strSuffix & "," & strLat & "," & strLong & "," & strExchange & "," & strRoute
        strTemp = strTemp & "," & strSA & "," & strNumber & "," & strWO & "," & strPUnit
        Print #1, strTemp
        
        If strBody = "" Then
            strBody = strTemp
        Else
            strBody = strBody & vbCr & strTemp
        End If
        
        iCounter = iCounter + 1
        
Next_objBlock:
    Next objBlock
    
    Open strFileName For Output As #1
    
    Print #1, "Enclosure Type,Suffix,Latitude,Longitude,Exchange,Route,Service Area,Ped Number,Work Order,Pay Unit"
    
    Print #1, strBody
    
    Close #1
    
    If strItemResults = "" Then
        strItemResults = strBlock & " Exported/Found: " & iCounter & "/" & objSS.Count
    Else
        strItemResults = strItemResults & vbCr & strBlock & " Exported/Found: " & iCounter & "/" & objSS.Count
    End If
    
Exit_Sub:
    objSS.Clear
    objSS.Delete
    
End Sub

Private Sub CreatePoleReport20(strBlock As String)
    Dim objSS As AcadSelectionSet
    Dim filterType, filterValue As Variant
    Dim grpCode(0) As Integer
    Dim grpValue(0) As Variant
    Dim objBlock As AcadBlockReference
    Dim vAttList As Variant
    Dim dPnt1(2), dPnt2(2) As Double
    
    'Dim strDWGName As String
    
    Dim vTemp As Variant
    Dim strWO, strSA, strExchange As String
    Dim strRoute, strNumber, strType As String
    Dim strSuffix, strPUnit As String
    Dim strLat, strLong, strTemp As String
    Dim strBody As String
    Dim vNE As Variant
    Dim iCounter As Integer
    
    iCounter = 0
    strWO = tbWO.Value
    strExchange = cbExchange.Value
    strSA = tbSA.Value
    
    Select Case strBlock
        Case "sPole"
            strFileName = strBaseName & "Poles.csv"
        Case "sPed"
            strFileName = strBaseName & "Peds.csv"
        Case "sHH"
            strFileName = strBaseName & "HHs.csv"
        Case Else
            strFileName = strBaseName & "Other.csv"
    End Select

    grpCode(0) = 2
    grpValue(0) = strBlock
    filterType = grpCode
    filterValue = grpValue
    
  On Error Resume Next
  
    Err = 0
    
    Set objSS = ThisDrawing.SelectionSets.Add("objSS")
    If Not Err = 0 Then
        Set objSS = ThisDrawing.SelectionSets.Item("objSS")
        Err = 0
    End If
    objSS.Select acSelectionSetWindow, vPnt1, vPnt2, filterType, filterValue
    If Not Err = 0 Then
        MsgBox "Error: " & Err.Number & vbCr & Err.Description
        Me.show
        Exit Sub
    End If
    
    If objSS.Count < 1 Then Exit Sub
    
    strBody = ""
    
    For Each objBlock In objSS
        vAttList = objBlock.GetAttributes
        If vAttList(0).TextString = "POLE" Then GoTo Next_objBlock
        If vAttList(0).TextString = "PED" Then GoTo Next_objBlock
        If vAttList(0).TextString = "HH" Then GoTo Next_objBlock
        If vAttList(0).TextString = "" Then GoTo Next_objBlock
        
        vTemp = Split(vAttList(0).TextString, "/")
        strRoute = vTemp(0)
        strNumber = vTemp(1)
        strType = "A"
        If vAttList(5).TextString = "" Then
            strSuffix = "30-5"
        Else
            strSuffix = Replace(vAttList(5).TextString, " ", "")
        End If
        
        If Not objBlock.Name = "sPole" Then strSuffix = ""
        
        If Not vAttList(2).TextString = "" Then
            strWO = vAttList(2).TextString
        End If
        
        vNE = TN83FtoLL(CDbl(objBlock.InsertionPoint(1)), CDbl(objBlock.InsertionPoint(0)))
        strLat = vNE(0)
        strLong = vNE(1)
        
        strPUnit = strType
        
        strTemp = strType & "," & strSuffix & "," & strLat & "," & strLong & "," & strExchange & "," & strRoute
        strTemp = strTemp & "," & strSA & "," & strNumber & "," & strWO & "," & strPUnit
        Print #1, strTemp
        
        If strBody = "" Then
            strBody = strTemp
        Else
            strBody = strBody & vbCr & strTemp
        End If
        
        iCounter = iCounter + 1
        
Next_objBlock:
    Next objBlock
    
    Open strFileName For Output As #1
    
    Print #1, "Enclosure Type,Suffix,Latitude,Longitude,Exchange,Route,Service Area,Ped Number,Work Order,Pay Unit"
    
    Print #1, strBody
    
    Close #1
    
    If strItemResults = "" Then
        strItemResults = strBlock & " Exported/Found: " & iCounter & "/" & objSS.Count
    Else
        strItemResults = strItemResults & vbCr & strBlock & " Exported/Found: " & iCounter & "/" & objSS.Count
    End If
    
Exit_Sub:
    objSS.Clear
    objSS.Delete
End Sub


Private Sub CreateCustomerReport(strBlock As String)
    Dim objSS As AcadSelectionSet
    Dim objBlock As AcadBlockReference
    Dim filterType, filterValue As Variant
    Dim grpCode(0) As Integer
    Dim grpValue(0) As Variant
    'Dim objBlock As AcadBlockReference
    Dim objPoint As AcadPoint
    Dim vAttList As Variant
    Dim dPnt1(2), dPnt2(2) As Double
    
    Dim vTemp As Variant
    Dim strWO, strSA, strExchange As String
    Dim strHN, strApt, strStreet As String
    Dim strLat, strLong, strTemp As String
    Dim strCity, strState, strZip As String
    Dim strBusiness As String
    Dim vNE, vResult As Variant
    Dim iCounter As Integer
    
    iCounter = 0
    strWO = tbWO.Value
    strExchange = cbExchange.Value
    strSA = tbSA.Value
    
    Select Case strBlock
        Case "RES"
            strFileName = strBaseName & "RES.csv"
        Case "BUSINESS"
            strFileName = strBaseName & "Business.csv"
        Case "SCHOOL"
            strFileName = strBaseName & "School.csv"
        Case "CHURCH"
            strFileName = strBaseName & "Church.csv"
        Case "TRLR"
            strFileName = strBaseName & "Trailer.csv"
        Case "MDU"
            strFileName = strBaseName & "MDU.csv"
        Case Else
            strFileName = strBaseName & "Other.csv"
    End Select

    grpCode(0) = 2
    grpValue(0) = strBlock
    filterType = grpCode
    filterValue = grpValue
    
  On Error Resume Next
    
    'dPnt1(0) = vPnt1(0)
    'dPnt1(1) = vPnt1(1)
    'dPnt1(2) = vPnt1(2)
    
    'dPnt2(0) = vPnt2(0)
    'dPnt2(1) = vPnt2(1)
    'dPnt2(2) = vPnt2(2)
  
    Err = 0
    
    Set objSS = ThisDrawing.SelectionSets.Add("objSS")
    If Not Err = 0 Then
        Set objSS = ThisDrawing.SelectionSets.Item("objSS")
        Err = 0
    End If
    objSS.Select acSelectionSetWindow, vPnt1, vPnt2, filterType, filterValue
    If Not Err = 0 Then
        MsgBox "Error: " & Err.Number & vbCr & Err.Description
        Me.show
        Exit Sub
    End If
    
    'MsgBox "Customers Found: " & objSS.Count
    If objSS.Count < 1 Then GoTo Exit_Sub
    
    Open strFileName For Output As #1
    
    Print #1, "House Number,Street,Apartment Number,Latitude,Longitude,City,State,Zip Code,Exchange,Service Area,Business Name"
    
    For Each objBlock In objSS
        vAttList = objBlock.GetAttributes
        
        vNE = TN83FtoLL(CDbl(objBlock.InsertionPoint(1)), CDbl(objBlock.InsertionPoint(0)))
        strLat = vNE(0)
        strLong = vNE(1)
        
        vResult = SeperateHouseNumber(CStr(vAttList(0).TextString))
        
        strHN = vResult(0)
        If UBound(vResult) > 0 Then
            strApt = vResult(1)
        Else
            strApt = ""
        End If
        
        strStreet = vAttList(1).TextString
        strCity = cbCity.Value
        strState = "TN"
        strZip = tbZipCode.Value
        strBusiness = Replace(vAttList(2).TextString, ",", ";")
        
        strTemp = strHN & "," & strStreet & "," & strApt & "," & strLat & "," & strLong & "," & strCity & "," & strState
        strTemp = strTemp & "," & strZip & "," & strExchange & "," & strSA & "," & strBusiness
        Print #1, strTemp
        
        iCounter = iCounter + 1
    Next objBlock
    
    'MsgBox "Export Complete"
    Close #1
    
    If strItemResults = "" Then
        strItemResults = strBlock & " Exported/Found: " & iCounter & "/" & objSS.Count
    Else
        strItemResults = strItemResults & vbCr & strBlock & " Exported/Found: " & iCounter & "/" & objSS.Count
    End If
    
Exit_Sub:
    
    objSS.Clear
    objSS.Delete
End Sub

Private Sub CreateCustomerReport20(strBlock As String)
    Dim objSS As AcadSelectionSet
    Dim objBlock As AcadBlockReference
    Dim filterType, filterValue As Variant
    Dim grpCode(0) As Integer
    Dim grpValue(0) As Variant
    Dim objPoint As AcadPoint
    Dim vAttList As Variant
    Dim dPnt1(2), dPnt2(2) As Double
    
    Dim vTemp As Variant
    Dim strWO, strSA, strExchange As String
    Dim strHN, strApt, strStreet As String
    Dim strLat, strLong, strTemp As String
    Dim strCity, strState, strZip As String
    Dim strBusiness As String
    Dim vNE, vResult As Variant
    Dim iCounter As Integer
    
    Dim strBody As String
    
    iCounter = 0
    strWO = tbWO.Value
    strExchange = cbExchange.Value
    strSA = tbSA.Value
    
    Select Case strBlock
        Case "RESIDENCE", "RES"
            strFileName = strBaseName & "RES.csv"
        Case "BUSINESS"
            strFileName = strBaseName & "Business.csv"
        Case "SCHOOL"
            strFileName = strBaseName & "School.csv"
        Case "CHURCH"
            strFileName = strBaseName & "Church.csv"
        Case "TRLR"
            strFileName = strBaseName & "Trailer.csv"
        Case "MDU"
            strFileName = strBaseName & "MDU.csv"
        Case Else
            strFileName = strBaseName & "Other.csv"
    End Select

    grpCode(0) = 2
    grpValue(0) = "Customer"
    filterType = grpCode
    filterValue = grpValue
    
  On Error Resume Next
    
    'dPnt1(0) = vPnt1(0)
    'dPnt1(1) = vPnt1(1)
    'dPnt1(2) = vPnt1(2)
    
    'dPnt2(0) = vPnt2(0)
    'dPnt2(1) = vPnt2(1)
    'dPnt2(2) = vPnt2(2)
  
    Err = 0
    
    Set objSS = ThisDrawing.SelectionSets.Add("objSS")
    If Not Err = 0 Then
        Set objSS = ThisDrawing.SelectionSets.Item("objSS")
        Err = 0
    End If
    objSS.Select acSelectionSetWindow, vPnt1, vPnt2, filterType, filterValue
    If Not Err = 0 Then
        MsgBox "Error: " & Err.Number & vbCr & Err.Description
        Me.show
        Exit Sub
    End If
    
    'MsgBox "Customers Found: " & objSS.Count
    If objSS.Count < 1 Then GoTo Exit_Sub
    
    strBody = ""
    
    For Each objBlock In objSS
        vAttList = objBlock.GetAttributes
        
        If Not vAttList(0).TextString = strBlock Then GoTo Next_Customer
        
        vNE = TN83FtoLL(CDbl(objBlock.InsertionPoint(1)), CDbl(objBlock.InsertionPoint(0)))
        strLat = vNE(0)
        strLong = vNE(1)
        
        vResult = SeperateHouseNumber(CStr(vAttList(1).TextString))
        
        strHN = vResult(0)
        If UBound(vResult) > 0 Then
            strApt = vResult(1)
        Else
            strApt = ""
        End If
        
        strStreet = vAttList(2).TextString
        strCity = cbCity.Value
        strState = "TN"
        strZip = tbZipCode.Value
        strBusiness = Replace(vAttList(3).TextString, ",", ";")
        
        strTemp = strHN & "," & strStreet & "," & strApt & "," & strLat & "," & strLong & "," & strCity & "," & strState
        strTemp = strTemp & "," & strZip & "," & strExchange & "," & strSA & "," & strBusiness
        'Print #1, strTemp
        If strBody = "" Then
            strBody = strTemp
        Else
            strBody = strBody & vbCr & strTemp
        End If
        
        iCounter = iCounter + 1
        
Next_Customer:
    Next objBlock
    
    'MsgBox "Export Complete"
    If strBody = "" Then GoTo Exit_Sub
    
    Open strFileName For Output As #1
    
    Print #1, "House Number,Street,Apartment Number,Latitude,Longitude,City,State,Zip Code,Exchange,Service Area,Business Name"
    
    Print #1, strBody
    
    Close #1
    
    If strItemResults = "" Then
        strItemResults = strBlock & " Exported/Found: " & iCounter & "/" & objSS.Count
    Else
        strItemResults = strItemResults & vbCr & strBlock & " Exported/Found: " & iCounter & "/" & objSS.Count
    End If
    
Exit_Sub:
    
    objSS.Clear
    objSS.Delete
End Sub

Private Function SeperateHouseNumber(strText As String)
    Dim strChar As String
    Dim strHN, strApt As String
    Dim vResult As Variant
    Dim iCounter As Integer
    Dim i As Long
    
    iCounter = 1
    strHN = ""
    
    For i = 1 To Len(strText)
        strChar = Mid(strText, i, 1)
        Select Case strChar
            Case "0", "1", "2", "3", "4", "5", "6", "7", "8", "9"
                strHN = strHN & strChar
            Case Else
                GoTo Exit_Next
        End Select
    Next i
Exit_Next:
    strApt = Right(strText, Len(strText) - Len(strHN))
    strHN = strHN & "<<" & strApt
    
    vResult = Split(strHN, "<<")
    
    SeperateHouseNumber = vResult
End Function


Private Function TN83FtoLL(dNorth As Double, dEast As Double)
    Dim dLat, dLong, dDLat As Double
    Dim dDiffE, dEast0 As Double
    Dim dDiffN, dNorth0 As Double
    Dim dR, dCAR, dCA, dU, dK As Double
    Dim LL(2) As Double
    
    dEast = dEast * 0.3048006096
    dNorth = dNorth * 0.3048006096
    
    dDiffE = dEast - 600000
    dDiffN = dNorth - 166504.1691
    
    dR = 8842127.1422 - dDiffN
    dCAR = Atn(dDiffE / dR)
    dCA = dCAR * 180 / 3.14159265359
    dLong = -86 + dCA / 0.585439726459
    
    dU = dDiffN - dDiffE * Tan(dCAR / 2)
    dDLat = dU * (0.00000901305249 + dU * (-6.77268E-15 + dU * (-3.72351E-20 + dU * -9.2828E-28)))
    dLat = 35.8340607459 + dDLat
    
    dK = 0.999948401424 + (1.23188E-14 * dU * dU) + (4.54E-22 * dU * dU * dU)
    
    LL(0) = dLat
    LL(1) = dLong
    LL(2) = dK
    
    TN83FtoLL = LL
End Function

Attribute VB_Name = "TraceForm"
Attribute VB_Base = "0{22131F2A-7471-4381-9EC6-E776B518CD23}{FB41CA0B-0CA5-4A3C-861E-383FC338F3D2}"
Attribute VB_GlobalNameSpace = False
Attribute VB_Creatable = False
Attribute VB_PredeclaredId = True
Attribute VB_Exposed = False
Attribute VB_TemplateDerived = False
Attribute VB_Customizable = False

Private Sub cbQuit_Click()
    Me.Hide
End Sub

Private Sub cbTrace_Click()
    If tbName.Value = "" Then Exit Sub
    If tbCount.Value = "" Then Exit Sub
    
    Dim excelApp As Excel.Application
    Dim ws As Excel.Worksheet
    Dim fName As String
    Dim strPath, strTemp As String
    Dim lRow As Long
    Dim iI, iLines As Integer
    Dim strPole, strType As String
    
    Dim vTemp As Variant
    Dim strName, strCount As String
    Dim strCurrent, strNext As String
    Dim iCount As Integer
    Dim iRange(1) As Integer
    Dim vCounts, vFibers As Variant
    
    Me.Hide
  On Error Resume Next
    
    strName = tbName.Value
    iCount = CInt(tbCount.Value)
    
    If iCount = 0 Then GoTo Exit_Sub
    
    strPath = ThisDrawing.FullName
    strPath = Replace(strPath, ".dwg", ".xlsx")
    
    fName = Dir(strPath)
    If fName = "" Then
        MsgBox "There are no Records in folder."
        Me.show
        Exit Sub
    End If
    
    Set excelApp = CreateObject("Excel.Application")
    excelApp.Visible = False
    
    Err = 0
    Set wb = Excel.Workbooks.Open(strPath)
    If Not Err = 0 Then
        MsgBox "Error opening file"
        GoTo Exit_Sub
    End If
    
    lRow = 2
    While Not Sheets("Closures").Cells(lRow, 1).Value = ""
        Select Case Sheets("Closures").Cells(lRow, 2).Value
        'If Sheets("Cables").Cells(lRow, 2).Value = "CO" Then
            Case "CO", "FDH", "FBRTERM"
                If Sheets("Closures").Cells(lRow, 1).Value = strName Then
                    vTemp = Split(Sheets("Closures").Cells(lRow, 8).Value, "~")
                    vCounts = Split(vTemp(1), "-")
                    iRange(0) = CInt(vCounts(0)) - 1
                    If UBound(vCounts) < 1 Then
                        iRange(1) = vCounts(0) + 1
                    Else
                        iRange(1) = vCounts(1) + 1
                    End If
                
                    If iCount > iRange(0) And iCount < iRange(1) Then
                        lbList.AddItem "CO"
                        lbList.List(lbList.ListCount - 1, 1) = Sheets("Closures").Cells(lRow, 2).Value & Sheets("Closures").Cells(lRow, 3).Value
                        lbList.List(lbList.ListCount - 1, 3) = iCount
                        lbList.List(lbList.ListCount - 1, 4) = "0"
                    
                        strCurrent = vTemp(2)
                    
                        GoTo Get_Cables
                    End If
                End If
        End Select
        
        lRow = lRow + 1
    Wend
    
    MsgBox "No Origination Point Found."
    
    GoTo Exit_Sub
    
Get_Cables:

    '   Loop
        lRow = 2
        While Not Sheets("Cables").Cells(lRow, 1).Value = ""
            
            lRow = lRow + 1
        Wend
        
        
    '   End loop
    
Exit_Sub:
    ActiveWorkbook.Save
    ActiveWorkbook.Close
    Me.show
End Sub

Private Sub lbList_Click()

End Sub

Private Sub UserForm_Initialize()
    lbList.ColumnCount = 6
    lbList.ColumnWidths = "48;48;48;48;48;48"
End Sub

Attribute VB_Name = "UserForm1"
Attribute VB_Base = "0{541D761C-8D63-4F4C-9855-48CBECE097DE}{AAF3B26F-CFF4-48DC-907C-ECEFD093CD9C}"
Attribute VB_GlobalNameSpace = False
Attribute VB_Creatable = False
Attribute VB_PredeclaredId = True
Attribute VB_Exposed = False
Attribute VB_TemplateDerived = False
Attribute VB_Customizable = False

Private Sub cbAddClosure_Click()

End Sub

Private Sub cbGetCables_Click()
    Dim excelApp As Excel.Application
    Dim ws As Excel.Worksheet
    Dim fName As String
    Dim strPath, strTemp As String
    Dim strPole, strType As String
    Dim vTemp As Variant
    Dim lRow As Long
    Dim iI As Integer
    
    Me.Hide
  On Error Resume Next
    
    strPole = tbPole.Value
    
    strPath = ThisDrawing.FullName
    strPath = Replace(strPath, ".dwg", ".xlsx")
    
    fName = Dir(strPath)
    If fName = "" Then
        MsgBox "There are no Records in folder."
        Exit Sub
    End If
    
    Set excelApp = CreateObject("Excel.Application")
    excelApp.Visible = False
    
    Err = 0
    Set wb = Excel.Workbooks.Open(strPath)
    If Not Err = 0 Then
        MsgBox "Error opening file"
        GoTo Exit_Sub
    End If
    
    lbSplice.Clear
    
    lRow = 2
    While Not Sheets("Cables").Cells(lRow, 1).Value = ""
        If Sheets("Cables").Cells(lRow, 1).Value = strPole Then
            lbSplice.AddItem strPole
            lbSplice.List(lbSplice.ListCount - 1, 1) = Sheets("Cables").Cells(lRow, 2).Value
            
            strTemp = Sheets("Cables").Cells(lRow, 7).Value & "(" & Sheets("Cables").Cells(lRow, 8).Value
            strTemp = strTemp & ")" & Sheets("Cables").Cells(lRow, 9).Value
            lbSplice.List(lbSplice.ListCount - 1, 2) = strTemp
            
            vTemp = Split(Sheets("Cables").Cells(lRow, 10).Value, "-")
            lbSplice.List(lbSplice.ListCount - 1, 3) = vTemp(0)
            
            lbSplice.List(lbSplice.ListCount - 1, 4) = lRow
        End If
        
        lRow = lRow + 1
    Wend
    
    lRow = 2
    While Not Sheets("Cables").Cells(lRow, 1).Value = ""
        If Sheets("Cables").Cells(lRow, 2).Value = strPole Then
            lbSplice.AddItem Sheets("Cables").Cells(lRow, 1).Value
            lbSplice.List(lbSplice.ListCount - 1, 1) = strPole
            
            strTemp = Sheets("Cables").Cells(lRow, 7).Value & "(" & Sheets("Cables").Cells(lRow, 8).Value
            strTemp = strTemp & ")" & Sheets("Cables").Cells(lRow, 9).Value
            lbSplice.List(lbSplice.ListCount - 1, 2) = strTemp
            
            vTemp = Split(Sheets("Cables").Cells(lRow, 10).Value, "-")
            lbSplice.List(lbSplice.ListCount - 1, 3) = vTemp(0)
            
            lbSplice.List(lbSplice.ListCount - 1, 4) = lRow
        End If
        
        lRow = lRow + 1
    Wend
    
    
Exit_Sub:
    ActiveWorkbook.Save
    ActiveWorkbook.Close
    
    Me.show
End Sub

Private Sub cbQuit_Click()
    Me.Hide
End Sub

Private Sub cbUpdate_Click()
    Dim iFCount, iTCount As Integer
    Dim iI, iFFiber, iTFiber As Integer
    Dim i0, i1, i2, i3, i4, i5 As Integer
    Dim vLine As Variant
    
    iI = lbCounts.ListIndex
    i0 = CInt(tbC0.Value)
    i1 = CInt(tbC1.Value)
    If tbC2.Value = "" Then
        i2 = 0
    Else
        i2 = CInt(tbC2.Value)
    End If
    If tbC3.Value = "" Then
        i3 = 0
    Else
        i3 = CInt(tbC3.Value)
    End If
    i4 = CInt(tbC4.Value)
    i5 = CInt(tbC5.Value)
    
    vLine = Split(lbCounts.List(iI, 0), "-")
    iFFiber = CInt(vLine(0))
    
    If i0 = i1 Then
        lbCounts.List(iI, 2) = i0
        lbCounts.List(iI, 0) = iFFiber
        iFFiber = iFFiber + 1
    Else
        lbCounts.List(iI, 2) = i0 & "-" & i1
        iTFiber = iFFiber + i1 - i0
        lbCounts.List(iI, 0) = iFFiber & "-" & iTFiber
        iFFiber = iTFiber + 1
    End If
    
    If Not i3 = 0 Then
        lbCounts.AddItem "", iI + 1
        lbCounts.List(iI + 1, 1) = lbCounts.List(iI, 1)
        If i2 = i3 Then
            lbCounts.List(iI + 1, 2) = i2
            lbCounts.List(iI + 1, 0) = iFFiber
            iFFiber = iFFiber + 1
        Else
            lbCounts.List(iI + 1, 2) = i2 & "-" & i3
            iTFiber = iFFiber + i3 - i2
            lbCounts.List(iI + 1, 0) = iFFiber & "-" & iTFiber
            iFFiber = iTFiber + 1
        End If
        lbCounts.List(iI + 1, 3) = lbCounts.List(iI, 3)
        lbCounts.List(iI + 1, 4) = lbCounts.List(iI, 4)
        
        iI = iI + 1
    End If
    
    lbCounts.AddItem "", iI + 1
    lbCounts.List(iI + 1, 1) = lbCounts.List(iI, 1)
    If i4 = i5 Then
        lbCounts.List(iI + 1, 2) = i4
        lbCounts.List(iI + 1, 0) = iFFiber
    Else
        lbCounts.List(iI + 1, 2) = i4 & "-" & i5
        iTFiber = iFFiber + i5 - i4
        lbCounts.List(iI + 1, 0) = iFFiber & "-" & iTFiber
    End If
    lbCounts.List(iI + 1, 3) = lbCounts.List(iI, 3)
    lbCounts.List(iI + 1, 4) = lbCounts.List(iI, 4)
    
    tbC0.Value = ""
    tbC1.Value = ""
    tbC2.Value = ""
    tbC3.Value = ""
    tbC4.Value = ""
    tbC5.Value = ""
    cbUpdate.Enabled = False
    
    tbName.Value = ""
    cbUpdateName.Enabled = False
    
    cbUpdateRecord.Enabled = True
End Sub

Private Sub cbUpdateName_Click()
    lbCounts.List(lbCounts.ListIndex, 1) = tbName.Value
    
    tbC0.Value = ""
    tbC1.Value = ""
    tbC2.Value = ""
    tbC3.Value = ""
    tbC4.Value = ""
    tbC5.Value = ""
    cbUpdate.Enabled = False
    
    tbName.Value = ""
    cbUpdateName.Enabled = False
    
    cbUpdateRecord.Enabled = True
End Sub

Private Sub cbUpdateRecord_Click()
    Dim excelApp As Excel.Application
    Dim ws As Excel.Worksheet
    Dim fName As String
    Dim strPath, strTemp As String
    Dim lRow As Long
    Dim iI As Integer
    Dim strPole, strType As String
    Dim vTemp As Variant
    
    lRow = CLng(tbRow.Value)
    
    strPath = ThisDrawing.FullName
    strPath = Replace(strPath, ".dwg", ".xlsx")
    
    fName = Dir(strPath)
    If fName = "" Then
        MsgBox "There are no Records in folder."
        Exit Sub
    End If
    
    Set excelApp = CreateObject("Excel.Application")
    excelApp.Visible = False
    
    Err = 0
    Set wb = Excel.Workbooks.Open(strPath)
    If Not Err = 0 Then
        MsgBox "Error opening file"
        GoTo Exit_Sub
    End If
    
    vTemp = Split(Sheets("Cables").Cells(lRow, 10).Value, "-")
    Sheets("Cables").Cells(lRow, 10).Value = vTemp(0) & "-" & lbCounts.ListCount
    
    For iI = 0 To lbCounts.ListCount - 1
        strTemp = lbCounts.List(iI, 0) & "++" & lbCounts.List(iI, 1) & "~"
        strTemp = strTemp & lbCounts.List(iI, 2) & "~" & lbCounts.List(iI, 3) & "~"
        strTemp = strTemp & lbCounts.List(iI, 4)
        Sheets("Cables").Cells(lRow, 11 + iI).Value = strTemp
    Next iI
    
    cbUpdateRecord.Enabled = False
    
Exit_Sub:
    ActiveWorkbook.Save
    ActiveWorkbook.Close
End Sub

Private Sub Label10_Click()
    Dim entPole As AcadObject
    Dim objBlock As AcadBlockReference
    Dim vAttList, basePnt As Variant
    Dim strNext As String
    
    Me.Hide
  On Error Resume Next
    
    ThisDrawing.Utility.GetEntity entPole, basePnt, "Select Structure: "
    If TypeOf entPole Is AcadBlockReference Then
        Set objBlock = entPole
    Else
        MsgBox "Not a valid pole."
        GoTo Exit_Sub
    End If
    
    vAttList = objBlock.GetAttributes
    
    strNext = vAttList(0).TextString
    If Not Err = 0 Then GoTo Exit_Sub
    
    tbPole.Value = strNext
    
Exit_Sub:
    Me.show
End Sub

Private Sub lbCounts_Click()
    If cbUpdate.Enabled = True Then
        tbC1.Enabled = False
        'tbC2.Enabled = False
        tbC3.Enabled = False
        'tbC4.Enabled = False
        cbUpdate.Enabled = False
        
        tbName.Value = ""
        cbUpdateName.Enabled = False
        
        tbC0.Value = ""
        tbC1.Value = ""
        tbC2.Value = ""
        tbC3.Value = ""
        tbC4.Value = ""
        tbC5.Value = ""
    End If
End Sub

Private Sub lbCounts_DblClick(ByVal Cancel As MSForms.ReturnBoolean)
    If lbCounts.ListCount < 1 Then Exit Sub
    
    Dim vLine As Variant
    
    vLine = Split(lbCounts.List(lbCounts.ListIndex, 2), "-")
    
    If UBound(vLine) = 1 Then
        tbC0.Value = vLine(0)
        tbC1.Enabled = True
        'tbC2.Enabled = True
        tbC3.Enabled = True
        'tbC4.Enabled = True
        tbC5.Value = vLine(1)
    
        cbUpdate.Enabled = True
    End If
    
    tbName.Value = lbCounts.List(lbCounts.ListIndex, 1)
    cbUpdateName.Enabled = True
End Sub

Private Sub lbSplice_DblClick(ByVal Cancel As MSForms.ReturnBoolean)
    Dim excelApp As Excel.Application
    Dim ws As Excel.Worksheet
    Dim fName As String
    Dim strPath, strTemp As String
    Dim strPole, strType As String
    Dim vTemp, vLine As Variant
    Dim lRow As Long
    Dim iI As Integer
    
    Me.Hide
  On Error Resume Next
    
    lbCounts.Clear
    lRow = lbSplice.List(lbSplice.ListIndex, 4)
    tbRow.Value = lRow
    
    strPath = ThisDrawing.FullName
    strPath = Replace(strPath, ".dwg", ".xlsx")
    
    fName = Dir(strPath)
    If fName = "" Then
        MsgBox "There are no Records in folder."
        Exit Sub
    End If
    
    Set excelApp = CreateObject("Excel.Application")
    excelApp.Visible = False
    
    Err = 0
    Set wb = Excel.Workbooks.Open(strPath)
    If Not Err = 0 Then
        MsgBox "Error opening file"
        GoTo Exit_Sub
    End If
    
    vTemp = Split(Sheets("Cables").Cells(lRow, 10).Value, "-")
    'iI = CInt(vTemp(1))
    
    For iI = 1 To CInt(vTemp(1))
        vTemp = Split(Sheets("Cables").Cells(lRow, 10 + iI).Value, "++")
        lbCounts.AddItem vTemp(0)
        
        vLine = Split(vTemp(UBound(vTemp)), "~")
        lbCounts.List(lbCounts.ListCount - 1, 1) = vLine(0)
        lbCounts.List(lbCounts.ListCount - 1, 2) = vLine(1)
        lbCounts.List(lbCounts.ListCount - 1, 3) = vLine(2)
        lbCounts.List(lbCounts.ListCount - 1, 4) = vLine(3)
    Next iI
    
Exit_Sub:
    ActiveWorkbook.Save
    ActiveWorkbook.Close
    
    Me.show
End Sub

Private Sub tbC1_Change()
    Dim iFiber As Integer
    
    If tbC1.Value = "" Then
        tbC4.Value = ""
        Exit Sub
    End If
    
    iFiber = CInt(tbC1.Value)
    
    If iFiber < CInt(tbC0.Value) Then
        'tbC1.Value = ""
        Exit Sub
    End If
    
    If tbC3.Value = "" Then
        If iFiber > CInt(tbC5.Value) - 1 Then
            tbC1.Value = ""
            tbC2.Value = ""
            Exit Sub
        End If
        tbC4.Value = iFiber + 1
    Else
        If iFiber > CInt(tbC3.Value) - 1 Then
            tbC1.Value = ""
            Exit Sub
        End If
        tbC2.Value = iFiber + 1
    End If
    
    If tbC2.Value = "" Then
        tbC4.Value = iFiber + 1
    End If
End Sub

Private Sub tbC3_Change()
    Dim iFiber As Integer
    
    If tbC3.Value = "" Then
        tbC4.Value = ""
        Exit Sub
    End If
    
    iFiber = CInt(tbC3.Value)
    
    If iFiber > CInt(tbC5.Value) - 1 Then
        tbC3.Value = ""
        Exit Sub
    End If
    tbC4.Value = iFiber + 1
    
    If tbC1.Value = "" Then
        If iFiber < CInt(tbC0.Value) + 1 Then
            'tbC3.Value = ""
            Exit Sub
        End If
        tbC2.Value = iFiber
        tbC1.Value = iFiber - 1
    Else
        If iFiber < CInt(tbC1.Value) + 1 Then
            tbC3.Value = ""
            Exit Sub
        End If
        tbC2.Value = CInt(tbC1.Value) + 1
    End If
End Sub

Private Sub UserForm_Initialize()
    lbCounts.ColumnCount = 5
    lbCounts.ColumnWidths = "48;48;48;72;36"
    
    lbSplice.ColumnCount = 5
    lbSplice.ColumnWidths = "48;48;72;48;36"
End Sub

Attribute VB_Name = "xxCountsAssignForm"
Attribute VB_Base = "0{835EDC76-684F-4A2B-B4FB-BC07F363105B}{EA117882-3E6F-4D45-B8FD-58B4EBC36ACA}"
Attribute VB_GlobalNameSpace = False
Attribute VB_Creatable = False
Attribute VB_PredeclaredId = True
Attribute VB_Exposed = False
Attribute VB_TemplateDerived = False
Attribute VB_Customizable = False
Private Sub cbAddClosure_Click()
    If lbCounts.ListCount < 1 Then Exit Sub
    
    Dim iSelected As Integer
    
    iSelected = 0
    
    For i = 0 To lbCounts.ListCount - 1
        If lbCounts.Selected(i) Then iSelected = iSelected + 1
    Next i
    If iSelected = 0 Then Exit Sub
    
    Dim strClosure As String
    Dim iIndex As Integer
    
    strClosure = tbPole.Value & " " & tbPosition.Value
    
    Me.Hide
    
    Load NewClosureForm
            
    NewClosureForm.tbPosition.Value = tbPosition.Value
    NewClosureForm.tbJob.Value = tbJob.Value
    NewClosureForm.tbPole.Value = strClosure
    
    If cbType.Value = "CO" Then
        NewClosureForm.cbType.Value = "HACO"
    Else
        NewClosureForm.cbType.Value = "HBFO"
    End If
            
    NewClosureForm.cbSize.Value = cbSize.Value
    
    For i = 0 To lbCounts.ListCount - 1
        If lbCounts.Selected(i) Then
            lbCounts.List(i, 3) = strClosure
            
            NewClosureForm.lbSplice.AddItem lbCounts.List(i, 0)
            iIndex = NewClosureForm.lbSplice.ListCount - 1
            
            NewClosureForm.lbSplice.List(iIndex, 1) = lbCounts.List(i, 1)
            NewClosureForm.lbSplice.List(iIndex, 2) = lbCounts.List(i, 2)
            NewClosureForm.lbSplice.List(iIndex, 3) = lbCounts.List(i, 3)
            NewClosureForm.lbSplice.List(iIndex, 4) = lbCounts.List(i, 4)
        End If
    Next i
    
    NewClosureForm.show
    
    Unload NewClosureForm
    
    cbUpdateRecord.Enabled = True
    
    Me.show
End Sub

Private Sub cbAddToPole_Click()
    Dim excelApp As Excel.Application
    Dim ws As Excel.Worksheet
    Dim fName As String
    Dim strPath, strTemp As String
    Dim entPole As AcadObject
    Dim objBlock As AcadBlockReference
    Dim vAttList, basePnt As Variant
    Dim lRow As Long
    Dim iI As Integer
    Dim strPole, strType As String
    
    Me.Hide
  On Error Resume Next
    
    ThisDrawing.Utility.GetEntity entPole, basePnt, "Select Pole: "
    If TypeOf entPole Is AcadBlockReference Then
        Set objBlock = entPole
    Else
        MsgBox "Not a valid pole."
        Me.show
        Exit Sub
    End If
    
    Select Case objBlock.Name
        Case "iPole"
            strType = "Aerial"
        Case Else
            strType = "Buried"
    End Select
    
    'If Not objBlock.Name = "iPole" Then
        'Me.show
        'Exit Sub
    'End If
    
    vAttList = objBlock.GetAttributes
    strPole = vAttList(0).TextString
    
    strPath = ThisDrawing.FullName
    strPath = Replace(strPath, ".dwg", ".xlsx")
    
    fName = Dir(strPath)
    If fName = "" Then
        MsgBox "There are no Records in folder."
        Exit Sub
    End If
    
    Set excelApp = CreateObject("Excel.Application")
    excelApp.Visible = False
    
    Err = 0
    Set wb = Excel.Workbooks.Open(strPath)
    If Not Err = 0 Then
        MsgBox "Error opening file"
        GoTo Exit_Sub
    End If
    
    lRow = 2
    While Not Sheets("Cables").Cells(lRow, 1).Value = ""
        If Sheets("Cables").Cells(lRow, 1).Value = strPole Then GoTo Found_Row
        lRow = lRow + 1
    Wend
    
Found_Row:

    tbRow.Value = lRow
    
    Sheets("Cables").Cells(lRow, 1).Value = strPole
    Sheets("Cables").Cells(lRow, 2).Value = strType
    Sheets("Cables").Cells(lRow, 3).Value = tbNextPole.Value
    Sheets("Cables").Cells(lRow, 4).Value = tbLength.Value
    Sheets("Cables").Cells(lRow, 5).Value = tbJob.Value
    Sheets("Cables").Cells(lRow, 7).Value = cbType.Value
    Sheets("Cables").Cells(lRow, 8).Value = cbSize.Value
    Sheets("Cables").Cells(lRow, 9).Value = cbSuffix.Value
    Sheets("Cables").Cells(lRow, 10).Value = tbPosition.Value & "-" & lbCounts.ListCount
    
    For iI = 0 To lbCounts.ListCount - 1
        strTemp = lbCounts.List(iI, 0) & "~" & lbCounts.List(iI, 1) & "~"
        strTemp = strTemp & lbCounts.List(iI, 2) & "~" & lbCounts.List(iI, 3) & "~"
        strTemp = strTemp & lbCounts.List(iI, 4)
        Sheets("Cables").Cells(lRow, 11 + iI).Value = strTemp
    Next iI
    
    cbUpdateRecord.Enabled = True
    
Exit_Sub:
    ActiveWorkbook.Save
    ActiveWorkbook.Close
    
    Me.show
End Sub

Private Sub cbGetCable_Click()
    Dim entPole As AcadObject
    Dim vAttList, basePnt As Variant
    Dim objBlock As AcadBlockReference
    Dim vLine, vItem, vTemp As Variant
    Dim strTemp, strFiber As String
    Dim strJob, strCable, strCount, strToPnt As String
    Dim iFFiber, iTFiber As Integer
    Dim iFCount, iTCount As Integer
    
    Me.Hide
  On Error Resume Next
    
    ThisDrawing.Utility.GetEntity entPole, basePnt, "Select Callout: "
    If TypeOf entPole Is AcadBlockReference Then
        Set objBlock = entPole
    Else
        MsgBox "Not a valid pole."
        Exit Sub
    End If
    
    If Not objBlock.Name = "CableCounts" Then
        Me.show
        Exit Sub
    End If
    
    lbCounts.Clear
    
    iFFiber = 1
    vTemp = Split(ThisDrawing.Name, " ")
    strJob = Replace(vTemp(0), ".dwg", "")
    
    vAttList = objBlock.GetAttributes
    
    vItem = Split(vAttList(1).TextString, "(")
    cbType.Value = vItem(0)
    vTemp = Split(vItem(1), ")")
    cbSize.Value = vTemp(0)
    cbSuffix.Value = vTemp(1)
        
    Select Case vTemp(1)
        Case ""
            cbSuffix.Value = "E"
            tbPosition.Value = "A2"
        Case "E"
            tbPosition.Value = "A2"
        Case Else
            tbPosition.Value = "A1"
    End Select
    
    vLine = Split(vAttList(0).TextString, "\P")
    
    For i = LBound(vLine) To UBound(vLine)
        
        vItem = Split(vLine(i), ": ")
        strCable = vItem(0)
        strCount = vItem(1)
        
        vTemp = Split(strCount, "-")
        iFCount = CInt(vTemp(0))
        If UBound(vTemp) > 0 Then
            iTCount = CInt(vTemp(1))
        Else
            iTCount = iFCount
        End If
        
        iTFiber = iFFiber + iTCount - iFCount
        If iTFiber = iFFiber Then
            strFiber = iFFiber
        Else
            strFiber = iFFiber & "-" & iTFiber
        End If
        
        lbCounts.AddItem strFiber
        lbCounts.List(lbCounts.ListCount - 1, 1) = strCable
        lbCounts.List(lbCounts.ListCount - 1, 2) = strCount
        lbCounts.List(lbCounts.ListCount - 1, 3) = strToPnt
        lbCounts.List(lbCounts.ListCount - 1, 4) = strJob
        
        iFFiber = iTFiber + 1
    Next i
        
    Me.show
End Sub

Private Sub cbGetPole_Click()
    Dim excelApp As Excel.Application
    Dim ws As Excel.Worksheet
    Dim fName As String
    Dim strPath, strTemp As String
    Dim entPole As AcadObject
    Dim objBlock As AcadBlockReference
    Dim vAttList, basePnt As Variant
    Dim lRow As Long
    Dim iI, iLines As Integer
    Dim strPole, strType As String
    Dim vTemp As Variant
    
    Me.Hide
  On Error Resume Next
    
    ThisDrawing.Utility.GetEntity entPole, basePnt, "Select Pole: "
    If TypeOf entPole Is AcadBlockReference Then
        Set objBlock = entPole
    Else
        MsgBox "Not a valid pole."
        Me.show
        Exit Sub
    End If
    
    'Select Case objBlock.Name
        'Case "iPole"
            'strType = "Aerial"
        'Case Else
            'strType = "Buried"
    'End Select
    
    vAttList = objBlock.GetAttributes
    strPole = vAttList(0).TextString
    
    strPath = ThisDrawing.FullName
    strPath = Replace(strPath, ".dwg", ".xlsx")
    
    fName = Dir(strPath)
    If fName = "" Then
        MsgBox "There are no Records in folder."
        Me.show
        Exit Sub
    End If
    
    Set excelApp = CreateObject("Excel.Application")
    excelApp.Visible = False
    
    Err = 0
    Set wb = Excel.Workbooks.Open(strPath)
    If Not Err = 0 Then
        MsgBox "Error opening file"
        GoTo Exit_Sub
    End If
    
    lRow = 2
    While Not Sheets("Cables").Cells(lRow, 1).Value = ""
        If Sheets("Cables").Cells(lRow, 1).Value = strPole Then
            'MsgBox "Found Pole"
            tbRow.Value = lRow
            
            tbPole.Value = Sheets("Cables").Cells(lRow, 1).Value
            tbNextPole.Value = Sheets("Cables").Cells(lRow, 3).Value
            tbLength.Value = Sheets("Cables").Cells(lRow, 4).Value
            tbJob.Value = Sheets("Cables").Cells(lRow, 5).Value
            cbType.Value = Sheets("Cables").Cells(lRow, 7).Value
            cbSize.Value = Sheets("Cables").Cells(lRow, 8).Value
            cbSuffix.Value = Sheets("Cables").Cells(lRow, 9).Value
            vTemp = Split(Sheets("Cables").Cells(lRow, 10).Value, "-")
            tbPosition.Value = vTemp(0)
            iLines = CInt(vTemp(1))
            
            lbCounts.Clear
            
            For iI = 0 To iLines - 1
                strTemp = Sheets("Cables").Cells(lRow, 11 + iI).Value
                vTemp = Split(strTemp, "~")
                
                lbCounts.AddItem vTemp(0)
                lbCounts.List(lbCounts.ListCount - 1, 1) = vTemp(1)
                lbCounts.List(lbCounts.ListCount - 1, 2) = vTemp(2)
                lbCounts.List(lbCounts.ListCount - 1, 3) = vTemp(3)
                lbCounts.List(lbCounts.ListCount - 1, 4) = vTemp(4)
            Next iI
            
            GoTo Exit_Sub
        End If
        
        lRow = lRow + 1
    Wend
    
    cbUpdateRecord.Enabled = True
    
    'For iI = 0 To lbCounts.ListCount - 1
        'strTemp = lbCounts.List(iI, 0) & "~" & lbCounts.List(iI, 1) & "~"
        'strTemp = strTemp & lbCounts.List(iI, 2) & "~" & lbCounts.List(iI, 3) & "~"
        'strTemp = strTemp & lbCounts.List(iI, 4)
        'Sheets("Cables").Cells(lRow, 11 + iI).Value = strTemp
    'Next iI
    
Exit_Sub:
    ActiveWorkbook.Save
    ActiveWorkbook.Close
    Me.show
End Sub

Private Sub cbNext_Click()
    Dim iOffset, iIndex As Integer
    Dim vC, vP As Variant
    Dim iC(1), iP(1) As Integer
    
    tbPole.Value = tbNextPole.Value
    tbLength.Value = ""
    tbNextPole.Value = ""
    iOffset = 0
    
    For i = 0 To lbCounts.ListCount - 1
        If Not lbCounts.List(i, 3) = tbPole.Value Then
            lbCounts.List(i, 1) = "XD"
            lbCounts.List(i, 2) = lbCounts.List(i, 0)
        End If
        lbCounts.List(i, 3) = ""
    Next i
    
    For i = 1 To lbCounts.ListCount - 1
        iIndex = i - iOffset
        If lbCounts.List(iIndex, 1) = lbCounts.List(iIndex - 1, 1) Then
            vC = Split(lbCounts.List(iIndex, 2), "-")
            vP = Split(lbCounts.List(iIndex - 1, 2), "-")
            iC(0) = CInt(vC(0))
            If UBound(vC) < 1 Then
                iC(1) = iC(0)
            Else
                iC(1) = CInt(vC(1))
            End If
            
            iP(0) = CInt(vP(0))
            If UBound(vP) < 1 Then
                iP(1) = iP(0)
            Else
                iP(1) = CInt(vP(1))
            End If
            
            If iC(0) = iP(1) + 1 Then
                lbCounts.List(iIndex - 1, 2) = iP(0) & "-" & iC(1)
                
                vC = Split(lbCounts.List(iIndex, 0), "-")
                vP = Split(lbCounts.List(iIndex - 1, 0), "-")
                
                lbCounts.List(iIndex - 1, 0) = vP(0) & "-"
                If UBound(vC) < 1 Then
                    lbCounts.List(iIndex - 1, 0) = lbCounts.List(iIndex - 1, 0) & vC(0)
                Else
                    lbCounts.List(iIndex - 1, 0) = lbCounts.List(iIndex - 1, 0) & vC(1)
                End If
                
                lbCounts.RemoveItem i
                iOffset = iOffset + 1
            End If
        End If
        lbCounts.List(i - iOffset, 3) = ""
    Next i
    
    cbUpdateRecord.Enabled = False
    
End Sub

Private Sub cbQuit_Click()
    Me.Hide
End Sub

Private Sub cbType_Change()
    cbSuffix.Clear
    
    Select Case cbType.Value
        Case "CO"
            cbSuffix.AddItem ""
            cbSuffix.AddItem "E"
            cbSuffix.AddItem "6M"
            cbSuffix.AddItem "6M-EHS"
            cbSuffix.AddItem "10M"
            cbSuffix.AddItem "16M"
        Case "BFO"
            cbSuffix.AddItem ""
            cbSuffix.AddItem "I"
        Case "UO"
            cbSuffix.AddItem ""
    End Select
End Sub

Private Sub cbUpdate_Click()
    Dim iFCount, iTCount As Integer
    Dim iI, iFFiber, iTFiber As Integer
    Dim i0, i1, i2, i3, i4, i5 As Integer
    Dim vLine As Variant
    
    iI = lbCounts.ListIndex
    i0 = CInt(tbC0.Value)
    i1 = CInt(tbC1.Value)
    If tbC2.Value = "" Then
        i2 = 0
    Else
        i2 = CInt(tbC2.Value)
    End If
    If tbC3.Value = "" Then
        i3 = 0
    Else
        i3 = CInt(tbC3.Value)
    End If
    i4 = CInt(tbC4.Value)
    i5 = CInt(tbC5.Value)
    
    vLine = Split(lbCounts.List(iI, 0), "-")
    iFFiber = CInt(vLine(0))
    
    If i0 = i1 Then
        lbCounts.List(iI, 2) = i0
        lbCounts.List(iI, 0) = iFFiber
        iFFiber = iFFiber + 1
    Else
        lbCounts.List(iI, 2) = i0 & "-" & i1
        iTFiber = iFFiber + i1 - i0
        lbCounts.List(iI, 0) = iFFiber & "-" & iTFiber
        iFFiber = iTFiber + 1
    End If
    
    If Not i3 = 0 Then
        lbCounts.AddItem "", iI + 1
        lbCounts.List(iI + 1, 1) = lbCounts.List(iI, 1)
        If i2 = i3 Then
            lbCounts.List(iI + 1, 2) = i2
            lbCounts.List(iI + 1, 0) = iFFiber
            iFFiber = iFFiber + 1
        Else
            lbCounts.List(iI + 1, 2) = i2 & "-" & i3
            iTFiber = iFFiber + i3 - i2
            lbCounts.List(iI + 1, 0) = iFFiber & "-" & iTFiber
            iFFiber = iTFiber + 1
        End If
        lbCounts.List(iI + 1, 3) = lbCounts.List(iI, 3)
        lbCounts.List(iI + 1, 4) = lbCounts.List(iI, 4)
        
        iI = iI + 1
    End If
    
    lbCounts.AddItem "", iI + 1
    lbCounts.List(iI + 1, 1) = lbCounts.List(iI, 1)
    If i4 = i5 Then
        lbCounts.List(iI + 1, 2) = i4
        lbCounts.List(iI + 1, 0) = iFFiber
    Else
        lbCounts.List(iI + 1, 2) = i4 & "-" & i5
        iTFiber = iFFiber + i5 - i4
        lbCounts.List(iI + 1, 0) = iFFiber & "-" & iTFiber
    End If
    lbCounts.List(iI + 1, 3) = lbCounts.List(iI, 3)
    lbCounts.List(iI + 1, 4) = lbCounts.List(iI, 4)
    
    tbC0.Value = ""
    tbC1.Value = ""
    tbC2.Value = ""
    tbC3.Value = ""
    tbC4.Value = ""
    tbC5.Value = ""
End Sub

Private Sub cbUpdateRecord_Click()
    Dim excelApp As Excel.Application
    Dim ws As Excel.Worksheet
    Dim fName As String
    Dim strPath, strTemp As String
    Dim lRow As Long
    Dim iI As Integer
    Dim strPole, strType As String
    
    strPole = tbPole.Value
    
    strPath = ThisDrawing.FullName
    strPath = Replace(strPath, ".dwg", ".xlsx")
    
    fName = Dir(strPath)
    If fName = "" Then
        MsgBox "There are no Records in folder."
        Exit Sub
    End If
    
    Set excelApp = CreateObject("Excel.Application")
    excelApp.Visible = False
    
    Err = 0
    Set wb = Excel.Workbooks.Open(strPath)
    If Not Err = 0 Then
        MsgBox "Error opening file"
        GoTo Exit_Sub
    End If
    
    lRow = CInt(tbRow.Value)
    
    Sheets("Cables").Cells(lRow, 1).Value = strPole
    Sheets("Cables").Cells(lRow, 2).Value = strType
    Sheets("Cables").Cells(lRow, 3).Value = lbCounts.List(iI, 3)
    Sheets("Cables").Cells(lRow, 4).Value = tbLength.Value
    Sheets("Cables").Cells(lRow, 5).Value = tbJob.Value
    Sheets("Cables").Cells(lRow, 7).Value = cbType.Value
    Sheets("Cables").Cells(lRow, 8).Value = cbSize.Value
    Sheets("Cables").Cells(lRow, 9).Value = cbSuffix.Value
    Sheets("Cables").Cells(lRow, 10).Value = tbPosition.Value & "-" & lbCounts.ListCount
    
    For iI = 0 To lbCounts.ListCount - 1
        strTemp = lbCounts.List(iI, 0) & "~" & lbCounts.List(iI, 1) & "~"
        strTemp = strTemp & lbCounts.List(iI, 2) & "~" & lbCounts.List(iI, 3) & "~"
        strTemp = strTemp & lbCounts.List(iI, 4)
        Sheets("Cables").Cells(lRow, 11 + iI).Value = strTemp
    Next iI
    
    cbUpdateRecord.Enabled = False
    
Exit_Sub:
    ActiveWorkbook.Save
    ActiveWorkbook.Close
End Sub

Private Sub Label11_Click()
    Dim entPole As AcadObject
    Dim objBlock As AcadBlockReference
    Dim vAttList, basePnt As Variant
    
    Me.Hide
  On Error Resume Next
    
    ThisDrawing.Utility.GetEntity entPole, basePnt, "Select Cable Span: "
    If TypeOf entPole Is AcadBlockReference Then
        Set objBlock = entPole
    Else
        MsgBox "Not a valid pole."
        Exit Sub
    End If
    
    If Not objBlock.Name = "cable_span" Then
        Me.show
        Exit Sub
    End If
    
    vAttList = objBlock.GetAttributes
    
    tbLength.Value = Replace(vAttList(2).TextString, "'", "")
    
    Me.show
End Sub

Private Sub Label14_Click()
    Dim entPole As AcadObject
    Dim objBlock As AcadBlockReference
    Dim vAttList, basePnt As Variant
    Dim strNext As String
    
    Me.Hide
  On Error Resume Next
    
    ThisDrawing.Utility.GetEntity entPole, basePnt, "Select Structure: "
    If TypeOf entPole Is AcadBlockReference Then
        Set objBlock = entPole
    Else
        MsgBox "Not a valid pole."
        GoTo Exit_Sub
    End If
    
    vAttList = objBlock.GetAttributes
    
    strNext = vAttList(0).TextString
    If Not Err = 0 Then GoTo Exit_Sub
    
    tbNextPole.Value = strNext
    
    For i = 0 To lbCounts.ListCount - 1
        If lbCounts.List(i, 3) = "" Then lbCounts.List(i, 3) = strNext
        If lbCounts.List(i, 3) = tbPole.Value Then lbCounts.List(i, 3) = strNext
    Next i
    
Exit_Sub:
    Me.show
End Sub

Private Sub Label4_Click()
    Dim entPole As AcadObject
    Dim vAttList, basePnt As Variant
    Dim objBlock As AcadBlockReference
    Dim strPnt As String
    Dim iCount As Integer
    
    Me.Hide
  On Error Resume Next
    
    ThisDrawing.Utility.GetEntity entPole, basePnt, "Select Next Point: "
    If TypeOf entPole Is AcadBlockReference Then
        Set objBlock = entPole
    Else
        MsgBox "Not a valid pole."
        Exit Sub
    End If
    
    Err = 0
    vAttList = objBlock.GetAttributes
    If Not Err = 0 Then
        Me.show
        Exit Sub
    End If
    
    If UBound(vAttList) < 0 Then
        Me.show
        Exit Sub
    End If
    
    iCount = 0
    strPnt = vAttList(0).TextString
    
    For i = 0 To lbCounts.ListCount - 1
        If lbCounts.Selected(i) Then
            lbCounts.List(i, 3) = strPnt
            iCount = iCount + 1
        End If
    Next i
    
    If iCount = 0 Then
        For i = 0 To lbCounts.ListCount - 1
            lbCounts.List(i, 3) = strPnt
        Next i
    End If
    
    If tbNextPole.Value = "" Then tbNextPole.Value = strPnt
        
    Me.show
End Sub

Private Sub lbCounts_Click()
    If cbUpdate.Enabled = True Then
        tbC1.Enabled = False
        'tbC2.Enabled = False
        tbC3.Enabled = False
        'tbC4.Enabled = False
        cbUpdate.Enabled = False
        
        tbC0.Value = ""
        tbC1.Value = ""
        tbC2.Value = ""
        tbC3.Value = ""
        tbC4.Value = ""
        tbC5.Value = ""
    End If
End Sub

Private Sub lbCounts_DblClick(ByVal Cancel As MSForms.ReturnBoolean)
    If lbCounts.ListCount < 1 Then Exit Sub
    
    Dim vLine As Variant
    
    vLine = Split(lbCounts.List(lbCounts.ListIndex, 2), "-")
    
    If UBound(vLine) = 1 Then
        tbC0.Value = vLine(0)
        tbC1.Enabled = True
        'tbC2.Enabled = True
        tbC3.Enabled = True
        'tbC4.Enabled = True
        tbC5.Value = vLine(1)
    
        cbUpdate.Enabled = True
    End If
End Sub

Private Sub tbC1_Change()
    Dim iFiber As Integer
    
    If tbC1.Value = "" Then
        tbC4.Value = ""
        Exit Sub
    End If
    
    iFiber = CInt(tbC1.Value)
    
    If iFiber < CInt(tbC0.Value) Then
        'tbC1.Value = ""
        Exit Sub
    End If
    
    If tbC3.Value = "" Then
        If iFiber > CInt(tbC5.Value) - 1 Then
            tbC1.Value = ""
            tbC2.Value = ""
            Exit Sub
        End If
        tbC4.Value = iFiber + 1
    Else
        If iFiber > CInt(tbC3.Value) - 1 Then
            tbC1.Value = ""
            Exit Sub
        End If
        tbC2.Value = iFiber + 1
    End If
    
    If tbC2.Value = "" Then
        tbC4.Value = iFiber + 1
    End If
End Sub

Private Sub tbC3_Change()
    Dim iFiber As Integer
    
    If tbC3.Value = "" Then
        tbC4.Value = ""
        Exit Sub
    End If
    
    iFiber = CInt(tbC3.Value)
    
    If iFiber > CInt(tbC5.Value) - 1 Then
        tbC3.Value = ""
        Exit Sub
    End If
    tbC4.Value = iFiber + 1
    
    If tbC1.Value = "" Then
        If iFiber < CInt(tbC0.Value) + 1 Then
            'tbC3.Value = ""
            Exit Sub
        End If
        tbC2.Value = iFiber
        tbC1.Value = iFiber - 1
    Else
        If iFiber < CInt(tbC1.Value) + 1 Then
            tbC3.Value = ""
            Exit Sub
        End If
        tbC2.Value = CInt(tbC1.Value) + 1
    End If
End Sub

Private Sub UserForm_Initialize()
    lbCounts.ColumnCount = 5
    lbCounts.ColumnWidths = "48;48;48;72;36"
    
    cbType.AddItem ""
    cbType.AddItem "CO"
    cbType.AddItem "BFO"
    cbType.AddItem "UO"
    
    cbSize.AddItem ""
    cbSize.AddItem "12"
    cbSize.AddItem "24"
    cbSize.AddItem "36"
    cbSize.AddItem "48"
    cbSize.AddItem "72"
    cbSize.AddItem "96"
    cbSize.AddItem "144"
    cbSize.AddItem "216"
    cbSize.AddItem "288"
    cbSize.AddItem "360"
    cbSize.AddItem "432"
    
    Dim strDWG As String
    
    strDWG = Replace(ThisDrawing.Name, ".dwg", "")
    tbJob.Value = strDWG
End Sub

Attribute VB_Name = "xxxCountsForm"
Attribute VB_Base = "0{AC27BB34-88FC-4A2D-8D5E-FB58E03E7262}{F68170AA-3850-41BA-9322-587DF08EBB5E}"
Attribute VB_GlobalNameSpace = False
Attribute VB_Creatable = False
Attribute VB_PredeclaredId = True
Attribute VB_Exposed = False
Attribute VB_TemplateDerived = False
Attribute VB_Customizable = False
Private Sub cbQuit_Click()
    Me.Hide
End Sub

Private Sub UserForm_Initialize()
    lbMain.ColumnCount = 2
    lbMain.ColumnWidths = "192;192"
    
    lbMain.AddItem "F1000: 1-108 F1025A/2 1999-100"
    lbMain.AddItem "F1000: 109-140 F1025A/2 1999-100"
    lbMain.List(lbMain.ListCount - 1, 1) = "F1025: 1-32 F1025A/2 2000-001"
    lbMain.AddItem "F1000: 141-144 F1025A/2 1999-100"
End Sub
