Attribute VB_Name = "AJPiUFDraw"
Attribute VB_Base = "0{FCFB3D2A-A0FA-1068-A738-08002B3371B5}"
Attribute VB_GlobalNameSpace = False
Attribute VB_Creatable = False
Attribute VB_PredeclaredId = False
Attribute VB_Exposed = True
Attribute VB_TemplateDerived = False
Attribute VB_Customizable = False
Option Explicit

Private m_frmUFCanvas As MSForms.UserForm
Private m_objCanvas As Object
Private m_shtHolder As Worksheet
Private m_blnUseUF As Boolean
Public Function Box(Left As Single, Top As Single, Width As Single, Height As Single) As Shape
'
' Add a box to the drawing
'
    On Error GoTo ErrBox
    Set Box = m_shtHolder.Shapes.AddShape(msoShapeRectangle, Left, Top, Width, Height)
    Exit Function
ErrBox:
    Set Box = Nothing
    Exit Function
End Function
Public Sub CleanCanvas()
'
' Clear both userform and temporary work sheet
'
    On Error Resume Next
    m_ClearHolder
    WipeCanvas
End Sub
'Public Function TextEffect(Left As Single, Top As Single, _
'                           Effect As MsoPresetTextEffect, Text As String, _
'                           Optional FontName As String = "Arial", _
'                           Optional FontSize As Single = 10, _
'                           Optional FontBold As MsoTriState = msoFalse, _
'                           Optional FontItalic As MsoTriState = msoFalse) As Shape
''
'' Add a Wordart to the drawing
''
'    On Error GoTo ErrTextEffect
'    Set TextEffect = m_shtHolder.Shapes.AddTextEffect(Effect, Text, _
'         FontName, FontSize, FontBold, FontItalic, Left, Top)
'    Exit Function
'ErrTextEffect:
'    Set TextEffect = Nothing
'    Exit Function
'End Function
Public Function Curve(Xs() As Single, Ys() As Single) As Shape
'
' Add a curve to the drawing
'
    Dim intIndex As Integer
    
    On Error GoTo ErrCurve
    With m_shtHolder.Shapes.BuildFreeform(msoEditingAuto, Xs(LBound(Xs)), Ys(LBound(Ys)))
        For intIndex = LBound(Xs) + 1 To UBound(Xs)
            .AddNodes msoSegmentCurve, msoEditingAuto, Xs(intIndex), Ys(intIndex)
        Next
        Set Curve = .ConvertToShape
    End With
    Exit Function
ErrCurve:
    Set Curve = Nothing
    Exit Function
End Function
Public Function FreeForm(Xs() As Single, Ys() As Single, Closed As Boolean) As Shape
'
' Add a Freeform to the drawing
'
    Dim intIndex As Integer
        
    On Error GoTo ErrFreeForm
    With m_shtHolder.Shapes.BuildFreeform(msoEditingAuto, Xs(LBound(Xs)), Ys(LBound(Ys)))
        For intIndex = LBound(Xs) + 1 To UBound(Xs)
            .AddNodes msoSegmentLine, msoEditingAuto, Xs(intIndex), Ys(intIndex)
        Next
        If Closed Then
            .AddNodes msoSegmentLine, msoEditingAuto, Xs(LBound(Xs)), Ys(LBound(Ys))
        End If
        Set FreeForm = .ConvertToShape
    End With
    Exit Function
ErrFreeForm:
    Set FreeForm = Nothing
    Exit Function
End Function
Public Function Oval(CenterX As Single, CenterY As Single, RadiusX As Single, RadiusY As Single) As Shape
'
' Add a circle to the drawing
'
    Dim Left As Single
    Dim Top As Single
    Dim Width As Single
    Dim Height As Single
    
    On Error GoTo ErrOval
    Left = CenterX - RadiusX
    Top = CenterY - RadiusY
    Width = RadiusX * 2
    Height = RadiusY * 2
    Set Oval = m_shtHolder.Shapes.AddShape(msoShapeOval, Left, Top, Width, Height)
    Exit Function
ErrOval:
    Set Oval = Nothing
    Exit Function
End Function
Public Function Round(CenterX As Single, CenterY As Single, Radius As Single) As Shape
'
' Add a circle to the drawing
'
    Dim Left As Single
    Dim Top As Single
    Dim Width As Single
    Dim Height As Single
    
    On Error GoTo ErrRound
    Left = CenterX - Radius
    Top = CenterY - Radius
    Width = Radius * 2
    Height = Radius * 2
    Set Round = m_shtHolder.Shapes.AddShape(msoShapeOval, Left, Top, Width, Height)
    Exit Function
ErrRound:
    Set Round = Nothing
    Exit Function
End Function
Public Function Line(X1 As Single, Y1 As Single, X2 As Single, Y2 As Single) As Shape
'
' Add a Line to the drawing
' always draw line with X2 & Y2 largest
'
    Dim sngX1 As Single
    Dim sngY1 As Single
    Dim sngX2 As Single
    Dim sngY2 As Single
    
    On Error GoTo ErrLine
    sngX1 = X1
    If X2 < sngX1 Then
        sngX1 = X2
        sngX2 = X1
    Else
        sngX2 = X2
    End If
    sngY1 = Y1
    If Y2 < sngY1 Then
        sngY1 = Y2
        sngY2 = Y1
    Else
        sngY2 = Y2
    End If
    
    Set Line = m_shtHolder.Shapes.AddLine(X1, Y1, X2, Y2)
    Exit Function
ErrLine:
    Set Line = Nothing
    Exit Function
End Function
Public Property Set CanvasGeneric(MyCanvas As Object)
'
' Create a pointer to an object
' this allows use to use any control that has a picture property
' set picture sizing and alignment
'
    On Error GoTo ErrCanvas
    m_blnUseUF = False
    Set m_objCanvas = MyCanvas
    m_objCanvas.PictureSizeMode = fmPictureSizeModeClip
    m_objCanvas.PictureAlignment = fmPictureAlignmentTopLeft
ErrCanvas:
    Exit Property
End Property
Public Property Set CanvasUserform(MyUserform As MSForms.UserForm)
'
' Create a pointer to the userform
' set picture sizing and alignment
'
    On Error GoTo ErrUFCanvas
    m_blnUseUF = True
    Set m_frmUFCanvas = MyUserform
    m_frmUFCanvas.PictureSizeMode = fmPictureSizeModeClip
    m_frmUFCanvas.PictureAlignment = fmPictureAlignmentTopLeft
    Exit Property
ErrUFCanvas:
    Set CanvasUserform = Nothing
    Exit Property
End Property
Public Sub WipeCanvas()
' clear canvas
    On Error Resume Next
    If m_blnUseUF Then
        m_frmUFCanvas.Picture = LoadPicture("")
    Else
        m_objCanvas.Picture = LoadPicture("")
    End If
End Sub
Private Sub m_ClearHolder()
'
' Remove all shapes from holding worksheet
'
    On Error GoTo ErrClearHolder
    Do While m_shtHolder.Shapes.count > 0
        m_shtHolder.Shapes(1).Delete
    Loop
ErrClearHolder:
    Exit Sub
End Sub
Private Function m_CreateFrame() As Shape
'
' Create a shape top left in order to keep the other
' elements in the correct offset positions
'
    Dim lngColor As Long

    On Error GoTo ErrCreateFrame
    If m_blnUseUF Then
        If m_frmUFCanvas.BackColor >= 0 Then
            lngColor = m_frmUFCanvas.BackColor
        Else
            lngColor = m_frmUFCanvas.BackColor And &HFF
            lngColor = GetSysColor(lngColor)
        End If
        Set m_CreateFrame = m_shtHolder.Shapes.AddShape(msoShapeRectangle, 0, 0, m_frmUFCanvas.InsideWidth - 1, m_frmUFCanvas.InsideHeight - 1)
    Else
        If m_objCanvas.BackColor >= 0 Then
            lngColor = m_objCanvas.BackColor
        Else
            lngColor = m_objCanvas.BackColor And &HFF
            lngColor = GetSysColor(lngColor)
        End If
        Set m_CreateFrame = m_shtHolder.Shapes.AddShape(msoShapeRectangle, 0, 0, m_objCanvas.Width - 1, m_objCanvas.Height - 1)
    End If
    With m_CreateFrame
        With .Fill
            .ForeColor.RGB = lngColor
            .BackColor.RGB = lngColor
        End With
        .Line.BackColor.RGB = lngColor
        .Line.ForeColor.RGB = lngColor
        .ZOrder msoSendToBack
    End With
    Exit Function
ErrCreateFrame:
    Set m_CreateFrame = Nothing
    Exit Function
End Function
Public Sub Paint()
'
' Group all shapes and copy to picture
'
    Dim shpFrame As Shape
    Dim intIndex As Integer
    
    On Error Resume Next
    Set shpFrame = m_CreateFrame
    
    ReDim vntItems(m_shtHolder.Shapes.count - 1) As Variant
    For Each shpFrame In m_shtHolder.Shapes
        vntItems(intIndex) = shpFrame.Name
        intIndex = intIndex + 1
    Next
    m_shtHolder.Shapes.Range(vntItems).Group
    Set shpFrame = m_shtHolder.Shapes(1)
    shpFrame.CopyPicture xlScreen, xlBitmap

    'Paste the picture from the clipboard into our image control
    If m_blnUseUF Then
        Set m_frmUFCanvas.Picture = PastePicture(xlBitmap)
    Else
        Set m_objCanvas.Picture = PastePicture(xlBitmap)
    End If
    
End Sub
Private Sub Class_Initialize()

    Set m_shtHolder = ThisWorkbook.Worksheets("AJPiHolder")
    m_ClearHolder
    
End Sub
Private Sub Class_Terminate()
    ' remove any shapes
    On Error Resume Next
    m_ClearHolder
    ThisWorkbook.Saved = True
    Set m_shtHolder = Nothing
    Set m_frmUFCanvas = Nothing
    Set m_objCanvas = Nothing
End Sub

Attribute VB_Name = "AddBLDGForm"
Attribute VB_Base = "0{ADD7ED1F-346A-4FC6-AE6B-9F65E2C4B58C}{DD13B1AA-B3C6-4014-9FDC-DA0EAB7B6687}"
Attribute VB_GlobalNameSpace = False
Attribute VB_Creatable = False
Attribute VB_PredeclaredId = True
Attribute VB_Exposed = False
Attribute VB_TemplateDerived = False
Attribute VB_Customizable = False

Private Sub cbPlace_Click()
    Dim objBldg As AcadBlockReference
    Dim returnPnt, vAttList As Variant
    Dim dScale As Double
    'Dim strBlock As String
    
    Me.Hide
  On Error Resume Next
    
    dScale = CDbl(cbScale.Value) / 100
    If Not Err = 0 Then
        dScale = 1#
        Err = 0
    End If
    
Place_Block:
    Err = 0
  
    returnPnt = ThisDrawing.Utility.GetPoint(, "Place " & cbType.Value & ": ")
    If Not Err = 0 Then GoTo Exit_Sub
    
    Set objBldg = ThisDrawing.ModelSpace.InsertBlock(returnPnt, "Customer", dScale, dScale, dScale, 0#)
    objBldg.Layer = "Customers"
    
    vAttList = objBldg.GetAttributes
    
    
    Select Case cbType.Value
        Case "RES"
            vAttList(0).TextString = "RESIDENCE"
            vAttList(5).TextString = ""
        Case "BUS"
            vAttList(0).TextString = "BUSINESS"
            vAttList(5).TextString = "B"
        Case "TRLR"
            vAttList(0).TextString = "TRAILER"
            vAttList(5).TextString = "T"
        Case "MDU"
            vAttList(0).TextString = "MDU"
            vAttList(5).TextString = "M"
        Case "CHURCH"
            vAttList(0).TextString = "CHURCH"
            vAttList(5).TextString = "C"
        Case "SCHOOL"
            vAttList(0).TextString = "SCHOOL"
            vAttList(5).TextString = "S"
        Case "EXT"
            vAttList(0).TextString = "EXTENSION"
            vAttList(5).TextString = "X"
        Case Else
    End Select
    
    vAttList(1).TextString = tbHNum.Value
    vAttList(2).TextString = tbStreet.Value
    If Not tbDescription.Value = "" Then vAttList(3).TextString = tbDescription.Value
    
    objBldg.Update
    
    If Not tbPlus.Value = "" Then tbHNum.Value = CDbl(tbHNum.Value) + tbPlus.Value
        
    GoTo Place_Block
    
Exit_Sub:
    Me.show
End Sub

Private Sub cbQuit_Click()
    Me.Hide
End Sub

Private Sub cbRename_Click()
    Dim objEntity As AcadEntity
    Dim objBlock As AcadBlockReference
    Dim returnPnt, vAttList As Variant
    'Dim dScale As Double
    'Dim strBlock As String
    
    Me.Hide
  On Error Resume Next
    
    dScale = CDbl(cbScale.Value) / 100
    If Not Err = 0 Then
        dScale = 1#
        Err = 0
    End If
    
Place_Block:
    Err = 0
    ThisDrawing.Utility.GetEntity objEntity, returnPnt, vbCr & "Select Existing Building: "
    If Not Err = 0 Then GoTo Exit_Sub
    If Not TypeOf objEntity Is AcadBlockReference Then GoTo Exit_Sub
    
    Set objBlock = objEntity
    Select Case objBlock.Name
        Case "Customer"
            vAttList = objBlock.GetAttributes
        Case Else
            GoTo Exit_Sub
    End Select
    
    
    If Not tbHNum.Value = "" Then
        vAttList(1).TextString = tbHNum.Value
        If Not tbPlus.Value = "" Then tbHNum.Value = CDbl(tbHNum.Value) + CDbl(tbPlus.Value)
    End If
    
    If Not tbStreet.Value = "" Then vAttList(2).TextString = tbStreet.Value
    If Not tbDescription.Value = "" Then vAttList(3).TextString = tbDescription.Value
    
    Select Case cbType.Value
        Case "RES"
            vAttList(0).TextString = "RESIDENCE"
            vAttList(5).TextString = ""
        Case "BUS"
            vAttList(0).TextString = "BUSINESS"
            vAttList(5).TextString = "B"
        Case "TRLR"
            vAttList(0).TextString = "TRAILER"
            vAttList(5).TextString = "T"
        Case "MDU"
            vAttList(0).TextString = "MDU"
            vAttList(5).TextString = "M"
        Case "CHURCH"
            vAttList(0).TextString = "CHURCH"
            vAttList(5).TextString = "C"
        Case "SCHOOL"
            vAttList(0).TextString = "SCHOOL"
            vAttList(5).TextString = "S"
        Case "EXT"
            vAttList(0).TextString = "EXTENSION"
            vAttList(5).TextString = "X"
        Case Else
    End Select
    
    objBlock.Update
        
    GoTo Place_Block
    
Exit_Sub:
    Me.show
End Sub

Private Sub Label1_Click()
    Dim objRoadname As AcadObject
    Dim obrGP As AcadBlockReference
    Dim basePnt, vList As Variant
    Dim objText As AcadText
    Dim objMText As AcadMText
    
    Me.Hide
On Error Resume Next
    
    ThisDrawing.Utility.GetEntity objRoadname, basePnt, "Select Address: "
    'MsgBox objRoadname.ObjectName
    
    Select Case objRoadname.ObjectName
        Case "AcDbText"
            Set objText = objRoadname
            tbHNum.Text = objText.TextString
        Case "AcDbMText"
            Set objMText = objRoadname
            tbHNum.Text = objMText.TextString
        'Case "AcDbBlockReference"
            'Set obrGP = objRoadname
            'vList = obrGP.GetAttributes
            'tbHNum.Value = vList(0).TextString
    End Select
    
    cbAddWL.SetFocus
    Me.show
End Sub

Private Sub Label2_Click()
    Dim objRoadname As AcadObject
    'Dim obrGP As AcadBlockReference
    Dim basePnt As Variant
    Dim objText As AcadText
    Dim objMText As AcadMText
    
    Me.Hide
On Error Resume Next
    
    ThisDrawing.Utility.GetEntity objRoadname, basePnt, "Select Road Name: "
    'MsgBox objRoadname.ObjectName
    
    Select Case objRoadname.ObjectName
        Case "AcDbText"
            Set objText = objRoadname
            tbStreet.Text = objText.TextString
        Case "AcDbMText"
            Set objMText = objRoadname
            tbStreet.Text = objMText.TextString
    End Select
    Me.show
End Sub

Private Sub UserForm_Initialize()
    cbScale.AddItem "50"
    cbScale.AddItem "75"
    cbScale.AddItem "100"
    cbScale.Value = "100"
    
    cbType.AddItem "RES"
    cbType.AddItem "BUS"
    cbType.AddItem "TRLR"
    cbType.AddItem "MDU"
    cbType.AddItem "CHURCH"
    cbType.AddItem "SCHOOL"
    cbType.AddItem "EXT"
    cbType.Value = "RES"
End Sub

Attribute VB_Name = "AddCableToBuried"
Attribute VB_Base = "0{5935E8CD-5580-42EE-AFBD-BBD3B41A9789}{DD1597D1-10F0-40A4-A124-5864EF572687}"
Attribute VB_GlobalNameSpace = False
Attribute VB_Creatable = False
Attribute VB_PredeclaredId = True
Attribute VB_Exposed = False
Attribute VB_TemplateDerived = False
Attribute VB_Customizable = False
Dim objPlant As AcadBlockReference

Private Sub cbAddUnit_Click()
    If cbAddUnit.Caption = "Update" Then
        lbUnits.List(lbUnits.ListIndex, 0) = tbUnit.Value
        lbUnits.List(lbUnits.ListIndex, 1) = tbQuantity.Value
        lbUnits.List(lbUnits.ListIndex, 2) = tbUNote.Value
        
        cbAddUnit.Caption = "Add Unit"
        GoTo Exit_Sub
    End If
    
    lbUnits.AddItem tbUnit.Value
    lbUnits.List(lbUnits.ListCount - 1, 1) = tbQuantity.Value
    lbUnits.List(lbUnits.ListCount - 1, 2) = tbUNote.Value
    
Exit_Sub:
    
    tbUnit.Value = ""
    tbQuantity.Value = ""
    tbUNote.Value = ""
End Sub

Private Sub cbCblType_Change()
    If cbCblType.Value = "BFO" Then
        cbSuffix.AddItem ""
        cbSuffix.AddItem "I"
        cbSuffix.AddItem "E(36)"
    Else
        cbSuffix.Clear
    End If
End Sub

Private Sub cbGetBlock_Click()
    Dim objEntity As AcadEntity
    Dim vReturnPnt, vAttList As Variant
    
    Me.Hide
    
    On Error Resume Next
    
    ThisDrawing.Utility.GetEntity objEntity, vReturnPnt, vbCr & "Select Buried Plant: "
    
    If Not Err = 0 Then
        MsgBox "Not a valid selection"
        Me.show
        Exit Sub
    End If
    
    If Not TypeOf objEntity Is AcadBlockReference Then
        MsgBox "Not a valid selection"
        Me.show
        Exit Sub
    End If
    
    Set objPlant = objEntity
    Select Case objPlant.Name
        Case "sPed", "sHH"
        Case Else
            MsgBox "Not a valid selection"
            Me.show
            Exit Sub
    End Select
    
    vAttList = objPlant.GetAttributes
    
    tbNumber.Value = vAttList(0).TextString
    
    lbUnits.Clear
    
    If Not vAttList(7).TextString = "" Then
        vAttList(7).TextString = Replace(vAttList(7).TextString, vbLf, "")
        vLine = Split(vAttList(7).TextString, ";;")
        For i = 0 To UBound(vLine)
            vItem = Split(vLine(i), "=")
            lbUnits.AddItem vItem(0)
            If InStr(vItem(1), "  ") > 0 Then
                vTemp = Split(vItem(1), "  ")
                lbUnits.List(lbUnits.ListCount - 1, 1) = vTemp(0)
                lbUnits.List(lbUnits.ListCount - 1, 2) = vTemp(1)
            Else
                lbUnits.List(lbUnits.ListCount - 1, 1) = vItem(1)
                lbUnits.List(lbUnits.ListCount - 1, 2) = ""
            End If
        Next i
    End If
    
    cbUpdateBlock.Enabled = True
    
    Me.show
End Sub

Private Sub cbGetCableSpan_Click()
    If cbCblType.Value = "" Then
        MsgBox "Need a Cable Type."
        Exit Sub
    End If
    
    If cbCableSize.Value = "" Then
        MsgBox "Need a Cable Size."
        Exit Sub
    End If
    
    cbGetUnits.Enabled = True
    
    Dim objEntity As AcadEntity
    Dim objBlock As AcadBlockReference
    Dim vReturnPnt, vAttList As Variant
    Dim strTemp, strLine As String
    'Dim iQuantity As Integer
    
    Me.Hide
    
    On Error Resume Next
    
    ThisDrawing.Utility.GetEntity objEntity, vReturnPnt, vbCr & "Select Cable Span Block: "
    
    If Not Err = 0 Then
        MsgBox "Not a valid selection"
        Me.show
        Exit Sub
    End If
    
    If Not TypeOf objEntity Is AcadBlockReference Then
        MsgBox "Not a valid selection"
        Me.show
        Exit Sub
    End If
    
    Set objBlock = objEntity
    Select Case objBlock.Name
        Case "cable_span"
        Case Else
            MsgBox "Not a valid selection"
            Me.show
            Exit Sub
    End Select
    
    vAttList = objBlock.GetAttributes
    
    strTemp = Replace(vAttList(2).TextString, "'", "")
    tbSpan.Value = strTemp
    'iQuantity = CInt(strTemp)
    
    strLine = "+" & cbCblType.Value & "(" & cbCableSize.Value & ")"
    lbUnits.AddItem strLine, 0
    lbUnits.List(0, 1) = strTemp
    
    Me.show
End Sub

Private Sub cbGetUnits_Click()
    Dim objSS As AcadSelectionSet
    Dim objEntity As AcadEntity
    Dim objBlock As AcadBlockReference
    Dim vAttList As Variant
    Dim strLine As String
    
    On Error Resume Next
    
    Me.Hide
    
    Set objSS = ThisDrawing.SelectionSets.Add("objSS")
    If Not Err = 0 Then
        Set objSS = ThisDrawing.SelectionSets.Item("objSS")
        Err = 0
    End If
    
    objSS.SelectOnScreen
    If objSS.count < 1 Then GoTo Exit_Sub
    
    For Each objEntity In objSS
        If Not TypeOf objEntity Is AcadBlockReference Then GoTo Next_objEntity
        
        Set objBlock = objEntity
        
        Select Case objBlock.Name
            Case "Map coil"
                vAttList = objBlock.GetAttributes
                
                strLine = "+" & cbCblType.Value & "(" & Replace(vAttList(1).TextString, "F", "") & ")"
                lbUnits.AddItem strLine, 1
                
                strLine = Replace(vAttList(0).TextString, "'", "")
                lbUnits.List(1, 1) = strLine
                lbUnits.List(1, 2) = "LOOP"
            Case "Map splice"
                vAttList = objBlock.GetAttributes
                
                strLine = "+HBFO(" & cbCableSize.Value & ")"
                lbUnits.AddItem strLine, 2
                lbUnits.List(2, 1) = "1"
                lbUnits.List(2, 2) = vAttList(0).TextString
        End Select
        
Next_objEntity:
    Next objEntity
    
Exit_Sub:
    objSS.Clear
    objSS.Delete
    
    Me.show
End Sub

Private Sub cbQuit_Click()
    Me.Hide
End Sub

Private Sub cbUpdateBlock_Click()
    If lbUnits.ListCount < 1 Then Exit Sub
    
    Dim vAttList As Variant
    Dim strLine As String
    
    vAttList = objPlant.GetAttributes
    
    strLine = lbUnits.List(0, 0) & "=" & lbUnits.List(0, 1)
    If Not lbUnits.List(0, 2) = "" Then strLine = strLine & "  " & lbUnits.List(0, 2)
    
    If lbUnits.ListCount > 1 Then
        For i = 1 To lbUnits.ListCount - 1
            strLine = strLine & ";;" & lbUnits.List(i, 0) & "=" & lbUnits.List(i, 1)
            If Not lbUnits.List(i, 2) = "" Then strLine = strLine & "  " & lbUnits.List(i, 2)
        Next i
    End If
    
    vAttList(7).TextString = strLine
    
    objPlant.Update
End Sub

Private Sub LblRRUD_Click()
    tbUnit.Value = "+RRCONDUIT"
    tbQuantity.SetFocus
    
    If tbSpan.Value = "" Then Exit Sub
    
    If cbCblType.Value = "UO" Then
        tbQuantity.Value = tbSpan.Value
        cbAddUnit.SetFocus
    End If
End Sub

Private Sub lbUnits_DblClick(ByVal Cancel As MSForms.ReturnBoolean)
    cbAddUnit.Caption = "Update"
    
    tbUnit.Value = lbUnits.List(lbUnits.ListIndex, 0)
    tbQuantity.Value = lbUnits.List(lbUnits.ListIndex, 1)
    tbUNote.Value = lbUnits.List(lbUnits.ListIndex, 2)
End Sub

Private Sub lbUnits_KeyDown(ByVal KeyCode As MSForms.ReturnInteger, ByVal Shift As Integer)
    Dim str0, str1, str2 As String
    
    Select Case KeyCode
        Case vbKeyDelete
            Dim strUnit, strQuantity, strNote As String
            Dim iIndex, iQuantity As Integer
            
            iIndex = lbUnits.ListIndex
            strUnit = lbUnits.List(iIndex, 0)
            strQuantity = lbUnits.List(iIndex, 1)
            iQuantity = CInt(strQuantity)
            If Not lbUnits.List(iIndex, 2) = "" Then strNote = lbUnits.List(iIndex, 2)
            
            lbUnits.RemoveItem lbUnits.ListIndex
            
            If InStr(strUnit, "BM60") > 0 Then
                
            End If
        Case vbKeyUp
            If lbUnits.ListIndex = 0 Then Exit Sub
            
            str0 = lbUnits.List(lbUnits.ListIndex, 0)
            str1 = lbUnits.List(lbUnits.ListIndex, 1)
            str2 = lbUnits.List(lbUnits.ListIndex, 2)
            
            lbUnits.List(lbUnits.ListIndex, 0) = lbUnits.List(lbUnits.ListIndex - 1, 0)
            lbUnits.List(lbUnits.ListIndex, 1) = lbUnits.List(lbUnits.ListIndex - 1, 1)
            lbUnits.List(lbUnits.ListIndex, 2) = lbUnits.List(lbUnits.ListIndex - 1, 2)
            
            lbUnits.List(lbUnits.ListIndex - 1, 0) = str0
            lbUnits.List(lbUnits.ListIndex - 1, 1) = str1
            lbUnits.List(lbUnits.ListIndex - 1, 2) = str2
            
            'lbUnits.ListIndex = lbUnits.ListIndex - 1
        Case vbKeyDown
            If lbUnits.ListIndex = lbUnits.ListCount - 1 Then Exit Sub
            
            str0 = lbUnits.List(lbUnits.ListIndex, 0)
            str1 = lbUnits.List(lbUnits.ListIndex, 1)
            str2 = lbUnits.List(lbUnits.ListIndex, 2)
            
            lbUnits.List(lbUnits.ListIndex, 0) = lbUnits.List(lbUnits.ListIndex + 1, 0)
            lbUnits.List(lbUnits.ListIndex, 1) = lbUnits.List(lbUnits.ListIndex + 1, 1)
            lbUnits.List(lbUnits.ListIndex, 2) = lbUnits.List(lbUnits.ListIndex + 1, 2)
            
            lbUnits.List(lbUnits.ListIndex + 1, 0) = str0
            lbUnits.List(lbUnits.ListIndex + 1, 1) = str1
            lbUnits.List(lbUnits.ListIndex + 1, 2) = str2
            
            'lbUnits.ListIndex = lbUnits.ListIndex + 1
    End Select
End Sub

Private Sub UserForm_Initialize()
    cbCblType.AddItem ""
    cbCblType.AddItem "BFO"
    cbCblType.AddItem "UO"
    
    cbCableSize.AddItem ""
    cbCableSize.AddItem "12"
    cbCableSize.AddItem "24"
    cbCableSize.AddItem "36"
    cbCableSize.AddItem "48"
    cbCableSize.AddItem "72"
    cbCableSize.AddItem "96"
    cbCableSize.AddItem "144"
    cbCableSize.AddItem "216"
    cbCableSize.AddItem "288"
    cbCableSize.AddItem "360"
    cbCableSize.AddItem "432"
    
    lbUnits.ColumnCount = 3
    lbUnits.ColumnWidths = "96;36;44"
End Sub

Attribute VB_Name = "AddCableToPole"
Attribute VB_Base = "0{C863B586-5837-49BD-8128-7837C7C05F77}{C6C36DE2-8C4B-4031-894D-A823EBE3B98D}"
Attribute VB_GlobalNameSpace = False
Attribute VB_Creatable = False
Attribute VB_PredeclaredId = True
Attribute VB_Exposed = False
Attribute VB_TemplateDerived = False
Attribute VB_Customizable = False
Dim iListIndex As Integer

Private Sub cbAdd_Click()
    If lbCounts.ListCount < 1 Then
        MsgBox "Counts empty." & vbCr & "Try add a Cable Size."
        Exit Sub
    End If
    
    If tbCblName.Value = "" Then
        MsgBox "Need to add a Count Name"
        Exit Sub
    End If
    
    If tbFFiber.Value = "" Then
        MsgBox "Missing From Fiber"
        Exit Sub
    End If
    
    If tbTFiber.Value = "" Then
        MsgBox "Missing To Fiber"
        Exit Sub
    End If
    
    If tbFCount.Value = "" Then
        MsgBox "Missing Start Count"
        Exit Sub
    End If
    
    Dim vLine, vCable, vFibers, vCounts As Variant
    Dim strLine, strOld As String
    Dim str1, str2, str3 As String
    Dim iFF, iTF As Integer
    Dim iFC, iTC As Integer
    Dim iPFF, iPTF As Integer
    Dim iPFC, iPTC As Integer
    Dim iNewTF, iNewFF As Integer
    Dim iNewTC, iNewFC As Integer
    
    str1 = "": str2 = "": str3 = ""
    
    iPFF = CInt(tbFFiber.Value)
    iPTF = CInt(tbTFiber.Value)
    
    iPFC = CInt(tbFCount.Value)
    iPTC = CInt(tbTCount.Value)
    
    For i = 0 To lbCounts.ListCount - 1
        vLine = Split(lbCounts.List(i), vbTab)
        vFibers = Split(vLine(0), "-")
        vCable = Split(vLine(1), ": ")
        vCounts = Split(vCable(1), "-")
        
        strOld = vCable(2)
        
        iFF = CInt(vFibers(0))
        If UBound(vFibers) > 0 Then
            iTF = CInt(vFibers(1))
        Else
            iTF = iFF
        End If
        
        iFC = CInt(vCounts(0))
        If UBound(vCounts) > 0 Then
            iTC = CInt(vCounts(1))
        Else
            iTC = iFC
        End If
        
        If iPFF > iTF Then GoTo Next_I
        
        Select Case (iPFF - iFF)
            Case Is = 0
                Select Case (iPTF - iTF)
                    Case Is = 0
                        str1 = iPFF & "-" & iPTF & vbTab & tbCblName.Value & ": " & iPFC  '& "-" & iTC
                        If iPFC < iPTC Then str1 = str1 & "-" & iPTC
                        str1 = str1 & ": " & tbPrevious.Value
                        lbCounts.List(i) = str1
                        GoTo Exit_Next
                    Case Is < 0
                        str1 = iPFF & "-" & iPTF & vbTab & tbCblName.Value & ": " & iPFC  '& "-" & iTC
                        If iPFC < iPTC Then str1 = str1 & "-" & iPTC
                        str1 = str1 & ": " & tbPrevious.Value
                        lbCounts.List(i) = str1
                        
                        iNewFF = iPTF + 1
                        iNewFC = iFC + iPTC - iPFC + 1
                        
                        str2 = iNewFF & "-" & iTF & vbTab & vCable(0) & ": " & iNewFC
                        If iNewFC < iTC Then str2 = str2 & "-" & iTC
                        str2 = str2 & ": " & strOld
                        lbCounts.AddItem str2, i + 1
                        GoTo Exit_Next
                    Case Is > 0
                        iNewTC = iPTC + iTF - iFF + 1
                        
                        str1 = iFF & "-" & iTF & vbTab & tbCblName.Value & ": " & iPFC & "-" & iNewTC & ": " & tbPrevious.Value
                        lbCounts.List(i) = str1
                        GoTo Exit_Next
                End Select
            Case Is > 0
                iNewTF = iPFF - 1
                iNewTC = iFC + iNewTF - iFF
                        
                str1 = iFF & "-" & iNewTF & vbTab & vCable(0) & ": " & iFC
                If iNewTC > iFC Then str1 = str1 & "-" & iNewTC
                str1 = str1 & ": " & strOld
                lbCounts.List(i) = str1
                        
                Select Case (iPTF - iTF)
                    Case Is = 0
                        str2 = iPFF & "-" & iPTF & vbTab & tbCblName.Value & ": " & iPFC
                        If iPFC < iPTC Then str2 = str2 & "-" & iPTC
                        str2 = str2 & ": " & tbPrevious.Value
                        lbCounts.AddItem str2, i + 1
                        GoTo Exit_Next
                    Case Is < 0
                        str2 = iPFF & "-" & iPTF & vbTab & tbCblName.Value & ": " & iPFC  '& "-" & iTC
                        If iPFC < iPTC Then str2 = str2 & "-" & iPTC
                        str2 = str2 & ": " & tbPrevious.Value
                        lbCounts.AddItem str2, i + 1
                        
                        iNewFF = iPTF + 1
                        iNewFC = iFC + iPTF - iFF + 1
                        
                        str3 = iNewFF & "-" & iTF & vbTab & vCable(0) & ": " & iNewFC
                        If iNewFC < iTC Then str3 = str3 & "-" & iTC
                        str3 = str3 & ": " & strOld
                        lbCounts.AddItem str3, i + 2
                        GoTo Exit_Next
                    Case Is > 0
                        iNewTC = iPTC + iTF - iFF + 1
                        
                        str2 = iFF & "-" & iTF & vbTab & tbCblName.Value & ": " & iPFC
                        If iPFC < iNewTC Then str2 = str2 & "-" & iNewTC
                        str2 = str2 & ": " & tbPrevious.Value
                        lbCounts.AddItem str2, i + 1
                        GoTo Exit_Next
                End Select
        End Select
Next_I:
    Next i
    
Exit_Next:
    'Dim strLine As String

    'strLine = tbFFiber.Value & "-" & tbTFiber.Value & vbTab
    'strLine = strLine & tbCblName.Value & ": " & tbFCount.Value & "-" & tbTCount.Value
    
    'lbCounts.AddItem strLine
End Sub

Private Sub cbAddToPole_Click()
    If lbCounts.ListCount < 1 Then
        MsgBox "Needs Counts"
        Exit Sub
    End If
    
    Dim objEntity As AcadEntity
    Dim objBlock As AcadBlockReference
    Dim vAttList, vLine As Variant
    Dim vReturnPnt As Variant
    Dim strLine As String
    Dim iAtt As Integer
    
    If cbCblType.Value = "CO" Then
        If cbSuffix.Value = "E" Then
            strLine = tbPosition.Value & "2: "
        Else
            strLine = tbPosition.Value & "1: "
        End If
    Else
        strLine = tbPosition.Value & "1: "
    End If
    
    strLine = strLine & cbCblType.Value & "(" & cbCableSize.Value & ")"
    If Not cbSuffix.Value = "" Then strLine = strLine & cbSuffix.Value
    strLine = strLine & " / "
    
    vLine = Split(lbCounts.List(0), vbTab)
    strLine = strLine & vLine(1)
    
    If lbCounts.ListCount > 1 Then
        For i = 1 To lbCounts.ListCount - 1
            vLine = Split(lbCounts.List(i), vbTab)
            strLine = strLine & " + " & vLine(1)
        Next i
    End If
    
    Me.Hide
  On Error Resume Next
    
    ThisDrawing.Utility.GetEntity objEntity, vReturnPnt
    If Not Err = 0 Then
        MsgBox "Cable not added to Block."
        Me.show
    End If
    
    If TypeOf objEntity Is AcadBlockReference Then
        Set objBlock = objEntity
    Else
        MsgBox "Cable not added to Block."
        Me.show
    End If
    
    Select Case objBlock.Name
        Case "sPole"
            iAtt = 25
        Case Else
            iAtt = 5
    End Select
    
    vAttList = objBlock.GetAttributes
    
    If vAttList(iAtt).TextString = "" Then
        vAttList(iAtt).TextString = strLine
    Else
        vAttList(iAtt).TextString = vAttList(iAtt).TextString & vbCr & strLine
    End If
    
    objBlock.Update
    
    tbPrevious.Value = vAttList(0).TextString
    
    Me.show
End Sub

Private Sub cbCableSize_AfterUpdate()
    If cbCableSize.Value = "" Then Exit Sub
    
    lbCounts.Clear
    
    lbCounts.AddItem "1-" & cbCableSize.Value & vbTab & "XD: 1-" & cbCableSize.Value & ": END"
End Sub

Private Sub cbCancel_Click()
    Me.Hide
End Sub

Private Sub cbCblType_Change()
    If cbCblType.Value = "CO" Then
        cbSuffix.AddItem ""
        cbSuffix.AddItem "E"
        cbSuffix.AddItem "6M-EHS"
        cbSuffix.AddItem "10M"
        cbSuffix.Enabled = True
    Else
        cbSuffix.Clear
        cbSuffix.Enabled = False
        
        tbPosition.Value = tbPosition.Value & "1"
    End If
End Sub

Private Sub cbSendToCounts_Click()
    Me.Hide
End Sub

Private Sub cbCLR_Click()
    lbCounts.Clear
    
    lbCounts.AddItem "1-" & cbCableSize.Value & vbTab & "XD: 1-" & cbCableSize.Value & ": END"
End Sub

Private Sub cbDelete_Click()
    lbCounts.RemoveItem (lbCounts.ListIndex)
End Sub

Private Sub cbDOWN_Click()
    Dim str1 As String
    Dim i, i2 As Integer
    
    If lbCounts.ListIndex = (lbCounts.ListCount - 1) Then Exit Sub
    i = lbCounts.ListIndex
    i2 = i + 1
    str1 = lbCounts.List(i)
    lbCounts.List(i) = lbCounts.List(i2)
    lbCounts.List(i2) = str1
    
    lbCounts.ListIndex = i2
End Sub

Private Sub cbUP_Click()
    Dim str1 As String
    Dim i, i2 As Integer
    
    If lbCounts.ListIndex = 0 Then Exit Sub
    i = lbcountss.ListIndex
    i2 = i - 1
    str1 = lbCounts.List(i)
    lbCounts.List(i) = lbCounts.List(i2)
    lbCounts.List(i2) = str1
    
    lbCounts.ListIndex = i2
End Sub

Private Sub Label12_Click()
    Dim objEntity As AcadEntity
    Dim objPrevious As AcadBlockReference
    Dim vReturnPnt, vAttList As Variant
    
    Me.Hide
    
    ThisDrawing.Utility.GetEntity objEntity, vReturnPnt, "Select Previous Block: "
    If TypeOf objEntity Is AcadBlockReference Then
        Set objPrevious = objEntity
        vAttList = objPrevious.GetAttributes
        
        tbPrevious.Value = vAttList(0).TextString
    End If
    
    Me.show
End Sub

Private Sub lbCounts_KeyDown(ByVal KeyCode As MSForms.ReturnInteger, ByVal Shift As Integer)
    If lbCounts.ListCount < 1 Then Exit Sub
    
    Dim str1 As String
    Dim i, i2 As Integer
    
    Select Case KeyCode
        Case vbKeyUp
            If lbCounts.ListIndex = 0 Then Exit Sub
            i = lbcountss.ListIndex
            i2 = i - 1
            str1 = lbCounts.List(i)
            lbCounts.List(i) = lbCounts.List(i2)
            lbCounts.List(i2) = str1
    
            lbCounts.ListIndex = i2
        Case vbKeyDown
            If lbCounts.ListIndex = (lbCounts.ListCount - 1) Then Exit Sub
            i = lbCounts.ListIndex
            i2 = i + 1
            str1 = lbCounts.List(i)
            lbCounts.List(i) = lbCounts.List(i2)
            lbCounts.List(i2) = str1
    
            lbCounts.ListIndex = i2
        Case vbKeyDelete
            lbCounts.RemoveItem (lbCounts.ListIndex)
    End Select
End Sub

Private Sub tbFCount_AfterUpdate()
    Dim iFFiber, iTFiber, iFCount, iTCount As Integer
    Dim iDiff As Integer
    Dim dTest As Double
    
    iFFiber = CInt(tbFFiber.Value)
    iTFiber = CInt(tbTFiber.Value)
    iFCount = CInt(tbFCount.Value)
    iDiff = iFCount - iFFiber
    dTest = iDiff / 12
    If Not (dTest - Int(dTest)) = 0 Then MsgBox "Off-Color"
    iDiff = iTFiber - iFFiber
    tbTCount.Value = iFCount + iDiff
End Sub

Private Sub tbFFiber_AfterUpdate()
    If CInt(tbFFiber.Value) > CInt(cbCableSize.Value) Then tbFFiber.Value = 1
End Sub

Private Sub tbTFiber_AfterUpdate()
    If CInt(tbTFiber.Value) > CInt(cbCableSize.Value) Then tbTFiber.Value = cbCableSize.Value
    If tbTFiber.Value < tbFFiber.Value Then tbTFiber.Value = tbFFiber.Value
End Sub

Private Sub UserForm_Initialize()
    cbCblType.AddItem ""
    cbCblType.AddItem "CO"
    cbCblType.AddItem "BFO"
    cbCblType.AddItem "UO"
    
    cbCableSize.AddItem ""
    cbCableSize.AddItem "12"
    cbCableSize.AddItem "24"
    cbCableSize.AddItem "36"
    cbCableSize.AddItem "48"
    cbCableSize.AddItem "72"
    cbCableSize.AddItem "96"
    cbCableSize.AddItem "144"
    cbCableSize.AddItem "216"
    cbCableSize.AddItem "288"
    cbCableSize.AddItem "360"
    cbCableSize.AddItem "432"
    
    cbUP.Caption = Chr(225)
    cbDOWN.Caption = Chr(226)
    
    'cbCblName.AddItem tbF1Name.Value
    'cbCblName.AddItem tbF2Name.Value
    'cbCblName.AddItem "XD"
    
    'cbCblType.Value = CountsForm.cbCblType.Value
    'cbCableSize.Value = CountsForm.cbCableSize.Value
    'If cbCableSize.Value = "" Then cbCableSize.Value = "144"
    
    'cbSuffix.Value = CountsForm.cbSuffix.Value
End Sub

Attribute VB_Name = "AddClearances"
Attribute VB_Base = "0{86C1BA0E-A732-496A-ADF6-90B9A101E892}{BD32EC75-6F5D-4628-A90D-2B62FAE74789}"
Attribute VB_GlobalNameSpace = False
Attribute VB_Creatable = False
Attribute VB_PredeclaredId = True
Attribute VB_Exposed = False
Attribute VB_TemplateDerived = False
Attribute VB_Customizable = False
Private Sub cbAdd_Click()
    Dim objSS As AcadSelectionSet
    Dim filterType, filterValue As Variant
    Dim grpCode(0) As Integer
    Dim grpValue(0) As Variant
    Dim objBlock As AcadBlockReference
    Dim objCLR As AcadBlockReference
    Dim vAttList As Variant
    Dim vLine, vAttach, vTemp As Variant
    Dim iTest, iClr As Integer
    Dim strLine As String
    Dim dRotate As Double
    Dim vInsert As Variant
    
    vLine = Split(tbCLR.Value, "-")
    iTest = CInt(vLine(0)) * 12
    If UBound(vLine) > 0 Then iTest = iTest + CInt(vLine(1))
    
    On Error Resume Next
    
    grpCode(0) = 2
    grpValue(0) = "cable_span"
    filterType = grpCode
    filterValue = grpValue
    
    Err = 0
    Set objSS = ThisDrawing.SelectionSets.Add("objSS")
    If Not Err = 0 Then
        Set objSS = ThisDrawing.SelectionSets.Item("objSS")
        objSS.Clear
    End If
    
    objSS.Select acSelectionSetAll, , , filterType, filterValue
    
    For Each objBlock In objSS
        vAttList = objBlock.GetAttributes
        If vAttList(0).TextString = "" Then GoTo Next_objBlock
        
        vLine = Split(UCase(vAttList(0).TextString), " ")
        If UBound(vLine) < 1 Then GoTo Next_objBlock
        
        Select Case vLine(0)
            Case "M", "MS"
                strLine = "MIDSPAN CLR"
            Case "D", "DW"
                strLine = "DRIVEWAY CLR"
            Case "R", "RD"
                strLine = "ROAD CLR"
        End Select
        
        vAttach = Split(vLine(1), "-")
        iClr = CInt(vAttach(0)) * 12
        If UBound(vAttach) > 0 Then iClr = iClr + CInt(vAttach(1))
        
        If iClr > iTest Then GoTo Next_objBlock
        
        dRotate = objBlock.Rotation
        vInsert = objBlock.InsertionPoint
        
        Set objCLR = ThisDrawing.ModelSpace.InsertBlock(vInsert, "clr", 1#, 1#, 1#, dRotate)
        objCLR.Layer = "Integrity Roads-Clearance"
        
        vAttList = objCLR.GetAttributes
        vAttList(0).TextString = strLine
        vAttList(1).TextString = vAttach(0) & "'"
        If UBound(vAttach) > 0 Then vAttList(1).TextString = vAttList(1).TextString & vAttach(1) & """"
        
        objCLR.Update
Next_objBlock:
    Next objBlock
    
    objSS.Clear
    objSS.Delete
    
    Me.Hide
End Sub

Private Sub cbQuit_Click()
    Me.Hide
End Sub

Private Sub CommandButton1_Click()
    Dim objEntity As AcadEntity
    Dim objBlock As AcadBlockReference
    Dim objCLR As AcadBlockReference
    Dim vAttList, vReturnPnt As Variant
    Dim vLine, vAttach, vTemp As Variant
    Dim strLine, strHeight As String
    Dim dRotate As Double
    Dim vInsert As Variant
    
    On Error Resume Next
    
    Me.Hide
    
Place_Block:
    
    ThisDrawing.Utility.GetEntity objEntity, vReturnPnt, "Select Span: "
    If Not Err = 0 Then GoTo Exit_Sub
    
    If Not TypeOf objEntity Is AcadBlockReference Then GoTo Exit_Sub
    Set objBlock = objEntity
    
    If Not objBlock.Name = "cable_span" Then GoTo Exit_Sub
    
    vAttList = objBlock.GetAttributes
    
    If vAttList(0).TextString = "" Then
        MsgBox "No clearance"
        GoTo Place_Block
    End If
        
    vLine = Split(UCase(vAttList(0).TextString), " ")
    If UBound(vLine) < 1 Then
        MsgBox "Invalid clearance"
        GoTo Place_Block
    End If
        
    Select Case vLine(0)
        Case "M", "MS"
            strLine = "MIDSPAN CLR"
        Case "D", "DW"
            strLine = "DRIVEWAY CLR"
        Case "R", "RD"
            strLine = "ROAD CLR"
    End Select
    
    strHeight = Replace(vLine(1), "-", "'") & """"
        
    dRotate = objBlock.Rotation
    vInsert = objBlock.InsertionPoint
        
    Set objCLR = ThisDrawing.ModelSpace.InsertBlock(vInsert, "clr", 1#, 1#, 1#, dRotate)
    objCLR.Layer = "Integrity Roads-Clearance"
        
    vAttList = objCLR.GetAttributes
    vAttList(0).TextString = strLine
    vAttList(1).TextString = strHeight
        
    objCLR.Update
    
    GoTo Place_Block
    
Exit_Sub:
    Me.Hide
End Sub

Attribute VB_Name = "AddRemoveUnits"
Attribute VB_Base = "0{B3599777-701E-4754-B00A-869DA03D7372}{165B1894-3AD1-498F-B426-BD052D426DE7}"
Attribute VB_GlobalNameSpace = False
Attribute VB_Creatable = False
Attribute VB_PredeclaredId = True
Attribute VB_Exposed = False
Attribute VB_TemplateDerived = False
Attribute VB_Customizable = False
Dim objBlock As AcadBlockReference

Private Sub cbAddUnit_Click()
    Dim iIndex As Integer
    
    If cbAddUnit.Caption = "Update" Then
        iIndex = lbUnits.ListIndex
        
        lbUnits.List(iIndex, 0) = tbUnit.Value
        lbUnits.List(iIndex, 1) = tbQuantity.Value
        If Not tbUNote.Value = "" Then
            lbUnits.List(iIndex, 2) = ""
        Else
            lbUnits.List(iIndex, 2) = tbUNote.Value
        End If
        
        tbUnit.Value = ""
        tbQuantity.Value = ""
        tbUNote.Value = ""
        
        cbAddUnit.Caption = "Add Unit"
    Else
        lbUnits.AddItem tbUnit.Value
        
        iIndex = lbUnits.ListCount - 1
        lbUnits.List(iIndex, 1) = tbQuantity.Value
        
        If Not tbUNote.Value = "" Then
            lbUnits.List(iIndex, 2) = ""
        Else
            lbUnits.List(iIndex, 2) = tbUNote.Value
        End If
        
        tbUnit.Value = ""
        tbQuantity.Value = ""
        tbUNote.Value = ""
        
    End If
End Sub

Private Sub cbCombine_Click()
    If lbUnits.ListCount < 2 Then Exit Sub
    
    Dim vCurrent, vOther, vItem As Variant
    Dim strCurrent As String
    
    For i = lbUnits.ListCount - 1 To 0 Step -1
        strCurrent = lbUnits.List(i, 0)
        
        For j = 0 To i - 1
            If lbUnits.List(j, 0) = strCurrent Then
                lbUnits.List(j, 1) = CInt(lbUnits.List(j, 1)) + CInt(lbUnits.List(i, 1))
                lbUnits.RemoveItem i
                GoTo Next_I
            End If
        Next j
Next_I:
    Next i
End Sub

Private Sub cbERemovetUnits_Click()
    Dim objSS As AcadSelectionSet
    Dim objEntity As AcadEntity
    Dim objItem As AcadBlockReference
    Dim vAttList As Variant
    Dim strAddUnit, strTemp As String
    Dim iRemoveIndex, iAddIndex As Integer
    Dim iAmount As Integer
    
    iRemoveIndex = -1
    iAddIndex = -1
    
    On Error Resume Next
    Me.Hide
    
    Set objSS = ThisDrawing.SelectionSets.Add("objss")
    If Not Err = 0 Then
        Set objSS = ThisDrawing.SelectionSets.Item("objss")
        Err = 0
    End If
    
    objSS.SelectOnScreen
    
    If objSS.count = 0 Then GoTo Exit_Sub
    
    For Each objEntity In objSS
        If Not TypeOf objEntity Is AcadBlockReference Then GoTo Next_objEntity
        
        Set objItem = objEntity
        vAttList = objItem.GetAttributes
        
        If Not Err = 0 Then GoTo Next_objEntity
            
        Select Case objItem.Name
            Case "ExGuyOL", "ExGuyOR"
                If InStr(LCase(objItem.Layer), "existing") > 0 Then
                    iRemoveIndex = GetExistingIndex("PM11")
                    iAmount = CInt(lbEUnits.List(iRemoveIndex, 2))
                
                    If iAmount > 1 Then
                        lbEUnits.List(iRemoveIndex) = iAmount - 1
                    Else
                        lbEUnits.RemoveItem iRemoveIndex
                    End If
                    
                    iRemoveIndex = GetExistingIndex(CStr(vAttList(2).TextString))
                    iAddIndex = 1001
                    strAddUnit = "+XXPE"
                    
                    objItem.Layer = "Integrity Removed"
                    objItem.Update
                Else
                    iAddIndex = GetProposedIndex("PM11")
                    iAmount = CInt(lbUnits.List(iAddIndex, 1))
                
                    If iAmount > 1 Then
                        lbUnits.List(iAddIndex) = iAmount - 1
                    Else
                        lbUnits.RemoveItem iAddIndex
                    End If
                    
                    iRemoveIndex = -1
                    iAddIndex = GetProposedIndex(CStr(vAttList(2).TextString))
                    
                    objItem.Delete
                End If
            Case "ExAncOL", "ExAncOR"
                If InStr(LCase(objItem.Layer), "existing") > 0 Then
                    iRemoveIndex = GetExistingIndex(CStr(vAttList(0).TextString))
                    iAddIndex = 1001
                    strAddUnit = "+XXPF"
                    
                    objItem.Layer = "Integrity Removed"
                    objItem.Update
                Else
                    iRemoveIndex = -1
                    iAddIndex = GetProposedIndex(CStr(vAttList(0).TextString))
                    
                    objItem.Delete
                End If
            Case "Map splice"
                If InStr(LCase(objItem.Layer), "aerial") > 0 Then iAddIndex = GetProposedIndex("+HACO")
                If InStr(LCase(objItem.Layer), "buried") > 0 Then iAddIndex = GetProposedIndex("+HBFO")
                
                objItem.Delete
            Case "Map coil"
                strTemp = Replace(vAttList(1).TextString, "F", "")
                If InStr(LCase(objItem.Layer), "aerial") > 0 Then strTemp = "+CO(" & strTemp & ")E"
                If InStr(LCase(objItem.Layer), "buried") > 0 Then strTemp = "+UO(" & strTemp & ")"
                
                iAddIndex = GetCoilIndex(strTemp)
                If iAddIndex < 0 Then
                    strTemp = Replace(strTemp, "UO", "BFO")
                    iAddIndex = GetCoilIndex(strTemp)
                End If
                
                objItem.Delete
        End Select
        
        'MsgBox objItem.Name & vbCr & "Remove: " & iRemoveIndex & vbCr & "Add: " & iAddIndex & vbCr & "String: " & strAddUnit
        
        If iRemoveIndex < 0 Then
            If iAddIndex < 0 Then
                GoTo Next_objEntity
            Else
                iAmount = CInt(lbUnits.List(iAddIndex, 1))
                
                If iAmount > 1 Then
                    lbUnits.List(iAddIndex) = iAmount - 1
                Else
                    lbUnits.RemoveItem iAddIndex
                End If
            End If
        Else
            iAmount = CInt(lbEUnits.List(iRemoveIndex, 1))
                
            If iAmount > 1 Then
                lbEUnits.List(iRemoveIndex) = iAmount - 1
            Else
                lbEUnits.RemoveItem iRemoveIndex
            End If
            
            If Not strAddUnit = "" Then
                If lbUnits.ListCount < 0 Then
                    lbUnits.AddItem strAddUnit
                    lbUnits.List(lbUnits.ListCount - 1, 1) = 1
                Else
                    For i = 0 To lbUnits.ListCount - 1
                        If lbUnits.List(i, 0) = strAddUnit Then
                            iAmount = CInt(lbUnits.List(i, 1)) + 1
                            lbUnits.List(i, 1) = iAmount
                            GoTo Next_objEntity
                        End If
                    Next i
                        
                    lbUnits.AddItem strAddUnit
                    lbUnits.List(lbUnits.ListCount - 1, 1) = 1
                End If
                GoTo Next_objEntity
            End If
            
            If iAddIndex > -1 Then
                iAmount = CInt(lbUnits.List(iAddIndex, 1))
                
                If iAmount > 1 Then
                    lbUnits.List(iAddIndex) = iAmount - 1
                Else
                    lbUnits.RemoveItem iAddIndex
                End If
            End If
        End If
        
Next_objEntity:
        Err = 0
        iRemoveIndex = -1
        iAddIndex = -1
        strAddUnit = ""
    Next objEntity
    
Exit_Sub:
    objSS.Clear
    objSS.Delete
    
    ThisDrawing.Regen acActiveViewport
    
    Me.show
End Sub

Private Sub cbGetBlock_Click()
    Dim objObject As AcadObject
    Dim vBasePnt, vAttList As Variant
    Dim vUnits, vLine, vItem, vTemp As Variant
    Dim strTemp As String
    Dim iAtt As Integer
    
    Me.Hide
  On Error Resume Next
    
    ThisDrawing.Utility.GetEntity objObject, vBasePnt, "Select Pole: "
    If TypeOf objObject Is AcadBlockReference Then
        Set objBlock = objObject
    Else
        MsgBox "Not a valid object."
        Me.show
        Exit Sub
    End If
    
    If Not objBlock.Name = "sPole" Then
        MsgBox "Not a valid Block."
        Me.show
        Exit Sub
    End If
    
    Select Case objBlock.Name
        Case "sPole"
            iAtt = 27
        Case "sPed", "sHH", "sFP"
            iAtt = 7
        Case Else
            MsgBox "Not a valid Block."
            Me.show
            Exit Sub
    End Select
    
    lbEUnits.Clear
    lbUnits.Clear
    
    vAttList = objBlock.GetAttributes
    
    If Not vAttList(iAtt).TextString = "" Then
        vAttList(iAtt).TextString = Replace(vAttList(iAtt).TextString, vbLf, "")
        vUnits = Split(vAttList(iAtt).TextString, " <-- ")
        
        If UBound(vUnits) > 0 Then
            vLine = Split(vUnits(0), ";;")
            For i = 0 To UBound(vLine)
                vItem = Split(vLine(i), "=")
                lbEUnits.AddItem vItem(0)
                If InStr(vItem(1), "  ") > 0 Then
                    vTemp = Split(vItem(1), "  ")
                    lbEUnits.List(lbEUnits.ListCount - 1, 1) = vTemp(0)
                    lbEUnits.List(lbEUnits.ListCount - 1, 2) = vTemp(1)
                Else
                    lbEUnits.List(lbEUnits.ListCount - 1, 1) = vItem(1)
                    lbEUnits.List(lbEUnits.ListCount - 1, 2) = ""
                End If
            Next i
        End If
        
        vLine = Split(vUnits(UBound(vUnits)), ";;")
        For i = 0 To UBound(vLine)
            vItem = Split(vLine(i), "=")
            lbUnits.AddItem vItem(0)
            If InStr(vItem(1), "  ") > 0 Then
                vTemp = Split(vItem(1), "  ")
                lbUnits.List(lbUnits.ListCount - 1, 1) = vTemp(0)
                lbUnits.List(lbUnits.ListCount - 1, 2) = vTemp(1)
            Else
                lbUnits.List(lbUnits.ListCount - 1, 1) = vItem(1)
                lbUnits.List(lbUnits.ListCount - 1, 2) = ""
            End If
        Next i
    End If
    
    cbAddUnit.Enabled = True
    cbERemovetUnits.Enabled = True
    cbGetUnits.Enabled = True
    cbUpdateBlock.Enabled = True
    
    Me.show
End Sub

Private Sub cbQuit_Click()
    Me.Hide
End Sub

Private Sub cbUpdateBlock_Click()
    Dim strExisting, strProposed As String
    Dim vAttList As Variant
    Dim iAtt As Integer
    
    strExisting = ""
    strProposed = ""
    
    If lbEUnits.ListCount < 1 Then GoTo Add_Proposed
    
    strExisting = lbEUnits.List(0, 0) & "=" & lbEUnits.List(0, 1)
    If Not lbEUnits.List(0, 2) = "" Then strExisting = strExisting & "  " & lbEUnits.List(0, 2)
    
    If lbEUnits.ListCount > 1 Then
        For i = 1 To lbEUnits.ListCount - 1
            strExisting = strExisting & ";;" & lbEUnits.List(i, 0) & "=" & lbEUnits.List(i, 1)
            If Not lbEUnits.List(i, 2) = "" Then strExisting = strExisting & "  " & lbEUnits.List(i, 2)
        Next i
    End If
    
Add_Proposed:
    
    If lbUnits.ListCount < 1 Then GoTo Save_Block
    
    strProposed = lbUnits.List(0, 0) & "=" & lbUnits.List(0, 1)
    If Not lbUnits.List(0, 2) = "" Then strProposed = strProposed & "  " & lbUnits.List(0, 2)
    
    If lbUnits.ListCount > 1 Then
        For i = 1 To lbUnits.ListCount - 1
            strProposed = strProposed & ";;" & lbUnits.List(i, 0) & "=" & lbUnits.List(i, 1)
            If Not lbUnits.List(i, 2) = "" Then strProposed = strProposed & "  " & lbUnits.List(i, 2)
        Next i
    End If
    
Save_Block:
    
    If strExisting = "" Then
        strExisting = strProposed
    Else
        strExisting = strExisting & " <-- " & strProposed
    End If
    
    vAttList = objBlock.GetAttributes
    
    Select Case objBlock.Name
        Case "sPole"
            iAtt = 27
        Case Else
            iAtt = 7
    End Select
    
    vAttList(iAtt).TextString = strExisting
    
    objBlock.Update
End Sub

Private Sub lbEUnits_KeyDown(ByVal KeyCode As MSForms.ReturnInteger, ByVal Shift As Integer)
    If lbEUnits.ListCount < 1 Then Exit Sub
    
    Dim strUnit, strQ, strNote As String
    Dim i, i2 As Integer
    
    Select Case KeyCode
        Case vbKeyDelete
            lbEUnits.RemoveItem lbEUnits.ListIndex
        Case vbKeyDown
            If lbEUnits.ListIndex = (lbEUnits.ListCount - 1) Then Exit Sub
            i = lbEUnits.ListIndex
            i2 = i + 1
            
            strUnit = lbEUnits.List(i, 0)
            strQ = lbEUnits.List(i, 1)
            strNote = lbEUnits.List(i, 2)
            
            lbEUnits.List(i, 0) = lbEUnits.List(i2, 0)
            lbEUnits.List(i, 1) = lbEUnits.List(i2, 1)
            lbEUnits.List(i, 2) = lbEUnits.List(i2, 2)
            
            lbEUnits.List(i2, 0) = strUnit
            lbEUnits.List(i2, 1) = strQ
            lbEUnits.List(i2, 2) = strNote
        Case vbKeyUp
            If lbEUnits.ListIndex = 0 Then Exit Sub
            i = lbEUnits.ListIndex
            i2 = i - 1
            
            strUnit = lbEUnits.List(i, 0)
            strQ = lbEUnits.List(i, 1)
            strNote = lbEUnits.List(i, 2)
            
            lbEUnits.List(i, 0) = lbEUnits.List(i2, 0)
            lbEUnits.List(i, 1) = lbEUnits.List(i2, 1)
            lbEUnits.List(i, 2) = lbEUnits.List(i2, 2)
            
            lbEUnits.List(i2, 0) = strUnit
            lbEUnits.List(i2, 1) = strQ
            lbEUnits.List(i2, 2) = strNote
    End Select
End Sub

Private Sub lbUnits_DblClick(ByVal Cancel As MSForms.ReturnBoolean)
    tbUnit.Value = lbUnits.List(lbUnits.ListIndex, 0)
    tbQuantity.Value = lbUnits.List(lbUnits.ListIndex, 1)
    tbUNote.Value = lbUnits.List(lbUnits.ListIndex, 2)
    
    cbAddUnit.Caption = "Update"
End Sub

Private Sub lbUnits_KeyDown(ByVal KeyCode As MSForms.ReturnInteger, ByVal Shift As Integer)
    If lbUnits.ListCount < 1 Then Exit Sub
    
    Dim strUnit, strQ, strNote As String
    Dim i, i2 As Integer
    
    Select Case KeyCode
        Case vbKeyDelete
            lbUnits.RemoveItem lbUnits.ListIndex
        Case vbKeyDown
            If lbUnits.ListIndex = (lbUnits.ListCount - 1) Then Exit Sub
            i = lbUnits.ListIndex
            i2 = i + 1
            
            strUnit = lbUnits.List(i, 0)
            strQ = lbUnits.List(i, 1)
            strNote = lbUnits.List(i, 2)
            
            lbUnits.List(i, 0) = lbUnits.List(i2, 0)
            lbUnits.List(i, 1) = lbUnits.List(i2, 1)
            lbUnits.List(i, 2) = lbUnits.List(i2, 2)
            
            lbUnits.List(i2, 0) = strUnit
            lbUnits.List(i2, 1) = strQ
            lbUnits.List(i2, 2) = strNote
        Case vbKeyUp
            If lbUnits.ListIndex = 0 Then Exit Sub
            i = lbUnits.ListIndex
            i2 = i - 1
            
            strUnit = lbUnits.List(i, 0)
            strQ = lbUnits.List(i, 1)
            strNote = lbUnits.List(i, 2)
            
            lbUnits.List(i, 0) = lbUnits.List(i2, 0)
            lbUnits.List(i, 1) = lbUnits.List(i2, 1)
            lbUnits.List(i, 2) = lbUnits.List(i2, 2)
            
            lbUnits.List(i2, 0) = strUnit
            lbUnits.List(i2, 1) = strQ
            lbUnits.List(i2, 2) = strNote
    End Select
End Sub

Private Sub UserForm_Initialize()
    lbUnits.ColumnCount = 3
    lbUnits.ColumnWidths = "96;36;44"
    
    lbEUnits.ColumnCount = 3
    lbEUnits.ColumnWidths = "96;36;44"

End Sub

Private Function GetExistingIndex(strItem As String)
    If lbEUnits.ListCount < 1 Then Exit Function
    
    Dim iIndex As Integer
    
    For iIndex = 0 To lbEUnits.ListCount - 1
        If InStr(lbEUnits.List(iIndex, 0), strItem) > 0 Then GoTo Found_Index
    Next iIndex
    
    iIndex = -1
    
Found_Index:
    
    GetExistingIndex = iIndex
End Function

Private Function GetProposedIndex(strItem As String)
    If lbUnits.ListCount < 1 Then Exit Function
    
    Dim iIndex As Integer
    
    For iIndex = 0 To lbUnits.ListCount - 1
        If InStr(lbUnits.List(iIndex, 0), strItem) > 0 Then GoTo Found_Index
    Next iIndex
    
    iIndex = -1
    
Found_Index:
    
    GetProposedIndex = iIndex
End Function

Private Function GetCoilIndex(strItem As String)
    If lbUnits.ListCount < 1 Then Exit Function
    
    Dim iIndex As Integer
    
    For iIndex = 0 To lbUnits.ListCount - 1
        If InStr(lbUnits.List(iIndex, 0), strItem) > 0 Then
            If InStr(lbUnits.List(iIndex, 2), "LOOP") > 0 Then GoTo Found_Index
        End If
    Next iIndex
    
    iIndex = -1
    
Found_Index:
    
    GetCoilIndex = iIndex
End Function

Attribute VB_Name = "AddTextToPoles"
Attribute VB_Base = "0{02B3EBD5-AA67-4028-8A96-52022E86C8BB}{E2047D02-8852-4A00-93E0-EB7D30DC45BD}"
Attribute VB_GlobalNameSpace = False
Attribute VB_Creatable = False
Attribute VB_PredeclaredId = True
Attribute VB_Exposed = False
Attribute VB_TemplateDerived = False
Attribute VB_Customizable = False
Private Sub cbAddToPole_Click()
    Dim objMText As AcadMText
    Dim objBlock As AcadBlockReference
    Dim objEntity As AcadEntity
    Dim vAttList As Variant
    Dim vReturnPnt As Variant
    Dim strLine As String
    Dim vLine, vItem As Variant
    Dim iCOMM As Integer
    
    On Error Resume Next
    Me.Hide
    
Get_Data:
    
    ThisDrawing.Utility.GetEntity objEntity, vReturnPnt, vbCr & "Select MText:"
    If Not Err = 0 Then GoTo Exit_Sub
    If Not TypeOf objEntity Is AcadMText Then GoTo Exit_Sub
    
    Set objMText = objEntity
    strLine = UCase(objMText.TextString)
    strLine = Replace(strLine, "\P", vbCr)
    strLine = Replace(strLine, vbLf, vbCr)
    strLine = Replace(strLine, vbTab, "")
    strLine = Replace(strLine, ": ", ":")
    strLine = Replace(strLine, "= ", "=")
    vLine = Split(strLine, vbCr)
    'tbMText.Value = strLine
    'MsgBox UBound(vLine) & vbCr & vbCr & strLine
    
    ThisDrawing.Utility.GetEntity objEntity, vReturnPnt, vbCr & "Select a Block:"
    If Not Err = 0 Then GoTo Exit_Sub
    If Not TypeOf objEntity Is AcadBlockReference Then GoTo Exit_Sub
    
    Set objBlock = objEntity
    Select Case objBlock.Name
        Case "sPole"
            vAttList = objBlock.GetAttributes
            iCOMM = 1
            
            For i = 0 To UBound(vLine)
                If InStr(vLine(i), tbStatus.Value) > 0 Then
                    vItem = Split(vLine(i), tbStatus.Value)
                    If vItem(0) = "" Then
                        vAttList(1).TextString = vItem(1)
                        GoTo Next_line
                    End If
                End If
                
                If InStr(vLine(i), tbOwner.Value) > 0 Then
                    vItem = Split(vLine(i), tbOwner.Value)
                    If vItem(0) = "" Then
                        vAttList(2).TextString = vItem(1)
                        GoTo Next_line
                    End If
                End If
                
                If InStr(vLine(i), tbOwnerNumber.Value) > 0 Then
                    vItem = Split(vLine(i), tbOwnerNumber.Value)
                    If vItem(0) = "" Then
                        vAttList(3).TextString = vItem(1)
                        GoTo Next_line
                    End If
                End If
                
                If InStr(vLine(i), tbOtherNumber.Value) > 0 Then
                    vItem = Split(vLine(i), tbOtherNumber.Value)
                    If vItem(0) = "" Then
                        vAttList(4).TextString = vItem(1)
                        GoTo Next_line
                    End If
                End If
                
                If InStr(vLine(i), tbHC.Value) > 0 Then
                    vItem = Split(vLine(i), tbHC.Value)
                    If vItem(0) = "" Then
                        vAttList(5).TextString = vItem(1)
                        GoTo Next_line
                    End If
                End If
                
                If InStr(vLine(i), tbGRD.Value) > 0 Then
                    vItem = Split(vLine(i), tbGRD.Value)
                    If vItem(0) = "" Then
                        vAttList(8).TextString = vItem(1)
                        GoTo Next_line
                    End If
                End If
                
                If InStr(vLine(i), tbN.Value) > 0 Then
                    vItem = Split(vLine(i), tbN.Value)
                    If vItem(0) = "" Then
                        vAttList(9).TextString = vItem(1)
                        GoTo Next_line
                    End If
                End If
                
                If InStr(vLine(i), tbT.Value) > 0 Then
                    vItem = Split(vLine(i), tbT.Value)
                    If vItem(0) = "" Then
                        vAttList(10).TextString = vItem(1)
                        GoTo Next_line
                    End If
                End If
                
                If InStr(vLine(i), tbLP.Value) > 0 Then
                    vItem = Split(vLine(i), tbLP.Value)
                    If vItem(0) = "" Then
                        vAttList(11).TextString = vItem(1)
                        GoTo Next_line
                    End If
                End If
                
                If InStr(vLine(i), tbA.Value) > 0 Then
                    vItem = Split(vLine(i), tbA.Value)
                    If vItem(0) = "" Then
                        vAttList(12).TextString = vItem(1)
                        GoTo Next_line
                    End If
                End If
                
                If InStr(vLine(i), tbSLC.Value) > 0 Then
                    vItem = Split(vLine(i), tbSLC.Value)
                    If vItem(0) = "" Then
                        vAttList(13).TextString = vItem(1)
                        GoTo Next_line
                    End If
                End If
                
                If InStr(vLine(i), tbSL.Value) > 0 Then
                    vItem = Split(vLine(i), tbSL.Value)
                    If vItem(0) = "" Then
                        vAttList(14).TextString = vItem(1)
                        GoTo Next_line
                    End If
                End If
                
                If InStr(vLine(i), tbNew.Value) > 0 Then
                    vItem = Split(vLine(i), tbNew.Value)
                    If vItem(0) = "" Then
                        vAttList(15).TextString = vItem(1)
                        GoTo Next_line
                    End If
                End If
                
                vAttList(15 + iCOMM).TextString = vLine(i)
                iCOMM = iCOMM + 1
                
Next_line:
            Next i
            
            objBlock.Update
        Case "cable_span"
            vAttList = objBlock.GetAttributes
            vAttList(0).TextString = vLine(0)
            objBlock.Update
        Case "Existing_Guys"
            vAttList = objBlock.GetAttributes
            iCOMM = 2
            
            For i = 0 To UBound(vLine)
                If InStr(vLine(i), tbAStatus.Value) > 0 Then
                    vItem = Split(vLine(i), tbAStatus.Value)
                    If vItem(0) = "" Then
                        vAttList(9).TextString = vItem(1)
                        GoTo Next_Line2
                    End If
                End If
                
                If InStr(vLine(i), tbAOffset.Value) > 0 Then
                    vItem = Split(vLine(i), tbAOffset.Value)
                    If vItem(0) = "" Then
                        vAttList(8).TextString = vItem(1)
                        GoTo Next_Line2
                    End If
                End If
                
                If InStr(vLine(i), tbAPower.Value) > 0 Then
                    vItem = Split(vLine(i), tbAPower.Value)
                    If vItem(0) = "" Then
                        vAttList(0).TextString = vItem(1)
                        GoTo Next_Line2
                    End If
                End If
                
                If InStr(vLine(i), tbANew.Value) > 0 Then
                    vItem = Split(vLine(i), tbANew.Value)
                    If vItem(0) = "" Then
                        vAttList(1).TextString = vItem(1)
                        GoTo Next_Line2
                    End If
                End If
                
                vAttList(iCOMM).TextString = vLine(i)
                iCOMM = iCOMM + 1
                
Next_Line2:
            Next i
        Case ""
        Case Else
            GoTo Exit_Sub
    End Select
    
    GoTo Get_Data
    
Exit_Sub:
    
    Me.show
End Sub

Private Sub cbGetText_Click()
    Dim objMText As AcadMText
    Dim objEntity As AcadEntity
    Dim vReturnPnt As Variant
    Dim strLine As String
    
    On Error Resume Next
    Me.Hide
    
    ThisDrawing.Utility.GetEntity objEntity, vReturnPnt, vbCr & "Select MText:"
    If Not Err = 0 Then GoTo Exit_Sub
    If Not TypeOf objEntity Is AcadMText Then GoTo Exit_Sub
    
    Set objMText = objEntity
    strLine = UCase(objMText.TextString)
    'tbMText.Value = strLine
    strLine = Replace(strLine, vbLf, vbCr)
    strLine = Replace(strLine, vbTab, "")
    strLine = Replace(strLine, ": ", ":")
    strLine = Replace(strLine, "= ", "=")
    tbMText.Value = Replace(strLine, "\P", vbCr)
        
Exit_Sub:
        
        Me.show
End Sub

Attribute VB_Name = "ArcViewCable"
Attribute VB_Base = "0{523471C4-6B5B-4B5C-8B92-2F5BC77BE7AF}{6F906ED8-BD4F-45A0-AB21-412A4385F042}"
Attribute VB_GlobalNameSpace = False
Attribute VB_Creatable = False
Attribute VB_PredeclaredId = True
Attribute VB_Exposed = False
Attribute VB_TemplateDerived = False
Attribute VB_Customizable = False


Private Sub cbAddData_Click()
    Dim amap As AcadMap
    Dim tbl As ODTable
    Dim tbls As ODTables
    Dim ODRcs As ODRecords
    Dim ODRc As ODRecord
    Dim boolVal As Boolean
    
    Dim objEntity As AcadEntity
    Dim vReturnPnt As Variant
    Dim objLine As AcadLine
    Dim objLWP As AcadLWPolyline
    Dim iLength As Integer
    Dim strCounts As String
    
    Me.Hide
    
    strCounts = Replace(tbCounts.Value, vbCr, " + ")
    strCounts = Replace(strCounts, vbLf, "")
    
    Set amap = ThisDrawing.Application.GetInterfaceObject("AutoCADMap.Application")
    
    Set tbls = amap.Projects(ThisDrawing).ODTables
    If tbls.count > 0 Then
        For Each tbl In tbls
            If tbl.Name = "Cables" Then GoTo Exit_For
        Next
    End If
    
    MsgBox "Object Data Table not found."
    GoTo Exit_Sub
    
Exit_For:
    
    ThisDrawing.Utility.GetEntity objEntity, vReturnPnt, "Select Cable: "
    
    If TypeOf objEntity Is AcadLine Then
        Set objLine = objEntity
        iLength = CInt(objLine.Length + 0.5)
    ElseIf TypeOf objEntity Is AcadLWPolyline Then
        Set objLWP = objEntity
        iLength = CInt(objLWP.Length + 0.5)
    Else
        MsgBox "Wrong type of Entity."
        GoTo Exit_Sub
    End If
    
    Set ODRcs = tbl.GetODRecords
            
    boolVal = ODRcs.Init(objEntity, True, False)
    Set ODRc = ODRcs.Record
    
    ODRc.Item(0).Value = tbCable.Value
    ODRc.Item(1).Value = iLength
    ODRc.Item(2).Value = strCounts
    
    boolVal = ODRcs.Update(ODRc)
    
    'GoTo Exit_For
    
Exit_Sub:
    Me.show
End Sub

Private Sub cbAddLines_Click()
    Dim objObject As AcadObject
    Dim objBlock As AcadBlockReference
    Dim vAttList As Variant
    Dim basePnt As Variant
    Dim X(0 To 2), Y(0 To 2), Z(0 To 2) As Double
    Dim leaderPnt(0 To 3) As Double
    Dim counter, iTemp As Integer
    Dim lineObj As AcadLWPolyline
    Dim layerObj As AcadLayer
    Dim strCommand As String
    
    Me.Hide
    ThisDrawing.SetVariable "CMDDIA", 0
    
  On Error Resume Next
    Set layerObj = ThisDrawing.Layers.Add("Cables - Aerial")
    ThisDrawing.ActiveLayer = layerObj
    
    ThisDrawing.Utility.GetEntity objObject, basePnt, "From Pole: "
    If TypeOf objObject Is AcadBlockReference Then
        Set objBlock = objObject
    Else
        GoTo Exit_While
    End If
    X(1) = objBlock.InsertionPoint(0)
    Y(1) = objBlock.InsertionPoint(1)
    Z(1) = 0#
    
    ThisDrawing.Utility.GetEntity objObject, basePnt, "To Pole: "
    If TypeOf objObject Is AcadBlockReference Then
        Set objBlock = objObject
    Else
        GoTo Exit_While
    End If
    If Not Err = 0 Then GoTo Exit_While
    
    X(0) = objBlock.InsertionPoint(0)
    Y(0) = objBlock.InsertionPoint(1)
    Z(0) = 0#
    X(2) = X(0)
    Y(2) = Y(0)
    
    leaderPnt(0) = X(1)
    leaderPnt(1) = Y(1)
    leaderPnt(2) = X(0)
    leaderPnt(3) = Y(0)
    
    Set lineObj = ThisDrawing.ModelSpace.AddLightWeightPolyline(leaderPnt)
    lineObj.Update
    
    strCommand = "_adeattachdata" & vbCr & "Cables" & vbCr & "a" & vbCr & "n" & vbCr & "l" & vbCr & vbCr & vbCr
    ThisDrawing.SendCommand strCommand
    
    
    
    
    
    
    
    Select Case objBlock.Name
        Case "sPED", "sHH"
            vAttList = objBlock.GetAttributes
            
            If vAttList(7).TextString = "" Then
                vAttList(7).TextString = "+" & tbCable.Value & "="
            Else
                vAttList(7).TextString = vAttList(7).TextString & ";;" & "+" & tbCable.Value & "="
            End If
        Case "sPole"
            vAttList = objBlock.GetAttributes
            
            If vAttList(27).TextString = "" Then
                vAttList(27).TextString = "+" & tbCable.Value & "="
            Else
                vAttList(27).TextString = vAttList(27).TextString & ";;" & "+" & tbCable.Value & "="
            End If
    End Select
    
    
    
    
    
    
    
    
    Err = 0
    
    While Err = 0
        X(1) = X(0)
        Y(1) = Y(0)
        
        Err = 0
        
        ThisDrawing.Utility.GetEntity objObject, basePnt, "To Pole: "
        
        If Not Err = 0 Then GoTo Exit_While
        
        If TypeOf objObject Is AcadBlockReference Then
            Set objBlock = objObject
        Else
            GoTo Exit_While
        End If
        
        X(0) = objBlock.InsertionPoint(0)
        Y(0) = objBlock.InsertionPoint(1)
    
        leaderPnt(0) = X(1)
        leaderPnt(1) = Y(1)
        leaderPnt(2) = X(0)
        leaderPnt(3) = Y(0)
    
        Set lineObj = ThisDrawing.ModelSpace.AddLightWeightPolyline(leaderPnt)
        lineObj.Update
        
        ThisDrawing.SendCommand strCommand
    Wend
    
Exit_While:
    ThisDrawing.SetVariable "CMDDIA", 1
    Me.show
End Sub

Private Sub cbCancel_Click()
    tbCounts.Value = ""
    
    Me.Hide
End Sub

Private Sub cbGet_Click()
    Dim objEntity As AcadEntity
    Dim objBlock As AcadBlockReference
    Dim vAttList, vReturnPnt As Variant
    Dim vLine As Variant
    
    On Error Resume Next
    
    Me.Hide
        
    ThisDrawing.Utility.GetEntity objEntity, vReturnPnt, "Select Cable Callout: "
        
    If Not Err = 0 Then GoTo Exit_Sub
    
    If TypeOf objEntity Is AcadBlockReference Then
        Set objBlock = objEntity
    Else
        GoTo Exit_Sub
    End If
    
    If Not objBlock.Name = "CableCounts" Then GoTo Exit_Sub
    
    vAttList = objBlock.GetAttributes
    
    tbCable.Value = vAttList(1).TextString
    tbCounts.Value = Replace(vAttList(0).TextString, "\P", vbCr)
Exit_Sub:
    Me.show
End Sub

Private Sub cbUpdate_Click()
    Me.Hide
End Sub

Attribute VB_Name = "ArcViewCustomer"
Attribute VB_Base = "0{5B844021-0EA2-41F1-A30E-46A5DDB19A7D}{C64488A4-DF73-4F4A-8715-748C7422C898}"
Attribute VB_GlobalNameSpace = False
Attribute VB_Creatable = False
Attribute VB_PredeclaredId = True
Attribute VB_Exposed = False
Attribute VB_TemplateDerived = False
Attribute VB_Customizable = False
Private Sub cbClear_Click()
    lbCustomers.Clear
End Sub

Private Sub cbConvert_Click()
    Dim objSSTemp4 As AcadSelectionSet
    Dim entItem As AcadEntity
    Dim obrTemp, objBlock As AcadBlockReference
    Dim attList, vAttList2 As Variant
    Dim vTemp As Variant
    Dim filterType, filterValue As Variant
    Dim vPnt1, vPnt2 As Variant
    Dim grpCode(0) As Integer
    Dim grpValue(0) As Variant
    Dim dPnt1(0 To 2) As Double
    Dim dPnt2(0 To 2) As Double
    Dim strType, strSymbol As String

    grpCode(0) = 2
    grpValue(0) = "RES,BUSINESS,TRLR,MDU,SCHOOL,CHURCH,LOT"
    filterType = grpCode
    filterValue = grpValue
    
  On Error Resume Next
    Me.Hide
    vPnt1 = ThisDrawing.Utility.GetPoint(, "Get BL Corner: ")
    vPnt2 = ThisDrawing.Utility.GetCorner(vPnt1, vbCr & "Get UR Corner: ")
    
    dPnt1(0) = vPnt1(0)
    dPnt1(1) = vPnt1(1)
    dPnt1(2) = vPnt1(2)
    
    dPnt2(0) = vPnt2(0)
    dPnt2(1) = vPnt2(1)
    dPnt2(2) = vPnt2(2)
  
    'Err = 0
    
    Set objSSTemp4 = ThisDrawing.SelectionSets.Add("objSSTemp4")
    If Not Err = 0 Then
        Set objSSTemp4 = ThisDrawing.SelectionSets.Item("objSSTemp4")
        Err = 0
    End If
    objSSTemp4.Select acSelectionSetWindow, dPnt1, dPnt2, filterType, filterValue
    
    For Each entItem In objSSTemp4
        If TypeOf entItem Is AcadBlockReference Then
            Set obrTemp = entItem
            
            'If obrTemp.Layer = "Integrity Future" Then GoTo Next_Object
            
            Select Case obrTemp.Name
                Case "RES"
                    strType = "RESIDENCE"
                    strSymbol = ""
                Case "TRLR"
                    strType = "TRAILER"
                    strSymbol = "T"
                Case "BUSINESS", "SCHOOL", "CHURCH", "MDU", "LOT", "VACANT", "ABANDONED"
                    strType = obrTemp.Name
                    strSymbol = Left(strType, 1)
                Case Else
                    GoTo Next_Object
            End Select
            
            attList = obrTemp.GetAttributes
            vTemp = obrTemp.InsertionPoint
            
            Set objBlock = ThisDrawing.ModelSpace.InsertBlock(vTemp, "Customer", 1#, 1#, 1#, 0#)
            objBlock.Layer = "Customers"
            
            vAttList2 = objBlock.GetAttributes
            vAttList2(0).TextString = strType
            vAttList2(1).TextString = attList(0).TextString
            vAttList2(2).TextString = attList(1).TextString
            vAttList2(3).TextString = attList(2).TextString
            vAttList2(4).TextString = ""
            vAttList2(5).TextString = strSymbol
            
            objBlock.Update
        End If
Next_Object:
    Next entItem
    
Exit_Sub:
    objSSTemp4.Clear
    objSSTemp4.Delete
    Me.show
End Sub

Private Sub cbGetCustomers_Click()
    Dim objSSTemp4 As AcadSelectionSet
    Dim entItem As AcadEntity
    Dim obrTemp, objBlock As AcadBlockReference
    Dim vAttList, vAttList2 As Variant
    Dim vTemp As Variant
    Dim filterType, filterValue As Variant
    Dim vPnt1, vPnt2 As Variant
    Dim grpCode(0) As Integer
    Dim grpValue(0) As Variant
    Dim dPnt1(0 To 2) As Double
    Dim dPnt2(0 To 2) As Double
    Dim strType, strSymbol As String
    Dim strTemp As String
    Dim iIndex As Integer

    grpCode(0) = 2
    grpValue(0) = "Customer"
    filterType = grpCode
    filterValue = grpValue
    
  On Error Resume Next
    Me.Hide
    vPnt1 = ThisDrawing.Utility.GetPoint(, "Get BL Corner: ")
    vPnt2 = ThisDrawing.Utility.GetCorner(vPnt1, vbCr & "Get UR Corner: ")
    
    dPnt1(0) = vPnt1(0)
    dPnt1(1) = vPnt1(1)
    dPnt1(2) = vPnt1(2)
    
    dPnt2(0) = vPnt2(0)
    dPnt2(1) = vPnt2(1)
    dPnt2(2) = vPnt2(2)
  
    'Err = 0
    
    Set objSSTemp4 = ThisDrawing.SelectionSets.Add("objSSTemp4")
    If Not Err = 0 Then
        Set objSSTemp4 = ThisDrawing.SelectionSets.Item("objSSTemp4")
        Err = 0
    End If
    objSSTemp4.Select acSelectionSetWindow, dPnt1, dPnt2, filterType, filterValue
    
    For Each entItem In objSSTemp4
        If TypeOf entItem Is AcadBlockReference Then
            Set obrTemp = entItem
            
            vAttList = obrTemp.GetAttributes
            
            If vAttList(4).TextString = "" Then
                strTemp = "<empty> - <empty>"
            Else
                strTemp = vAttList(4).TextString
            End If
            
            If InStr(strTemp, " (") > 0 Then
                strTemp = Replace(strTemp, " (", " RC ")
                strTemp = Replace(strTemp, ")", "")
            End If
            
            vTemp = Split(strTemp, " - ")
            lbCustomers.AddItem vTemp(0)
            
            iIndex = lbCustomers.ListCount - 1
            lbCustomers.List(iIndex, 1) = vTemp(1)
            lbCustomers.List(iIndex, 2) = vAttList(1).TextString
            lbCustomers.List(iIndex, 3) = vAttList(2).TextString
            If Not vAttList(0).TextString = "" Then lbCustomers.List(iIndex, 4) = vAttList(3).TextString
            lbCustomers.List(iIndex, 5) = vAttList(0).TextString
        End If
    Next entItem
    
Exit_Sub:
    objSSTemp4.Clear
    objSSTemp4.Delete
    Me.show
End Sub

Private Sub cbQuit_Click()
    Me.Hide
End Sub

Private Sub Label42_Click()
    If lbCustomers.ListCount = 0 Then Exit Sub
    
    Dim strPole1, strCount, strHSE As String
    Dim strRoad, strNote, strType As String
    Dim strTest1, strTest2 As String
    Dim vTest As Variant
    
    Dim strPole2, strOwner2, strDWG2 As String
    Dim strLower2, strRTA2 As Integer
    Dim iCount, iOffset As Integer
    Dim iIndex As Integer
    
    On Error Resume Next
    Err = 0
    
    iCount = lbCustomers.ListCount - 1
    
    'For c = 0 To iCount
        'If IsNull(lbCustomers.List(c, 0)) Then lbCustomers.List(c, 0) = "-"
        'If IsNull(lbCustomers.List(c, 1)) Then lbCustomers.List(c, 1) = "-"
        'If IsNull(lbCustomers.List(c, 2)) Then lbCustomers.List(c, 2) = "0"
        'If IsNull(lbCustomers.List(c, 3)) Then lbCustomers.List(c, 3) = "0"
        'If IsNull(lbCustomers.List(c, 4)) Then lbCustomers.List(c, 4) = "-"
        
        'If lbCustomers.List(c, 0) = "" Then lbCustomers.List(c, 0) = "-"
        'If lbCustomers.List(c, 1) = "" Then lbCustomers.List(c, 1) = "-"
        'If lbCustomers.List(c, 2) = "" Then lbCustomers.List(c, 2) = "0"
        'If lbCustomers.List(c, 3) = "" Then lbCustomers.List(c, 3) = "0"
        'If lbCustomers.List(c, 4) = "" Then lbCustomers.List(c, 4) = "-"
    'Next c
    
    For a = iCount To 1 Step -1
        For b = 0 To a - 1
            strTest1 = Replace(lbCustomers.List(b, 1), ")", "")
            vTest = Split(strTest1, ": ")
            strTest1 = vTest(1)
            
            strTest2 = Replace(lbCustomers.List(b + 1, 1), ")", "")
            vTest = Split(strTest2, ": ")
            strTest2 = vTest(1)
                        
            'If lbCustomers.List(b, 1) > lbCustomers.List(b + 1, 1) Then
            If CInt(strTest1) > CInt(strTest2) Then
                strPole1 = lbCustomers.List(b + 1, 0)
                strCount = lbCustomers.List(b + 1, 1)
                strHSE = lbCustomers.List(b + 1, 2)
                strRoad = lbCustomers.List(b + 1, 3)
                strNote = lbCustomers.List(b + 1, 4)
                strType = lbCustomers.List(b + 1, 5)
                
                lbCustomers.List(b + 1, 0) = lbCustomers.List(b, 0)
                lbCustomers.List(b + 1, 1) = lbCustomers.List(b, 1)
                lbCustomers.List(b + 1, 2) = lbCustomers.List(b, 2)
                lbCustomers.List(b + 1, 3) = lbCustomers.List(b, 3)
                lbCustomers.List(b + 1, 4) = lbCustomers.List(b, 4)
                lbCustomers.List(b + 1, 5) = lbCustomers.List(b, 5)
                                
                lbCustomers.List(b, 0) = strPole1
                lbCustomers.List(b, 1) = strCount
                lbCustomers.List(b, 2) = strHSE
                lbCustomers.List(b, 3) = strRoad
                lbCustomers.List(b, 4) = strNote
                lbCustomers.List(b, 5) = strType
            End If
        Next b
    Next a
End Sub

Private Sub UserForm_Initialize()
    lbCustomers.ColumnCount = 6
    lbCustomers.ColumnWidths = "102;90;36;140;114;68"
End Sub

Attribute VB_Name = "ArcViewPole"
Attribute VB_Base = "0{4087B3E3-8B9E-40EE-BA6B-FB27C1E19D96}{44B64E32-24FD-4F6A-B036-3CA06989893C}"
Attribute VB_GlobalNameSpace = False
Attribute VB_Creatable = False
Attribute VB_PredeclaredId = True
Attribute VB_Exposed = False
Attribute VB_TemplateDerived = False
Attribute VB_Customizable = False

Dim objPole As AcadBlockReference

Private Sub cbAddAttach_Click()
    Dim strMR As String
    
    If cbAddAttach.Caption = "Update" Then
        lbAttach.List(lbAttach.ListIndex, 0) = cbAttachment.Value
        lbAttach.List(lbAttach.ListIndex, 1) = tbEAttach.Value
        lbAttach.List(lbAttach.ListIndex, 2) = tbPAttach.Value
        
        cbAddAttach.Caption = "Add Data"
        GoTo Exit_Sub
    End If
    
    lbAttach.AddItem cbAttachment.Value
    lbAttach.List(lbAttach.ListCount - 1, 1) = tbEAttach.Value
    lbAttach.List(lbAttach.ListCount - 1, 2) = tbPAttach.Value
    
    lbAttach.ListIndex = lbAttach.ListCount - 1
    
Exit_Sub:
    If tbPAttach.Value = "" Then
        strMR = ""
    Else
        strMR = GetMR(CStr(tbEAttach.Value), CStr(tbPAttach.Value))
    End If
    
    lbAttach.List(lbAttach.ListIndex, 3) = strMR
    
    cbAttachment.Value = ""
    tbEAttach.Value = ""
    tbPAttach.Value = ""
End Sub

Private Sub cbAddCable_Click()
    Load ArcViewPoleCable
    
        ArcViewPoleCable.show
        
        If Not ArcViewPoleCable.tbCounts.Value = "" Then
            lbCables.AddItem ArcViewPoleCable.tbCable.Value
            lbCables.List(lbCables.ListCount - 1, 1) = Replace(ArcViewPoleCable.tbCounts.Value, vbCr, " + ")
            lbCables.List(lbCables.ListCount - 1, 1) = Replace(lbCables.List(lbCables.ListCount - 1, 1), vbLf, "")
        End If
        
    Unload ArcViewPoleCable
End Sub

Private Sub cbAddData_Click()
    If cbAddData.Caption = "Update" Then
        lbData.List(lbData.ListIndex, 1) = tbDValue.Value
        
        cbDType.Value = ""
        cbDType.Enabled = True
        tbDValue.Value = ""
        
        cbAddData.Caption = "Add Data"
        Exit Sub
    End If
    
    Select Case cbDType.Value
        Case "H-C"
            lbData.AddItem "1  H-C"
        Case "Owner #"
            lbData.AddItem "2  Owner #"
        Case "Other #"
            lbData.AddItem "3  Other #"
        Case "Ground"
            lbData.AddItem "9  Ground"
    End Select
    lbData.List(lbData.ListCount - 1, 1) = tbDValue.Value
    
    cbDType.Value = ""
    tbDValue.Value = ""
End Sub

Private Sub cbAddSplice_Click()
    If cbAddSplice.Caption = "Update" Then
        lbSplices.List(lbSplices.ListIndex) = tbSValue.Value
        
        tbSValue.Value = ""
        
        cbAddSplice.Caption = "Add Splice"
        Exit Sub
    End If
    
    If tbSValue.Value = "" Then Exit Sub
    lbSplices.List(lbSplices.ListCount - 1) = tbSValue.Value
    
    tbSValue.Value = ""
End Sub

Private Sub cbAddUnit_Click()
    If cbAddUnit.Caption = "Update" Then
        lbUnits.List(lbUnits.ListIndex, 0) = tbUnit.Value
        lbUnits.List(lbUnits.ListIndex, 1) = tbQuantity.Value
        lbUnits.List(lbUnits.ListIndex, 2) = tbUNote.Value
        
        cbAddUnit.Caption = "Add Unit"
        GoTo Exit_Sub
    End If
    
    lbUnits.AddItem tbUnit.Value
    lbUnits.List(lbUnits.ListCount - 1, 1) = tbQuantity.Value
    lbUnits.List(lbUnits.ListCount - 1, 2) = tbUNote.Value
    
Exit_Sub:
    
    tbUnit.Value = ""
    tbQuantity.Value = ""
    tbUNote.Value = ""
End Sub

Private Sub cbGetAttachemnt_Click()
    Dim objSS As AcadSelectionSet
    Dim objEntity As AcadEntity
    Dim objBlock As AcadBlockReference
    Dim vAttList, vLine, vItem As Variant
    Dim strTemp, strLine As String
    Dim iFeet, iInch, iTotal, iRL As Integer
    
    Me.Hide
    
  On Error Resume Next
    
    Set objSS = ThisDrawing.SelectionSets.Add("objSS")
    If Not Err = 0 Then Set objSS = ThisDrawing.SelectionSets.Item("objSS")
        
    objSS.SelectOnScreen
    For Each objEntity In objSS
        If Not TypeOf objEntity Is AcadBlockReference Then GoTo Next_objEntity
        
        Set objBlock = objEntity
        If objBlock.Name = "pole_attach" Then
            vAttList = objBlock.GetAttributes
            
            lbAttach.AddItem vAttList(2).TextString, 0
            
            strTemp = Replace(vAttList(3).TextString, "'", "-")
            strTemp = Replace(strTemp, """", "")
            
            If vAttList(4).TextString = "" Then
                lbAttach.List(0, 1) = strTemp
                lbAttach.List(0, 2) = ""
            Else
                Select Case Left(vAttList(4).TextString, 1)
                    Case "N"
                        lbAttach.List(0, 1) = ""
                        lbAttach.List(0, 2) = strTemp
                    Case "A"
                        lbAttach.List(0, 1) = "X"
                        lbAttach.List(0, 2) = strTemp
                    Case "R", "L"
                        lbAttach.List(0, 2) = strTemp
                        
                        vLine = Split(strTemp, "-")
                        iFeet = CInt(vLine(0))
                        If UBound(vLine) < 1 Then
                            iInch = 0
                        Else
                            iInch = CInt(vLine(1))
                        End If
                        iTotal = iFeet * 12 + iInch
                        
                        vLine = Split(vAttList(4).TextString, " ")
                        strLine = Replace(vLine(1), """", "")
                        
                        If Left(vAttList(4).TextString, 1) = "R" Then
                            iRL = 0 - CInt(strLine)
                        Else
                            iRL = CInt(strLine)
                        End If
                        
                        iTotal = iTotal + iRL
                        iFeet = Int(iTotal / 12)
                        iInch = iTotal - (iFeet * 12)
                        
                        lbAttach.List(0, 1) = iFeet & "-" & iInch
                    Case "T"
                        lbAttach.List(0, 1) = strTemp
                        lbAttach.List(0, 2) = strTemp
                    Case Else
                        lbAttach.List(0, 1) = strTemp
                        lbAttach.List(0, 2) = ""
                End Select
            End If
            
            lbAttach.List(0, 3) = vAttList(4).TextString
        End If
        
        
Next_objEntity:
    Next objEntity
    
    objSS.Clear
    objSS.Delete
    
    Call SortAttachments
    
    Me.show
End Sub

Private Sub cbGetCables_Click()
    Dim objEntity As AcadEntity
    Dim objBlock As AcadBlockReference
    Dim vAttList, vBasePnt As Variant
    Dim strLine As String
    
    Me.Hide
    On Error Resume Next
    
    ThisDrawing.Utility.GetEntity objEntity, vBasePnt, "Get Cable Callout: "
    
    If Not Err = 0 Then GoTo Exit_Sub
    
    If Not TypeOf objEntity Is AcadBlockReference Then
        MsgBox "Invalid selection"
        GoTo Exit_Sub
    End If
    
    Set objBlock = objEntity
    
    If Not objBlock.Name = "CableCounts" Then
        MsgBox "Invalid block"
        Me.show
        Exit Sub
    End If
    
    vAttList = objBlock.GetAttributes
    
    lbCables.AddItem vAttList(1).TextString
    lbCables.List(lbCables.ListCount - 1, 1) = Replace(vAttList(0).TextString, "\P", " + ")
    
Exit_Sub:
    Me.show
End Sub

Private Sub cbGetClosures_Click()
    Dim objEntity As AcadEntity
    Dim objBlock As AcadBlockReference
    Dim vAttList, vBasePnt As Variant
    Dim vLine As Variant
    Dim strLine As String
    
    Me.Hide
    On Error Resume Next
    
    ThisDrawing.Utility.GetEntity objEntity, vBasePnt, "Get Closure Callout: "
    
    If Not Err = 0 Then GoTo Exit_Sub
    
    If Not TypeOf objEntity Is AcadBlockReference Then
        MsgBox "Invalid selection"
        GoTo Exit_Sub
    End If
    
    Set objBlock = objEntity
    
    If Not objBlock.Name = "terminal" Then
        MsgBox "Invalid block"
        GoTo Exit_Sub
    End If
    
    vAttList = objBlock.GetAttributes
    'vLine = Split(vAttList(0).TextString, "\P")
    
    'For j = 0 To UBound(vLine)
        'lbSplices.AddItem vLine(j)
    'Next j
    
    strLine = Replace(vAttList(0).TextString, "\P", " + ")
    lbSplices.AddItem strLine
    
Exit_Sub:
    Me.show
End Sub

Private Sub cbGetPole_Click()
    Dim objObject As AcadObject
    'Dim objBlock As AcadBlockReference
    Dim vBasePnt, vAttList As Variant
    Dim vLine, vItem As Variant
    Dim strTemp As String
    
    lbData.Clear
    lbAttach.Clear
    lbUnits.Clear
    lbCables.Clear
    lbSplices.Clear
    
    cbUpdatePole.Enabled = True
    
    Me.Hide
  On Error Resume Next
    
    ThisDrawing.Utility.GetEntity objObject, vBasePnt, "Select Pole: "
    If TypeOf objObject Is AcadBlockReference Then
        Set objPole = objObject
    Else
        MsgBox "Not a valid object."
        Me.show
        Exit Sub
    End If
    
    If Not objPole.Name = "iPole" Then
        MsgBox "Not a valid pole."
        Me.show
        Exit Sub
    End If
    
    vAttList = objPole.GetAttributes
    
    tbPoleNumber.Value = vAttList(0).TextString
    tbOwner.Value = vAttList(2).TextString
    
    lbData.AddItem "1  H-C"
    If vAttList(5).TextString = "" Then
        lbData.List(lbData.ListCount - 1, 1) = "?-?"
    Else
        lbData.List(lbData.ListCount - 1, 1) = vAttList(5).TextString
    End If
    
    
    
    If vAttList(3).TextString = "" Then
        lbData.AddItem "2  Owner #"
        lbData.List(lbData.ListCount - 1, 1) = "NA"
    Else
        vLine = Split(vAttList(3).TextString, " ")
        For j = 0 To UBound(vLine)
            If j = 0 Then
                lbData.AddItem "2  Owner #"
                lbData.List(lbData.ListCount - 1, 1) = vLine(j)
            Else
                lbData.AddItem "3  Other #"
                lbData.List(lbData.ListCount - 1, 1) = vLine(j)
            End If
        Next j
    End If
    
    
    
    If Not vAttList(4).TextString = "" Then
        vLine = Split(vAttList(4).TextString, " ")
        
        For i = 0 To UBound(vLine)
            vItem = Split(vLine(i), "=")
            
            If UBound(vItem) = 0 Then
                lbData.AddItem "3  Other #"
                lbData.List(lbData.ListCount - 1, 1) = "???  " & vLine(i)
            Else
                For j = 1 To UBound(vItem)
                    Select Case vItem(0)
                        Case "A"
                            vItem(0) = "ATT"
                        Case "CH"
                            vItem(0) = "CHARTER"
                        Case "CO"
                            vItem(0) = "COMCAST"
                        Case "D"
                            vItem(0) = "DREMC"
                        Case "M"
                            vItem(0) = "MTEMC"
                        Case "N"
                            vItem(0) = "NES"
                        Case "T"
                            vItem(0) = "TDS"
                    End Select
                    
                    lbData.AddItem "3  Other #"
                    lbData.List(lbData.ListCount - 1, 1) = vItem(0) & "  " & vItem(j)
                Next j
            End If
        Next i
    End If
    
    
    lbData.AddItem "9  Ground"
    Select Case UCase(vAttList(8).TextString)
        Case "", "N"
            lbData.List(lbData.ListCount - 1, 1) = "NO GRD"
        Case "M"
            lbData.List(lbData.ListCount - 1, 1) = "MGNV"
        Case "T"
            lbData.List(lbData.ListCount - 1, 1) = "TGB"
        Case "B"
            lbData.List(lbData.ListCount - 1, 1) = "BROKEN GRD"
        Case Else
            lbData.List(lbData.ListCount - 1, 1) = vAttList(8).TextString
    End Select
    
    Me.show
    Exit Sub
    '<---------------------------------------------------------------- not complete - Add Attachments
    Dim iFeet, iInch, iMax, iMin As Integer
    Dim str1 As String
    
    iMax = 1200
    iMin = 0
    
    For n = 9 To 26
        If vAttList(n).TextString = "" Then GoTo Next_N
        
        vLine = Split(vAttList(n).TextString, " ")
        
        Select Case n
            Case Is = 9
                For k = 0 To UBound(vLine)
                    lbAttach.AddItem "NEUTRAL"
                    lbAttach.List(lbAttach.ListCount - 1, 1) = vLine(k)
                    
                    vItem = Split(vLine(k), "-")
                    iFeet = CInt(vItem(0))
                    If UBound(vItem) < 1 Then
                        iInch = 0
                    Else
                        iInch = CInt(vItem(1))
                    End If
                    
                    If iMax > (iFeet * 12 + iInch) Then
                        iMax = iFeet * 12 + iInch - CInt(tbNeu.Value)
                        iFeet = Int(iMax / 12)
                        iInch = iMax - (iFeet * 12)
                    
                        tbMaxAtt.Value = iFeet & "-" & iInch
                    End If
                Next k
            Case Is = 10
                For k = 0 To UBound(vLine)
                    lbAttach.AddItem "TRANSFORMER"
                    lbAttach.List(lbAttach.ListCount - 1, 1) = vLine(k)
                    
                    vItem = Split(vLine(k), "-")
                    iFeet = CInt(vItem(0))
                    If UBound(vItem) < 1 Then
                        iInch = 0
                    Else
                        iInch = CInt(vItem(1))
                    End If
                    
                    If iMax > (iFeet * 12 + iInch - CInt(tbTrans.Value)) Then
                        iMax = iFeet * 12 + iInch - CInt(tbTrans.Value)
                        iFeet = Int(iMax / 12)
                        iInch = iMax - (iFeet * 12)
                    
                        tbMaxAtt.Value = iFeet & "-" & iInch
                    End If
                Next k
            Case Is = 11, Is = 12, Is = 13
                For k = 0 To UBound(vLine)
                    Select Case n
                        Case Is = 11
                            lbAttach.AddItem "LOW POWER"
                        Case Is = 11
                            lbAttach.AddItem "ANTENNA"
                        Case Is = 11
                            lbAttach.AddItem "ST LT CIR"
                    End Select
                    
                    lbAttach.List(lbAttach.ListCount - 1, 1) = vLine(k)
                    
                    vItem = Split(vLine(k), "-")
                    iFeet = CInt(vItem(0))
                    If UBound(vItem) < 1 Then
                        iInch = 0
                    Else
                        iInch = CInt(vItem(1))
                    End If
                    
                    If iMax > (iFeet * 12 + iInch - CInt(tbLP.Value)) Then
                        iMax = iFeet * 12 + iInch - CInt(tbLP.Value)
                        iFeet = Int(iMax / 12)
                        iInch = iMax - (iFeet * 12)
                    
                        tbMaxAtt.Value = iFeet & "-" & iInch
                    End If
                Next k
            Case Is = 14
                For k = 0 To UBound(vLine)
                    lbAttach.AddItem "ST LT"
                    lbAttach.List(lbAttach.ListCount - 1, 1) = vLine(k)
                    
                    vItem = Split(vLine(k), "-")
                    iFeet = CInt(vItem(0))
                    If UBound(vItem) < 1 Then
                        iInch = 0
                    Else
                        iInch = CInt(vItem(1))
                    End If
                    
                    If iMax > (iFeet * 12 + iInch - CInt(tbStLt.Value)) Then
                        iMax = iFeet * 12 + iInch - CInt(tbStLt.Value)
                        iFeet = Int(iMax / 12)
                        iInch = iMax - (iFeet * 12)
                    
                        tbMaxAtt.Value = iFeet & "-" & iInch
                    End If
                Next k
            Case Is = 15
                strTemp = "CATV"
                For k = 0 To UBound(vLine)
                    str1 = ""
                    If CInt(Left(vLine(j), 1)) < 1 Then
                        strTemp = vLine(j)
                        GoTo Next_CATV
                    End If
            
                    If Len(vLine(j)) < 3 Then vLine(j) = vLine(j) & "-0"
                    
                    If UCase(Right(vLine(j), 1)) = "X" Then
                        str1 = "ATTACH"
                        vLine(j) = Replace(vItem(j), "X", "")
                    End If
                    
                    If UCase(Right(vLine(j), 1)) = "C" Then
                        strTemp = strTemp & " C-WIRE"
                        vLine(j) = Replace(vItem(j), "C", "")
                    End If
                    
                    lbAttach.AddItem strTemp
                    lbAttach.List(lbAttach.ListCount - 1, 1) = vLine(j)
                    lbAttach.List(lbAttach.ListCount - 1, 2) = ""
                    lbAttach.List(lbAttach.ListCount - 1, 3) = str1
Next_CATV:
                Next k
            Case Is = 16
                strTemp = "ATT"
                For k = 0 To UBound(vLine)
                    str1 = ""
                    If CInt(Left(vLine(j), 1)) < 1 Then
                        strTemp = vLine(j)
                        GoTo Next_ATT
                    End If
            
                    If Len(vLine(j)) < 3 Then vLine(j) = vLine(j) & "-0"
                    
                    If UCase(Right(vLine(j), 1)) = "X" Then
                        str1 = "ATTACH"
                        vLine(j) = Replace(vItem(j), "X", "")
                    End If
                    
                    If UCase(Right(vLine(j), 1)) = "C" Then
                        strTemp = strTemp & " C-WIRE"
                        vLine(j) = Replace(vItem(j), "C", "")
                    End If
                    
                    lbAttach.AddItem strTemp
                    lbAttach.List(lbAttach.ListCount - 1, 1) = vLine(j)
                    lbAttach.List(lbAttach.ListCount - 1, 2) = ""
                    lbAttach.List(lbAttach.ListCount - 1, 3) = str1
Next_ATT:
                Next k
            Case Is = 17
                strTemp = "TDS"
                For k = 0 To UBound(vLine)
                    str1 = ""
                    If CInt(Left(vLine(j), 1)) < 1 Then
                        strTemp = vLine(j)
                        GoTo Next_TDS
                    End If
            
                    If Len(vLine(j)) < 3 Then vLine(j) = vLine(j) & "-0"
                    
                    If UCase(Right(vLine(j), 1)) = "X" Then
                        str1 = "ATTACH"
                        vLine(j) = Replace(vItem(j), "X", "")
                    End If
                    
                    If UCase(Right(vLine(j), 1)) = "C" Then
                        strTemp = strTemp & " C-WIRE"
                        vLine(j) = Replace(vItem(j), "C", "")
                    End If
                    
                    lbAttach.AddItem strTemp
                    lbAttach.List(lbAttach.ListCount - 1, 1) = vLine(j)
                    lbAttach.List(lbAttach.ListCount - 1, 2) = ""
                    lbAttach.List(lbAttach.ListCount - 1, 3) = str1
Next_TDS:
                Next k
            Case Is = 18
                strTemp = "UTC"
                For k = 0 To UBound(vLine)
                    str1 = ""
                    If CInt(Left(vLine(j), 1)) < 1 Then
                        strTemp = vLine(j)
                        GoTo Next_UTC
                    End If
            
                    If Len(vLine(j)) < 3 Then vLine(j) = vLine(j) & "-0"
                    
                    If UCase(Right(vLine(j), 1)) = "X" Then
                        str1 = "ATTACH"
                        vLine(j) = Replace(vItem(j), "X", "")
                    End If
                    
                    If UCase(Right(vLine(j), 1)) = "C" Then
                        strTemp = strTemp & " C-WIRE"
                        vLine(j) = Replace(vItem(j), "C", "")
                    End If
                    
                    lbAttach.AddItem strTemp
                    lbAttach.List(lbAttach.ListCount - 1, 1) = vLine(j)
                    lbAttach.List(lbAttach.ListCount - 1, 2) = ""
                    lbAttach.List(lbAttach.ListCount - 1, 3) = str1
Next_UTC:
                Next k
        End Select
        '<------------------------------------------------------------- Continue getting Pole Attachments
Next_N:
    Next n
    
    Me.show
End Sub

Private Sub cbGetsPole_Click()
    Dim objObject As AcadObject
    'Dim objBlock As AcadBlockReference
    Dim vBasePnt, vAttList As Variant
    Dim vLine, vItem, vTemp As Variant
    Dim strTemp As String
    
    lbData.Clear
    lbAttach.Clear
    lbUnits.Clear
    lbCables.Clear
    lbSplices.Clear
    
    cbUpdatePole.Enabled = True
    
    Me.Hide
  On Error Resume Next
    
    ThisDrawing.Utility.GetEntity objObject, vBasePnt, "Select Pole: "
    If TypeOf objObject Is AcadBlockReference Then
        Set objPole = objObject
    Else
        MsgBox "Not a valid object."
        Me.show
        Exit Sub
    End If
    
    If Not objPole.Name = "sPole" Then
        MsgBox "Not a valid pole."
        Me.show
        Exit Sub
    End If
    
    vAttList = objPole.GetAttributes
    
    tbPoleNumber.Value = vAttList(0).TextString
    tbOwner.Value = vAttList(2).TextString
    
    lbData.AddItem "1  H-C"
    If vAttList(5).TextString = "" Then
        lbData.List(lbData.ListCount - 1, 1) = "?-?"
    Else
        lbData.List(lbData.ListCount - 1, 1) = vAttList(5).TextString
    End If
    
    
    
    If vAttList(3).TextString = "" Then
        lbData.AddItem "2  Owner #"
        lbData.List(lbData.ListCount - 1, 1) = "NA"
    Else
        vLine = Split(vAttList(3).TextString, " ")
        For j = 0 To UBound(vLine)
            If j = 0 Then
                lbData.AddItem "2  Owner #"
                lbData.List(lbData.ListCount - 1, 1) = vLine(j)
            Else
                lbData.AddItem "3  Other #"
                lbData.List(lbData.ListCount - 1, 1) = vLine(j)
            End If
        Next j
    End If
    
    
    
    If Not vAttList(4).TextString = "" Then
        vLine = Split(vAttList(4).TextString, " ")
        
        For i = 0 To UBound(vLine)
            vItem = Split(vLine(i), "=")
            
            If UBound(vItem) = 0 Then
                lbData.AddItem "3  Other #"
                lbData.List(lbData.ListCount - 1, 1) = "???  " & vLine(i)
            Else
                For j = 1 To UBound(vItem)
                    Select Case vItem(0)
                        Case "A"
                            vItem(0) = "ATT"
                        Case "CH"
                            vItem(0) = "CHARTER"
                        Case "CO"
                            vItem(0) = "COMCAST"
                        Case "D"
                            vItem(0) = "DREMC"
                        Case "M"
                            vItem(0) = "MTEMC"
                        Case "N"
                            vItem(0) = "NES"
                        Case "T"
                            vItem(0) = "TDS"
                    End Select
                    
                    lbData.AddItem "3  Other #"
                    lbData.List(lbData.ListCount - 1, 1) = vItem(0) & "=" & vItem(j)
                Next j
            End If
        Next i
    End If
    
    
    lbData.AddItem "9  Ground"
    Select Case UCase(vAttList(8).TextString)
        Case "", "N"
            lbData.List(lbData.ListCount - 1, 1) = "NO GRD"
        Case "M"
            lbData.List(lbData.ListCount - 1, 1) = "MGNV"
        Case "T"
            lbData.List(lbData.ListCount - 1, 1) = "TGB"
        Case "B"
            lbData.List(lbData.ListCount - 1, 1) = "BROKEN GRD"
        Case Else
            lbData.List(lbData.ListCount - 1, 1) = vAttList(8).TextString
    End Select
    
    '<---------------------------------------------------------------- Add Attachments
    
    For n = 9 To 24
        If vAttList(n).TextString = "" Then GoTo Next_N
        
        
        Select Case n
            Case Is = 9
                vLine = Split(vAttList(n).TextString, " ")
                For k = 0 To UBound(vLine)
                    lbAttach.AddItem "NEUTRAL"
                    
                    If InStr(vLine(k), ")") > 0 Then
                        vTemp = Split(vLine(k), ")")
                        vTemp(0) = Replace(vTemp(0), "(", "")
                        
                        lbAttach.List(lbAttach.ListCount - 1, 1) = vTemp(0)
                        lbAttach.List(lbAttach.ListCount - 1, 2) = vTemp(1)
                        lbAttach.List(lbAttach.ListCount - 1, 3) = GetMR(CStr(vTemp(0)), CStr(vTemp(1)))
                    Else
                        lbAttach.List(lbAttach.ListCount - 1, 1) = vLine(k)
                        lbAttach.List(lbAttach.ListCount - 1, 2) = ""
                        lbAttach.List(lbAttach.ListCount - 1, 3) = ""
                    End If
                Next k
            Case Is = 10
                vLine = Split(vAttList(n).TextString, " ")
                For k = 0 To UBound(vLine)
                    lbAttach.AddItem "TRANSFORMER"
                    
                    If InStr(vLine(k), ")") > 0 Then
                        vTemp = Split(vLine(k), ")")
                        vTemp(0) = Replace(vTemp(0), "(", "")
                        
                        lbAttach.List(lbAttach.ListCount - 1, 1) = vTemp(0)
                        lbAttach.List(lbAttach.ListCount - 1, 2) = vTemp(1)
                        lbAttach.List(lbAttach.ListCount - 1, 3) = GetMR(CStr(vTemp(0)), CStr(vTemp(1)))
                    Else
                        lbAttach.List(lbAttach.ListCount - 1, 1) = vLine(k)
                        lbAttach.List(lbAttach.ListCount - 1, 2) = ""
                        lbAttach.List(lbAttach.ListCount - 1, 3) = ""
                    End If
                Next k
            Case Is = 11, Is = 12, Is = 13
                vLine = Split(vAttList(n).TextString, " ")
                For k = 0 To UBound(vLine)
                    
                    Select Case n
                        Case Is = 11
                            lbAttach.AddItem "LOW POWER"
                        Case Is = 12
                            lbAttach.AddItem "ANTENNA"
                        Case Is = 13
                            lbAttach.AddItem "ST LT CIR"
                    End Select
                    
                    If InStr(vLine(k), ")") > 0 Then
                        vTemp = Split(vLine(k), ")")
                        vTemp(0) = Replace(vTemp(0), "(", "")
                        
                        lbAttach.List(lbAttach.ListCount - 1, 1) = vTemp(0)
                        lbAttach.List(lbAttach.ListCount - 1, 2) = vTemp(1)
                        lbAttach.List(lbAttach.ListCount - 1, 3) = GetMR(CStr(vTemp(0)), CStr(vTemp(1)))
                    Else
                        lbAttach.List(lbAttach.ListCount - 1, 1) = vLine(k)
                        lbAttach.List(lbAttach.ListCount - 1, 2) = ""
                        lbAttach.List(lbAttach.ListCount - 1, 3) = ""
                    End If
                Next k
            Case Is = 14
                vLine = Split(vAttList(n).TextString, " ")
                For k = 0 To UBound(vLine)
                    lbAttach.AddItem "ST LT"
                    
                    If InStr(vLine(k), ")") > 0 Then
                        vTemp = Split(vLine(k), ")")
                        vTemp(0) = Replace(vTemp(0), "(", "")
                        
                        lbAttach.List(lbAttach.ListCount - 1, 1) = vTemp(0)
                        lbAttach.List(lbAttach.ListCount - 1, 2) = vTemp(1)
                        lbAttach.List(lbAttach.ListCount - 1, 3) = GetMR(CStr(vTemp(0)), CStr(vTemp(1)))
                    Else
                        lbAttach.List(lbAttach.ListCount - 1, 1) = vLine(k)
                        lbAttach.List(lbAttach.ListCount - 1, 2) = ""
                        lbAttach.List(lbAttach.ListCount - 1, 3) = ""
                    End If
                Next k
            Case Is = 15
                vLine = Split(vAttList(n).TextString, " ")
                For k = 0 To UBound(vLine)
                    lbAttach.AddItem "NEW 6M"
                    
                    lbAttach.List(lbAttach.ListCount - 1, 1) = ""
                    lbAttach.List(lbAttach.ListCount - 1, 2) = vLine(k)
                    lbAttach.List(lbAttach.ListCount - 1, 3) = "NEW"
                Next k
            Case Is > 15
                vLine = Split(UCase(vAttList(n).TextString), "=")
                vItem = Split(vLine(1), " ")
                For k = 0 To UBound(vItem)
                    If InStr(vItem(k), "C") > 0 Then
                        vLine(0) = vLine(0) & " C-WIRE"
                        vItem(k) = Replace(vItem(k), "C", "")
                    End If
                    
                    If InStr(vItem(k), "D") > 0 Then
                        vLine(0) = vLine(0) & " DROP"
                        vItem(k) = Replace(vItem(k), "D", "")
                    End If
                    
                    If InStr(vItem(k), "O") > 0 Then
                        vLine(0) = vLine(0) & " OHG"
                        vItem(k) = Replace(vItem(k), "O", "")
                    End If
                    
                    lbAttach.AddItem vLine(0)
                    
                    If InStr(vItem(k), "X") > 0 Then
                        lbAttach.List(lbAttach.ListCount - 1, 3) = "ATTACH"
                        vItem(k) = Replace(vItem(k), "X", "")
                    Else
                        lbAttach.List(lbAttach.ListCount - 1, 3) = ""
                    End If
                    
                    If InStr(vItem(k), ")") > 0 Then
                        vTemp = Split(vItem(k), ")")
                        vTemp(0) = Replace(vTemp(0), "(", "")
                        
                        lbAttach.List(lbAttach.ListCount - 1, 1) = vTemp(0)
                        lbAttach.List(lbAttach.ListCount - 1, 2) = vTemp(1)
                        lbAttach.List(lbAttach.ListCount - 1, 3) = GetMR(CStr(vTemp(0)), CStr(vTemp(1)))
                    Else
                        lbAttach.List(lbAttach.ListCount - 1, 1) = vItem(k)
                        lbAttach.List(lbAttach.ListCount - 1, 2) = ""
                    End If
                Next k
        End Select
Next_N:
    Next n
    
    'att 25
    If Not vAttList(25).TextString = "" Then
        vAttList(25).TextString = Replace(vAttList(25).TextString, vbLf, "")
        vLine = Split(vAttList(25).TextString, vbCr)
        For i = 0 To UBound(vLine)
            vItem = Split(vLine(i), " / ")
            lbCables.AddItem vItem(0)
            lbCables.List(lbCables.ListCount - 1, 1) = vItem(1)
        Next i
    End If
    
    'att 26
    If Not vAttList(26).TextString = "" Then
        vAttList(26).TextString = Replace(vAttList(26).TextString, vbLf, "")
        'If InStr(vAttList(26).TextString, " + ") > 0 Then vAttList(26).TextString = Replace(vAttList(26).TextString, " + ", vbCr)
        
        vLine = Split(vAttList(26).TextString, vbCr)
        For i = 0 To UBound(vLine)
            lbSplices.AddItem vLine(i)
        Next i
    End If
    
    'att 27
    If Not vAttList(27).TextString = "" Then
        vAttList(27).TextString = Replace(vAttList(27).TextString, vbLf, "")
        vLine = Split(vAttList(27).TextString, ";;")
        For i = 0 To UBound(vLine)
            vItem = Split(vLine(i), "=")
            lbUnits.AddItem vItem(0)
            If InStr(vItem(1), "  ") > 0 Then
                vTemp = Split(vItem(1), "  ")
                lbUnits.List(lbUnits.ListCount - 1, 1) = vTemp(0)
                lbUnits.List(lbUnits.ListCount - 1, 2) = vTemp(1)
            Else
                lbUnits.List(lbUnits.ListCount - 1, 1) = vItem(1)
                lbUnits.List(lbUnits.ListCount - 1, 2) = ""
            End If
        Next i
    End If
    
    Call SortAttachments
    
    Me.show
End Sub

Private Sub cbGetUnits_Click()
    Dim objSS As AcadSelectionSet
    Dim objEntity As AcadEntity
    Dim objBlock As AcadBlockReference
    Dim vAttList, vLine, vItem As Variant
    Dim strTemp, strLine As String
    Dim iFeet, iInch, iTotal, iRL As Integer
    
    Me.Hide
    
  On Error Resume Next
    
    Set objSS = ThisDrawing.SelectionSets.Add("objSS")
    If Not Err = 0 Then Set objSS = ThisDrawing.SelectionSets.Item("objSS")
        
    objSS.SelectOnScreen
    For Each objEntity In objSS
        If Not TypeOf objEntity Is AcadBlockReference Then GoTo Next_objEntity
        
        Set objBlock = objEntity
        If objBlock.Name = "pole_unit" Then
            vAttList = objBlock.GetAttributes
            
            vLine = Split(vAttList(3).TextString, "=")
            lbUnits.AddItem vLine(0), 0
            
            vLine(1) = Replace(vLine(1), "  ", " ")
            vItem = Split(vLine(1), " ")
            lbUnits.List(0, 1) = vItem(0)
            If UBound(vItem) < 1 Then
                lbUnits.List(0, 2) = ""
            Else
                lbUnits.List(0, 2) = vItem(1)
            End If
        End If
Next_objEntity:
    Next objEntity
    
    objSS.Clear
    objSS.Delete
    
    Me.show
End Sub

Private Sub cbPlace_Click()
    If lbCables.ListIndex < 0 Then Exit Sub
    
    Dim objCallout As AcadBlockReference
    'Dim strBlock As String
    
    'strBlock = "Callout"
    
    Dim returnPnt As Variant
    Dim vBlockCoords(0 To 2) As Double
    Dim lwpCoords(0 To 3) As Double
    Dim dPrevious(0 To 2) As Double
    Dim dOrigin(0 To 2) As Double
    Dim dScale As Double
    Dim lineObj As AcadLWPolyline
    Dim objCircle As AcadCircle
    Dim objCircle2 As AcadCircle
    Dim objText As AcadText
    Dim objText2 As AcadText
    Dim str1, str2, str3, strLetter As String
    Dim lowNum, highNum, strArray() As String
    Dim mainStatus, tempStatus As String
    Dim vLine, vCounts As Variant
    Dim iIndex As Integer
    
    Dim strAtt0, strAtt1, strAtt2 As String
    Dim strLayer As String
    
    iIndex = lbCables.ListIndex
    
    vLine = Split(lbCables.List(iIndex, 0), ": ")
    strAtt0 = tbPoleNumber.Value & ": " & vLine(0)
    strAtt1 = vLine(1)
    strAtt2 = Replace(lbCables.List(iIndex, 1), " + ", "\P")
    
    If Left(vLine(1), 2) = "CO" Then
        strLayer = "Integrity Proposed-Aerial"
    Else
        strLayer = "Integrity Proposed-Buried"
    End If
    
  'On Error Resume Next
    dOrigin(0) = 0
    dOrigin(1) = 0
    dOrigin(2) = 0
    
    'If cbSuffix.Value = "" And cbCblType.Value = "CO" Then
        'str1 = "Do you need a cable suffix?"
        'result = MsgBox(str1, vbYesNo)
        'If result = 6 Then Exit Sub
    'End If
    
    Me.Hide
    
    returnPnt = ThisDrawing.Utility.GetPoint(, "Select Point: ")
    lwpCoords(0) = returnPnt(0)
    lwpCoords(1) = returnPnt(1)
    dPrevious(0) = returnPnt(0)
    dPrevious(1) = returnPnt(1)
    dPrevious(2) = 0#
    
    returnPnt = ThisDrawing.Utility.GetPoint(dPrevious, "Select Point: ")
    vBlockCoords(0) = returnPnt(0)
    vBlockCoords(1) = returnPnt(1)
    vBlockCoords(2) = returnPnt(2)
    lwpCoords(2) = vBlockCoords(0)
    lwpCoords(3) = vBlockCoords(1)
    
    If cbPlacement.Value = "Leader" Then
        Set lineObj = ThisDrawing.ModelSpace.AddLightWeightPolyline(lwpCoords)
        lineObj.Layer = strLayer
        lineObj.Update
    Else
        Set objCircle = ThisDrawing.ModelSpace.AddCircle(dPrevious, 8)
        objCircle.Layer = strLayer
        objCircle.Update
        Set objCircle2 = ThisDrawing.ModelSpace.AddCircle(returnPnt, 8)
        objCircle2.Layer = strLayer
        objCircle2.Update
        
        strLetter = UCase(ThisDrawing.Utility.GetString(0, "Enter Callout Letter:"))
        Set objText = ThisDrawing.ModelSpace.AddText(strLetter, dOrigin, 8)
        Set objText2 = ThisDrawing.ModelSpace.AddText(strLetter, dOrigin, 8)
        objText.Layer = strLayer
        objText.Alignment = acAlignmentMiddle
        objText.TextAlignmentPoint = dPrevious
        objText2.Layer = strLayer
        objText2.Alignment = acAlignmentMiddle
        objText2.TextAlignmentPoint = vBlockCoords
        objText.Update
        objText2.Update
        
        vBlockCoords(0) = vBlockCoords(0) + 8
        lwpCoords(0) = 0
    End If
    
    
    'dScale = CDbl(cbScale.Value) / 100
    If dScale = 0 Then dScale = 0.75
        
    Set objCallout = ThisDrawing.ModelSpace.InsertBlock(vBlockCoords, "Callout", dScale, dScale, dScale, 0)
    attItem = objCallout.GetAttributes
    
    attItem(0).TextString = strAtt0
    attItem(1).TextString = strAtt1
    attItem(2).TextString = strAtt2
    
    objCallout.Layer = strLayer
    
    If lwpCoords(2) < lwpCoords(0) Then
        vBlockCoords(0) = vBlockCoords(0) - (75 * dScale)
        objCallout.InsertionPoint = vBlockCoords
    End If
    objCallout.Update
    
    Me.show
End Sub

Private Sub cbQuit_Click()
    Me.Hide
End Sub

Private Sub cbSort_Click()
    Call SortAttachments
End Sub

Private Sub cbUpdatePole_Click()
    Dim strLine As String
    Dim vAttList, vLine As Variant
    
    strLine = ""
    lbTemp.Clear
    
    vAttList = objPole.GetAttributes
    
    '<------------------------------------------------------------------- Data
    
    vAttList(0).TextString = tbPoleNumber.Value
    vAttList(2).TextString = tbOwner.Value
    
    If lbData.ListCount > 0 Then
        For i = 0 To lbData.ListCount - 1
            Select Case Left(lbData.List(i, 0), 1)
                Case "1"
                    vAttList(5).TextString = Replace(lbData.List(i, 1), " - ", "-")
                Case "2"
                    vAttList(3).TextString = lbData.List(i, 1)
                Case "3"
                    If strLine = "" Then
                        If InStr(lbData.List(i, 1), "  ") > 0 Then
                            strLine = tbOwner.Value & "*" & lbData.List(i, 1)
                        Else
                            strLine = lbData.List(i, 1)
                        End If
                    Else
                        If InStr(lbData.List(i, 1), "  ") > 0 Then
                            strLine = strLine & " " & tbOwner.Value & "*" & lbData.List(i, 1)
                        Else
                            strLine = strLine & " " & lbData.List(i, 1)
                        End If
                    End If
                Case "9"
                    vAttList(8).TextString = lbData.List(i, 1)
            End Select
        Next i
        
        vAttList(4).TextString = strLine
    End If
    
    '<------------------------------------------------------------------- Attachments
    
    If lbAttach.ListCount > 0 Then
        Dim strN, strT, strLP, strA, strSLC, strSL As String
        Dim strNew, strOHG As String
    
        For i = 0 To lbAttach.ListCount - 1
            strLine = ""
            
            If lbAttach.List(i, 1) = "" Then
                strLine = lbAttach.List(i, 2)
            Else
                If lbAttach.List(i, 2) = "" Then
                    strLine = lbAttach.List(i, 1)
                Else
                    strLine = "(" & lbAttach.List(i, 1) & ")" & lbAttach.List(i, 2)
                End If
            End If
            
            Select Case lbAttach.List(i, 0)
                Case "NEUTRAL"
                    If strN = "" Then
                        strN = strLine
                    Else
                        strN = strN & " " & strLine
                    End If
                Case "TRANSFORMER"
                    If strT = "" Then
                        strT = strLine
                    Else
                        strT = strT & " " & strLine
                    End If
                Case "LOW POWER"
                    If strLP = "" Then
                        strLP = strLine
                    Else
                        strLP = strLP & " " & strLine
                    End If
                Case "ANTENNA"
                    If strA = "" Then
                        strA = strLine
                    Else
                        strA = strA & " " & strLine
                    End If
                Case "ST LT CIR"
                    If strSLC = "" Then
                        strSLC = strLine
                    Else
                        strSLC = strSLC & " " & strLine
                    End If
                Case "ST LT"
                    If strSL = "" Then
                        strSL = strLine
                    Else
                        strSL = strSL & " " & strLine
                    End If
                Case Else
                    If InStr(lbAttach.List(i, 3), "NEW") > 0 Then
                        If strNew = "" Then
                            strNew = strLine
                        Else
                            strNew = strNew & " " & strLine
                        End If
                    Else
                        If lbTemp.ListCount = 0 Then
                            lbTemp.AddItem lbAttach.List(i, 0)
                            lbTemp.List(0, 1) = strLine
                        Else
                            For k = 0 To lbTemp.ListCount - 1
                                If lbTemp.List(k, 0) = lbAttach.List(i, 0) Then
                                    lbTemp.List(k, 1) = lbTemp.List(k, 1) & " " & strLine
                                    GoTo Found_Match
                                End If
                            Next k
                            
                            lbTemp.AddItem lbAttach.List(i, 0)
                            lbTemp.List(lbTemp.ListCount - 1, 1) = strLine
                            
Found_Match:
                        End If
                    End If
            End Select
            
        Next i
        
        If Not strN = "" Then vAttList(9).TextString = strN
        If Not strT = "" Then vAttList(10).TextString = strT
        If Not strLP = "" Then vAttList(11).TextString = strLP
        If Not strA = "" Then vAttList(12).TextString = strA
        If Not strSLC = "" Then vAttList(13).TextString = strSLC
        If Not strSL = "" Then vAttList(14).TextString = strSL
        If Not strNew = "" Then vAttList(15).TextString = strNew
        
        If lbTemp.ListCount > 0 Then
            For k = 0 To lbTemp.ListCount - 1
                Select Case k
                    Case Is = 0
                        vAttList(16).TextString = lbTemp.List(0, 0) & "=" & lbTemp.List(0, 1)
                    Case Is = 1
                        vAttList(17).TextString = lbTemp.List(1, 0) & "=" & lbTemp.List(1, 1)
                    Case Is = 2
                        vAttList(18).TextString = lbTemp.List(2, 0) & "=" & lbTemp.List(2, 1)
                    Case Is = 3
                        vAttList(19).TextString = lbTemp.List(3, 0) & "=" & lbTemp.List(3, 1)
                    Case Is = 4
                        vAttList(20).TextString = lbTemp.List(4, 0) & "=" & lbTemp.List(4, 1)
                    Case Is = 5
                        vAttList(21).TextString = lbTemp.List(5, 0) & "=" & lbTemp.List(5, 1)
                    Case Is = 6
                        vAttList(22).TextString = lbTemp.List(6, 0) & "=" & lbTemp.List(6, 1)
                    Case Is = 7
                        vAttList(23).TextString = lbTemp.List(7, 0) & "=" & lbTemp.List(7, 1)
                    Case Else
                        MsgBox "Maximum Comms Reached"
                End Select
            Next k
        End If
    End If
    
    '<------------------------------------------------------------------- Cables
    strLine = ""
    
    If lbCables.ListCount > 0 Then
        For i = 0 To lbCables.ListCount - 1
            If strLine = "" Then
                strLine = lbCables.List(i, 0) & " / " & lbCables.List(i, 1)
            Else
                strLine = strLine & vbCr & lbCables.List(i, 0) & " / " & lbCables.List(i, 1)
            End If
        Next i
        
        vAttList(25).TextString = strLine
    End If
    
    '<------------------------------------------------------------------- Splices
    strLine = ""
    
    If lbSplices.ListCount > 0 Then
        For i = 0 To lbSplices.ListCount - 1
            If strLine = "" Then
                strLine = lbSplices.List(i, 0)
            Else
                strLine = strLine & " + " & lbSplices.List(i, 0)
            End If
        Next i
        
        vAttList(26).TextString = strLine
    End If
    
    '<------------------------------------------------------------------- Units
    strLine = ""
    
    If lbUnits.ListCount > 0 Then
        For i = 0 To lbUnits.ListCount - 1
            If strLine = "" Then
                strLine = lbUnits.List(i, 0) & "=" & lbUnits.List(i, 1)
                If Not lbUnits.List(i, 2) = "" Then strLine = strLine & "  " & lbUnits.List(i, 2)
            Else
                strLine = strLine & ";;" & lbUnits.List(i, 0) & "=" & lbUnits.List(i, 1)
                If Not lbUnits.List(i, 2) = "" Then strLine = strLine & "  " & lbUnits.List(i, 2)
            End If
        Next i
        
        vAttList(27).TextString = strLine
    End If
    
    cbUpdatePole.Enabled = False
End Sub

Private Sub Label6_Click()
    Dim entPole As AcadObject
    Dim basePnt As Variant
    
    Me.Hide
  On Error Resume Next
    
    ThisDrawing.Utility.GetEntity entPole, basePnt, "Left Click to Exit: "
    
    Me.show
End Sub

Private Sub lbAttach_DblClick(ByVal Cancel As MSForms.ReturnBoolean)
    cbAddAttach.Caption = "Update"
    
    cbAttachment.Value = lbAttach.List(lbAttach.ListIndex, 0)
    tbEAttach.Value = lbAttach.List(lbAttach.ListIndex, 1)
    tbPAttach.Value = lbAttach.List(lbAttach.ListIndex, 2)
End Sub

Private Sub lbAttach_KeyDown(ByVal KeyCode As MSForms.ReturnInteger, ByVal Shift As Integer)
    Dim str0, str1, str2, str3 As String
    
    Select Case KeyCode
        Case vbKeyDelete
            If lbAttach.ListIndex < 0 Then Exit Sub
            lbAttach.RemoveItem lbAttach.ListIndex
        Case vbKeyUp
            If lbAttach.ListIndex = 0 Then Exit Sub
            
            str0 = lbAttach.List(lbAttach.ListIndex, 0)
            str1 = lbAttach.List(lbAttach.ListIndex, 1)
            str2 = lbAttach.List(lbAttach.ListIndex, 2)
            str3 = lbAttach.List(lbAttach.ListIndex, 3)
            
            lbAttach.List(lbAttach.ListIndex, 0) = lbAttach.List(lbAttach.ListIndex - 1, 0)
            lbAttach.List(lbAttach.ListIndex, 1) = lbAttach.List(lbAttach.ListIndex - 1, 1)
            lbAttach.List(lbAttach.ListIndex, 2) = lbAttach.List(lbAttach.ListIndex - 1, 2)
            lbAttach.List(lbAttach.ListIndex, 3) = lbAttach.List(lbAttach.ListIndex - 1, 3)
            
            lbAttach.List(lbAttach.ListIndex - 1, 0) = str0
            lbAttach.List(lbAttach.ListIndex - 1, 1) = str1
            lbAttach.List(lbAttach.ListIndex - 1, 2) = str2
            lbAttach.List(lbAttach.ListIndex - 1, 3) = str3
            
            'lbAttach.ListIndex = lbAttach.ListIndex - 1
        Case vbKeyDown
            If lbAttach.ListIndex = lbAttach.ListCount - 1 Then Exit Sub
            
            str0 = lbAttach.List(lbAttach.ListIndex, 0)
            str1 = lbAttach.List(lbAttach.ListIndex, 1)
            str2 = lbAttach.List(lbAttach.ListIndex, 2)
            str3 = lbAttach.List(lbAttach.ListIndex, 3)
            
            lbAttach.List(lbAttach.ListIndex, 0) = lbAttach.List(lbAttach.ListIndex + 1, 0)
            lbAttach.List(lbAttach.ListIndex, 1) = lbAttach.List(lbAttach.ListIndex + 1, 1)
            lbAttach.List(lbAttach.ListIndex, 2) = lbAttach.List(lbAttach.ListIndex + 1, 2)
            lbAttach.List(lbAttach.ListIndex, 3) = lbAttach.List(lbAttach.ListIndex + 1, 3)
            
            lbAttach.List(lbAttach.ListIndex + 1, 0) = str0
            lbAttach.List(lbAttach.ListIndex + 1, 1) = str1
            lbAttach.List(lbAttach.ListIndex + 1, 2) = str2
            lbAttach.List(lbAttach.ListIndex + 1, 3) = str3
            
            'lbAttach.ListIndex = lbAttach.ListIndex + 1
    End Select
End Sub

Private Sub lbCables_DblClick(ByVal Cancel As MSForms.ReturnBoolean)
    Me.Hide
    
    Load ArcViewPoleCable
    
        ArcViewPoleCable.tbCable.Value = lbCables.List(lbCables.ListIndex, 0)
        ArcViewPoleCable.tbCounts.Value = Replace(lbCables.List(lbCables.ListIndex, 1), " + ", vbCr)
    
        ArcViewPoleCable.show
        
        If Not ArcViewPoleCable.tbCounts.Value = "" Then
            lbCables.List(lbCables.ListIndex, 0) = ArcViewPoleCable.tbCable.Value
            lbCables.List(lbCables.ListIndex, 1) = Replace(ArcViewPoleCable.tbCounts.Value, vbCr, " + ")
            lbCables.List(lbCables.ListIndex, 1) = Replace(lbCables.List(lbCables.ListIndex, 1), vbLf, "")
        End If
        
    Unload ArcViewPoleCable
    
    Me.show
End Sub

Private Sub lbCables_KeyDown(ByVal KeyCode As MSForms.ReturnInteger, ByVal Shift As Integer)
    Dim str0, str1 As String
    
    Select Case KeyCode
        Case vbKeyDelete
            lbCounts.RemoveItem lbCounts.ListIndex
        Case vbKeyUp
            If lbCounts.ListIndex = 0 Then Exit Sub
            
            str0 = lbCounts.List(lbCounts.ListIndex, 0)
            str1 = lbCounts.List(lbCounts.ListIndex, 1)
            
            lbCounts.List(lbCounts.ListIndex, 0) = lbCounts.List(lbCounts.ListIndex - 1, 0)
            lbCounts.List(lbCounts.ListIndex, 1) = lbCounts.List(lbCounts.ListIndex - 1, 1)
            
            lbCounts.List(lbCounts.ListIndex - 1, 0) = str0
            lbCounts.List(lbCounts.ListIndex - 1, 1) = str1
            
            'lbCounts.ListIndex = lbCounts.ListIndex - 1
        Case vbKeyDown
            If lbCounts.ListIndex = lbCounts.ListCount - 1 Then Exit Sub
            
            str0 = lbCounts.List(lbCounts.ListIndex, 0)
            str1 = lbCounts.List(lbCounts.ListIndex, 1)
            
            lbCounts.List(lbCounts.ListIndex, 0) = lbCounts.List(lbCounts.ListIndex + 1, 0)
            lbCounts.List(lbCounts.ListIndex, 1) = lbCounts.List(lbCounts.ListIndex + 1, 1)
            
            lbCounts.List(lbCounts.ListIndex + 1, 0) = str0
            lbCounts.List(lbCounts.ListIndex + 1, 1) = str1
            
            'lbCounts.ListIndex = lbCounts.ListIndex + 1
    End Select
End Sub

Private Sub lbData_DblClick(ByVal Cancel As MSForms.ReturnBoolean)
    Select Case Left(lbData.List(lbData.ListIndex, 0), 1)
        Case "1"
            cbDType.Value = "H-C"
        Case "2"
            cbDType.Value = "Owner #"
        Case "3"
            cbDType.Value = "Other #"
        Case "9"
            cbDType.Value = "Ground"
    End Select
    cbDType.Enabled = False
    cbAddData.Caption = "Update"
    
    tbDValue.Value = lbData.List(lbData.ListIndex, 1)
End Sub

Private Sub lbData_KeyDown(ByVal KeyCode As MSForms.ReturnInteger, ByVal Shift As Integer)
    Dim str0, str1 As String
    
    Select Case KeyCode
        Case vbKeyDelete
            lbData.RemoveItem lbData.ListIndex
        Case vbKeyReturn
            Select Case Left(lbData.List(lbData.ListIndex, 0), 1)
                Case "1"
                    cbDType.Value = "H-C"
                Case "2"
                    cbDType.Value = "Owner #"
                Case "3"
                    cbDType.Value = "Other #"
                Case "9"
                    cbDType.Value = "Ground"
            End Select
            cbDType.Enabled = False
            cbAddData.Caption = "Update"
    
            tbDValue.Value = lbData.List(lbData.ListIndex, 1)
        Case vbKeyUp
            If lbData.ListIndex = 0 Then Exit Sub
            
            str0 = lbData.List(lbData.ListIndex, 0)
            str1 = lbData.List(lbData.ListIndex, 1)
            
            lbData.List(lbData.ListIndex, 0) = lbData.List(lbData.ListIndex - 1, 0)
            lbData.List(lbData.ListIndex, 1) = lbData.List(lbData.ListIndex - 1, 1)
            
            lbData.List(lbData.ListIndex - 1, 0) = str0
            lbData.List(lbData.ListIndex - 1, 1) = str1
            
            'lbData.ListIndex = lbData.ListIndex - 1
        Case vbKeyDown
            If lbData.ListIndex = lbData.ListCount - 1 Then Exit Sub
            
            str0 = lbData.List(lbData.ListIndex, 0)
            str1 = lbData.List(lbData.ListIndex, 1)
            
            lbData.List(lbData.ListIndex, 0) = lbData.List(lbData.ListIndex + 1, 0)
            lbData.List(lbData.ListIndex, 1) = lbData.List(lbData.ListIndex + 1, 1)
            
            lbData.List(lbData.ListIndex + 1, 0) = str0
            lbData.List(lbData.ListIndex + 1, 1) = str1
            
            'lbData.ListIndex = lbData.ListIndex + 1
    End Select
End Sub

Private Sub lbSplices_DblClick(ByVal Cancel As MSForms.ReturnBoolean)
    cbAddSplice.Caption = "Update"
    
    tbSValue.Value = lbSplices.List(lbSplices.ListIndex)
End Sub

Private Sub lbUnits_DblClick(ByVal Cancel As MSForms.ReturnBoolean)
    cbAddUnit.Caption = "Update"
    
    tbUnit.Value = lbUnits.List(lbUnits.ListIndex, 0)
    tbQuantity.Value = lbUnits.List(lbUnits.ListIndex, 1)
    tbUNote.Value = lbUnits.List(lbUnits.ListIndex, 2)
End Sub

Private Sub lbUnits_KeyDown(ByVal KeyCode As MSForms.ReturnInteger, ByVal Shift As Integer)
    Dim str0, str1, str2 As String
    
    Select Case KeyCode
        Case vbKeyDelete
            lbUnits.RemoveItem lbUnits.ListIndex
        Case vbKeyUp
            If lbUnits.ListIndex = 0 Then Exit Sub
            
            str0 = lbUnits.List(lbUnits.ListIndex, 0)
            str1 = lbUnits.List(lbUnits.ListIndex, 1)
            str2 = lbUnits.List(lbUnits.ListIndex, 2)
            
            lbUnits.List(lbUnits.ListIndex, 0) = lbUnits.List(lbUnits.ListIndex - 1, 0)
            lbUnits.List(lbUnits.ListIndex, 1) = lbUnits.List(lbUnits.ListIndex - 1, 1)
            lbUnits.List(lbUnits.ListIndex, 2) = lbUnits.List(lbUnits.ListIndex - 1, 2)
            
            lbUnits.List(lbUnits.ListIndex - 1, 0) = str0
            lbUnits.List(lbUnits.ListIndex - 1, 1) = str1
            lbUnits.List(lbUnits.ListIndex - 1, 2) = str2
            
            'lbUnits.ListIndex = lbUnits.ListIndex - 1
        Case vbKeyDown
            If lbUnits.ListIndex = lbUnits.ListCount - 1 Then Exit Sub
            
            str0 = lbUnits.List(lbUnits.ListIndex, 0)
            str1 = lbUnits.List(lbUnits.ListIndex, 1)
            str2 = lbUnits.List(lbUnits.ListIndex, 2)
            
            lbUnits.List(lbUnits.ListIndex, 0) = lbUnits.List(lbUnits.ListIndex + 1, 0)
            lbUnits.List(lbUnits.ListIndex, 1) = lbUnits.List(lbUnits.ListIndex + 1, 1)
            lbUnits.List(lbUnits.ListIndex, 2) = lbUnits.List(lbUnits.ListIndex + 1, 2)
            
            lbUnits.List(lbUnits.ListIndex + 1, 0) = str0
            lbUnits.List(lbUnits.ListIndex + 1, 1) = str1
            lbUnits.List(lbUnits.ListIndex + 1, 2) = str2
            
            'lbUnits.ListIndex = lbUnits.ListIndex + 1
    End Select
End Sub

Private Sub UserForm_Initialize()
    lbData.ColumnCount = 2
    lbData.ColumnWidths = "60;180"
    
    lbAttach.ColumnCount = 4
    lbAttach.ColumnWidths = "84;36;36;84"
    
    lbUnits.ColumnCount = 3
    lbUnits.ColumnWidths = "96;36;48"
    
    lbCables.ColumnCount = 2
    lbCables.ColumnWidths = "96;285"
    
    lbTemp.ColumnCount = 2
    lbTemp.ColumnWidths = "48;72"
    
    cbDType.AddItem "H-C"
    cbDType.AddItem "Owner #"
    cbDType.AddItem "Other #"
    cbDType.AddItem "Ground"
    
    cbAttachment.AddItem "NEUTRAL"
    cbAttachment.AddItem "TRANSFORMER"
    cbAttachment.AddItem "LOW POWER"
    cbAttachment.AddItem "ANTENNA"
    cbAttachment.AddItem "ST LT CIR"
    cbAttachment.AddItem "ST LT"
    cbAttachment.AddItem "NEW 6M"
    cbAttachment.AddItem "NEW 10M"
    cbAttachment.AddItem "CLEC"
    cbAttachment.AddItem "XO"
    cbAttachment.AddItem "ZAYO"
    cbAttachment.AddItem "LEVEL3"
    cbAttachment.AddItem "ATT"
    cbAttachment.AddItem "TDS"
    cbAttachment.AddItem "PWR OHG"
    cbAttachment.AddItem "NEW OHG"
    cbAttachment.AddItem "CLEC OHG"
    cbAttachment.AddItem "TELCO OHG"
    cbAttachment.AddItem "ATT OHG"
    cbAttachment.AddItem "TDS OHG"
    cbAttachment.AddItem "UTC OHG"
    cbAttachment.AddItem "OHG"
    
    cbPlacement.AddItem "Leader"
    cbPlacement.AddItem "Away"
    cbPlacement.Value = "Leader"
    
    cbScale.AddItem "50"
    cbScale.AddItem "75"
    cbScale.AddItem "100"
    cbScale.Value = "100"
End Sub

Private Function GetMR(strE As String, strP As String)
    Dim vLine, vItem As Variant
    Dim strMR As String
    Dim iEF, iEI, iPF, iPI, iMR As Integer
    
    Select Case strE
        Case ""
            strMR = "NEW"
        Case "X"
            strMR = "ATTACH"
        Case strP
            strMR = "TRANSFER"
        Case Else
            If strP = "" Then
                strMR = ""
            Else
                vLine = Split(strE, "-")
                iEF = CInt(vLine(0))
                iEI = CInt(vLine(1))
                iEI = iEF * 12 + iEI
            
                vLine = Split(strP, "-")
                iPF = CInt(vLine(0))
                iPI = CInt(vLine(1))
                iPI = iPF * 12 + iPI
            
                iMR = iPI - iEI
            
                If iMR > 0 Then
                    strMR = "RAISE " & iMR & """"
                Else
                    strMR = "LOWER " & Abs(iMR) & """"
                End If
            End If
    End Select
    
    GetMR = strMR
End Function

Private Sub SortAttachments()
    Dim strArrayList(), strArraySorted(), strData() As String
    Dim strListItem() As String     '<---------------------------------------------Sort
    'Dim attArray, attItem As Variant
    'Dim str1, str2 As String
    'Dim i, iDWGNum, test1, place1, temp1 As Integer
    Dim vLine As Variant
    Dim strTemp As String
    Dim iFeet, iInch As Integer
    'Dim tempFt, tempIn As Integer
    'Dim iNewFt, iNewIn As Integer
    Dim i As Integer
    
    'test1 = 0
    
    ReDim strData(0 To lbAttach.ListCount - 1)
    ReDim strListItem(0 To lbAttach.ListCount - 1)
    ReDim strArraySorted(0 To lbAttach.ListCount - 1)
    
    For i = 0 To UBound(strListItem)
        strListItem(i) = i
    Next i
    
    For i = 0 To UBound(strData)
        If lbAttach.List(i, 2) = "" Then
            vLine = Split(lbAttach.List(i, 1), "-")
        Else
            vLine = Split(lbAttach.List(i, 2), "-")
        End If
        
        iFeet = CInt(vLine(0))
        iInch = CInt(vLine(1)) + iFeet * 12
        
        strData(i) = iInch
    Next i
    
    'test1 = UBound(strData) - 1

    For i = UBound(strData) To (LBound(strData) + 1) Step -1
        For j = LBound(strData) To (i - 1)
            If CInt(strData(j)) < CInt(strData(j + 1)) Then
                strTemp = strData(j + 1)
                strData(j + 1) = strData(j)
                strData(j) = strTemp
                
                strTemp = strListItem(j + 1)
                strListItem(j + 1) = strListItem(j)
                strListItem(j) = strTemp
            End If
        Next j
    Next i
    
    For i = LBound(strListItem) To UBound(strListItem)
        strArraySorted(i) = lbAttach.List(strListItem(i), 0) & vbTab & lbAttach.List(strListItem(i), 1) & vbTab & lbAttach.List(strListItem(i), 2) & vbTab & lbAttach.List(strListItem(i), 3)
    Next i
        
    lbAttach.Clear
    For i = LBound(strListItem) To UBound(strListItem)
        vLine = Split(strArraySorted(i), vbTab)
        
        lbAttach.AddItem vLine(0)
        lbAttach.List(lbAttach.ListCount - 1, 1) = vLine(1)
        lbAttach.List(lbAttach.ListCount - 1, 2) = vLine(2)
        lbAttach.List(lbAttach.ListCount - 1, 3) = vLine(3)
    Next i
End Sub

Attribute VB_Name = "ArcViewPoleCable"
Attribute VB_Base = "0{FD07DC99-5AEF-4AA0-A5D8-CB85392DE16C}{651A07E1-8222-4457-8D71-F71E8474AFAF}"
Attribute VB_GlobalNameSpace = False
Attribute VB_Creatable = False
Attribute VB_PredeclaredId = True
Attribute VB_Exposed = False
Attribute VB_TemplateDerived = False
Attribute VB_Customizable = False


Private Sub cbAddData_Click()
    Dim amap As AcadMap
    Dim tbl As ODTable
    Dim tbls As ODTables
    Dim ODRcs As ODRecords
    Dim ODRc As ODRecord
    Dim boolVal As Boolean
    
    Dim objEntity As AcadEntity
    Dim vReturnPnt As Variant
    Dim objLine As AcadLine
    Dim objLWP As AcadLWPolyline
    Dim iLength As Integer
    
    Set amap = ThisDrawing.Application.GetInterfaceObject("AutoCADMap.Application")
    
    Set tbls = amap.Projects(ThisDrawing).ODTables
    If tbls.count > 0 Then
        For Each tbl In tbls
            If tbl.Name = "Cables" Then GoTo Exit_For
        Next
    End If
    
    MsgBox "Object Data Table not found."
    Exit Sub
    
Exit_For:
    Set ODRcs = tbl.GetODRecords
    
    Me.Hide
    
    ThisDrawing.Utility.GetEntity objEntity, vReturnPnt, "Select Cable: "
    
    If TypeOf objEntity Is AcadLine Then
        Set objLine = objEntity
        iLength = objLine.Length
    ElseIf TypeOf objEntity Is AcadLWPolyline Then
        Set objLWP = objEntity
        iLength = objLWP.Length
    Else
        MsgBox "Wrong type of Entity."
        Me.show
        Exit Sub
    End If
    
    Set ODRc = tbl.CreateRecord
    
    ODRc.Item(0).Value = tbCable.Value
    ODRc.Item(1).Value = iLength
    ODRc.Item(2).Value = tbCounts.Value
    
    MsgBox objEntity.ObjectID
    'ODRc.AttachTo objEntity.ObjectID
    If TypeOf objEntity Is AcadLine Then
        MsgBox "Line ID  " & objLine.ObjectID
        'ODRc.AttachTo (objLine.ObjectID)
    Else
        MsgBox "LWP ID  " & objLWP.ObjectID
        'ODRc.AttachTo (objLWP.ObjectID)
    End If
    
    Me.show
End Sub

Private Sub cbCancel_Click()
    tbCounts.Value = ""
    
    Me.Hide
End Sub

Private Sub cbUpdate_Click()
    Me.Hide
End Sub

Attribute VB_Name = "AttachmentAlias"
Attribute VB_Base = "0{FD78D32D-49A1-4A70-B269-737165ABD467}{870FBD49-D47D-40A8-B59A-8055CC3272F2}"
Attribute VB_GlobalNameSpace = False
Attribute VB_Creatable = False
Attribute VB_PredeclaredId = True
Attribute VB_Exposed = False
Attribute VB_TemplateDerived = False
Attribute VB_Customizable = False
Private Sub cbAdd_Click()
    If tbAlias.Value = "" Then Exit Sub
    If tbCompany.Value = "" Then Exit Sub
    
    If cbAdd.Caption = "Update" Then
        lbAlias.Enabled = True
        cbAdd.Caption = "Add Alias"
        
        lbAlias.List(lbAlias.ListIndex, 0) = UCase(tbAlias.Value)
        lbAlias.List(lbAlias.ListIndex, 1) = UCase(tbCompany.Value)
    Else
        lbAlias.AddItem UCase(tbAlias.Value)
        lbAlias.List(lbAlias.ListCount - 1, 1) = UCase(tbCompany.Value)
    End If
End Sub

Private Sub cbQuit_Click()
    Me.Hide
End Sub

Private Sub cbReplace_Click()
    If lbAlias.ListCount < 1 Then Exit Sub
    
    Dim filterType, filterValue As Variant
    Dim grpCode(0) As Integer
    Dim grpValue(0) As Variant
    Dim objSS As AcadSelectionSet
    Dim objBlock As AcadBlockReference
    Dim vAttList As Variant
    Dim vLine, vItem As Variant
    Dim strTemp As String
    
    On Error Resume Next
    
    grpCode(0) = 2
    grpValue(0) = "sPole"
    filterType = grpCode
    filterValue = grpValue
    
    Err = 0
    Set objSS = ThisDrawing.SelectionSets.Add("objSS")
    If Not Err = 0 Then
        Set objSS = ThisDrawing.SelectionSets.Item("objSS")
        objSS.Clear
    End If
    
    objSS.Select acSelectionSetAll, , , filterType, filterValue
    
    For i = 0 To objSS.count - 1
        Set objBlock = objSS.Item(i)
        vAttList = objBlock.GetAttributes
        
        If vAttList(0).TextString = "" Then GoTo Next_objBlock
        If vAttList(1).TextString = "INCOMPLETE" Then GoTo Next_objBlock
        
        If Not vAttList(4).TextString = "" Then
            If InStr(vAttList(4).TextString, "=") > 0 Then
                vLine = Split(UCase(vAttList(4).TextString), " ")
                
                For j = 0 To UBound(vLine)
                    vItem = Split(vLine(j), "=")
                    
                    If UBound(vItem) = 0 Then
                        vAttList(4).TextString = vAttList(2).TextString & "=" & vAttList(4).TextString
                        GoTo Next_Other
                    End If
            
                    For k = 0 To lbAlias.ListCount - 1
                        If vItem(0) = lbAlias.List(k, 0) Then
                            vLine(j) = lbAlias.List(k, 1) & "=" & vItem(1)
                            objBlock.Update
                    
                            GoTo Next_Other
                        End If
                    Next k
Next_Other:
                Next j
                
                strTemp = vLine(0)
                If UBound(vLine) > 0 Then
                    For j = 1 To UBound(vLine)
                        strTemp = strTemp & " " & vLine(j)
                    Next j
                End If
                
                vAttList(4).TextString = strTemp
            Else
                vAttList(4).TextString = vAttList(2).TextString & "=" & vAttList(4).TextString
            End If
        End If
        
        For j = 16 To 23
            If vAttList(j).TextString = "" Then GoTo Next_J
            If InStr(vAttList(j).TextString, "=") < 1 Then GoTo Next_J
            
            vLine = Split(UCase(vAttList(j).TextString), "=")
            If UBound(vLine) < 1 Then GoTo Next_J
            
            For k = 0 To lbAlias.ListCount - 1
                If vLine(0) = lbAlias.List(k, 0) Then
                    vAttList(j).TextString = lbAlias.List(k, 1) & "=" & vLine(1)
                    objBlock.Update
                    
                    GoTo Next_J
                End If
            Next k
            
Next_J:
        Next j
Next_objBlock:
    Next i
    
    grpValue(0) = "Existing_Guys"
    filterType = grpCode
    filterValue = grpValue
    
    objSS.Clear
    objSS.Select acSelectionSetAll, , , filterType, filterValue
    
    For i = 0 To objSS.count - 1
        Set objBlock = objSS.Item(i)
        vAttList = objBlock.GetAttributes
        
        For j = 0 To 7
            If vAttList(j).TextString = "" Then GoTo Next_Other2
            If InStr(vAttList(j).TextString, "=") > 0 Then
                vItem = Split(UCase(vAttList(j).TextString), "=")
                
                For k = 0 To lbAlias.ListCount - 1
                    If vItem(0) = lbAlias.List(k, 0) Then
                        vAttList(j).TextString = lbAlias.List(k, 1) & "=" & vItem(1)
                        objBlock.Update
                    
                        GoTo Next_Other2
                    End If
                Next k
            End If
Next_Other2:
        Next j
    Next i
    
    objSS.Clear
    objSS.Delete
End Sub

Private Sub lbAlias_DblClick(ByVal Cancel As MSForms.ReturnBoolean)
    tbAlias.Value = lbAlias.List(lbAlias.ListIndex, 0)
    tbCompany.Value = lbAlias.List(lbAlias.ListIndex, 1)
    
    cbAdd.Caption = "Update"
    lbAlias.Enabled = False
End Sub

Private Sub lbAlias_KeyDown(ByVal KeyCode As MSForms.ReturnInteger, ByVal Shift As Integer)
    If lbAlias.ListCount < 1 Then Exit Sub
    Select Case KeyCode
        Case vbKeyDelete
            lbAlias.RemoveItem lbAlias.ListIndex
    End Select
End Sub

Private Sub UserForm_Initialize()
    lbAlias.ColumnCount = 2
    lbAlias.ColumnWidths = "72;162"
    
    Call GetAliases
End Sub

Private Sub GetAliases()
    Dim filterType, filterValue As Variant
    Dim grpCode(0) As Integer
    Dim grpValue(0) As Variant
    Dim objSS As AcadSelectionSet
    Dim objBlock As AcadBlockReference
    Dim vAttList As Variant
    
    On Error Resume Next
    
    lbAlias.Clear
    
    grpCode(0) = 2
    grpValue(0) = "Alias"
    filterType = grpCode
    filterValue = grpValue
    
    Err = 0
    Set objSS = ThisDrawing.SelectionSets.Add("objSS")
    If Not Err = 0 Then
        Set objSS = ThisDrawing.SelectionSets.Item("objSS")
        objSS.Clear
    End If
    
    objSS.Select acSelectionSetAll, , , filterType, filterValue
    
    For i = 0 To objSS.count - 1
        Set objBlock = objSS.Item(i)
        vAttList = objBlock.GetAttributes
        
        If vAttList(0).TextString = "" Then GoTo Next_objBlock
        If vAttList(0).TextString = "alias" Then GoTo Next_objBlock
        
        lbAlias.AddItem UCase(vAttList(0).TextString), 0
        lbAlias.List(0, 1) = UCase(vAttList(1).TextString)
        
Next_objBlock:
    Next i
    
    objSS.Clear
    objSS.Delete
End Sub

Attribute VB_Name = "BuriedPlantForm"
Attribute VB_Base = "0{8F46651E-7FBA-4A9D-9995-76C6F7CBE103}{070FF48B-9EBF-4C4C-B3ED-9A2446921D23}"
Attribute VB_GlobalNameSpace = False
Attribute VB_Creatable = False
Attribute VB_PredeclaredId = True
Attribute VB_Exposed = False
Attribute VB_TemplateDerived = False
Attribute VB_Customizable = False

Dim Pi As Double

Private Sub cbPlaceBM61_Click()
    'Dim lineObj2 As AcadLWPolyline
    Dim objLWP As AcadLWPolyline
    Dim returnPnt1, returnPnt2 As Variant
    Dim lwpCoords(0 To 3) As Double
    Dim objOffset1, objOffset2 As Variant
    
  Me.Hide
    
    returnPnt1 = ThisDrawing.Utility.GetPoint(, "From point:")
    returnPnt2 = ThisDrawing.Utility.GetPoint(, "To point:")
    
    lwpCoords(0) = returnPnt1(0)
    lwpCoords(1) = returnPnt1(1)
    lwpCoords(2) = returnPnt2(0)
    lwpCoords(3) = returnPnt2(1)
    
    Set objLWP = ThisDrawing.ModelSpace.AddLightWeightPolyline(lwpCoords)
    objLWP.Update
    'Set lineObj2 = ThisDrawing.ModelSpace.AddLightWeightPolyline(lwpCoords)
    'lineObj2.Update
    
    'objOffset1 = lineObj2.Offset(1)
    'objOffset2 = lineObj2.Offset(-1)
  Me.show
End Sub

Private Sub cbPlaceUD_Click()
    Dim insertPnt(0 To 2), leaderPnt(0 To 3) As Double
    Dim newVertex(0 To 1) As Double
    Dim objBlock As AcadBlockReference
    Dim lineObj As AcadLWPolyline
    Dim returnPnt, attList As Variant
    Dim attItem, basePnt As Variant
    Dim str, str1 As String
    Dim strDistance As String
    'Dim strArray() As String
    Dim dScale, dDistance, dRotate As Double
    Dim dOffset As Double
    Dim xDiff, yDiff, zDiff, dDist As Double
    Dim vEOBL, vEOBR As Variant
    Dim vReturnPnt, vEndPnt As Variant
    Dim iCounter As Integer
    
    Me.Hide
  On Error Resume Next
    
    vReturnPnt = ThisDrawing.Utility.GetPoint(, "Start Point: ")
    
    dScale = cbScale.Value / 100
    leaderPnt(0) = vReturnPnt(0)
    leaderPnt(1) = vReturnPnt(1)
    
    Err = 0
    vEndPnt = ThisDrawing.Utility.GetPoint(vReturnPnt, "Next Point: ")
    If Not Err = 0 Then GoTo Exit_Sub
    vReturnPnt = vEndPnt
    
    leaderPnt(2) = vEndPnt(0)
    leaderPnt(3) = vEndPnt(1)
    
    Set lineObj = ThisDrawing.ModelSpace.AddLightWeightPolyline(leaderPnt)
    Select Case cbUDStatus.Value
        Case "New"
            lineObj.Layer = "Integrity Proposed"
        Case "Existing"
            lineObj.Layer = "Integrity Existing-Buried"
        Case "Future"
            lineObj.Layer = "Integrity Future"
    End Select
    
    lineObj.Linetype = "DASHED"
    lineObj.Update
    
    iCounter = 2
    Err = 0
    
    While Err = 0
        vEndPnt = ThisDrawing.Utility.GetPoint(vReturnPnt, "Next Point: ")
        If Not Err = 0 Then GoTo Exit_While
        vReturnPnt = vEndPnt
        
        newVertex(0) = vEndPnt(0)
        newVertex(1) = vEndPnt(1)
        
        lineObj.AddVertex iCounter, newVertex
        lineObj.Update
        iCounter = iCounter + 1
    Wend
Exit_While:

    Err = 0
    
    dOffset = 2 * dScale
    vEOBL = lineObj.Offset(dOffset)
    vEOBR = lineObj.Offset(-dOffset)
    
    lineObj.Linetype = "HIDDEN"
    'lineObj.Layer = objBlock.Layer
    lineObj.Update
    dDistance = CInt(lineObj.Length)
    
    vReturnPnt = ThisDrawing.Utility.GetPoint(, "Callout Point: ")
    vEndPnt = ThisDrawing.Utility.GetPoint(vReturnPnt, "Direction of Rotation: ")
    If Not Err = 0 Then GoTo Exit_Sub
    
    insertPnt(0) = vReturnPnt(0)
    insertPnt(1) = vReturnPnt(1)
    insertPnt(2) = 0#
    
    xDiff = vEndPnt(0) - vReturnPnt(0)
    yDiff = vEndPnt(1) - vReturnPnt(1)
    
    dRotate = Atn(yDiff / xDiff)
    
    Err = 0
    Set objBlock = ThisDrawing.ModelSpace.InsertBlock(vReturnPnt, "cable_span", dScale, dScale, dScale, dRotate)
    If Not Err = 0 Then MsgBox "Error: Placing Block"
    attList = objBlock.GetAttributes
    
    strDistance = ThisDrawing.Utility.GetString(0, "Enter Distance(" & dDistance & "'): ")
    
    If strDistance = "" Then
        str1 = cbUDType.Value & "=" & dDistance & "'"
    Else
        str1 = cbUDType.Value & "=" & strDistance
        If Not Right(str1, 1) = "'" Then str1 = str1 & "'"
    End If
    
    attList(2).TextString = str1
    
    objBlock.Layer = lineObj.Layer
    objBlock.Update
    
    If Not cbPlaceCbl Then lineObj.Delete
    lineObj.Update
    
Exit_Sub:
    Me.show
End Sub

Private Sub cbQuit_Click()
    Me.Hide
End Sub

Private Sub cbType_Change()
    If cbType.Value = "FP" Then
        tbLetter.Enabled = True
    Else
        tbLetter.Value = ""
        tbLetter.Enabled = False
    End If
End Sub

Private Sub cpPlaceFP_Click()
    Dim objBlock As AcadBlockReference
    Dim returnPnt, attList As Variant
    Dim vLevel1, vLevel2, vLevel3 As Variant
    Dim strBlock, strNumber, strRoute As String
    Dim dScale As Double
    Dim iNumber As Integer
    'Dim objInfo As AcadBlockReference
    'Dim str As String
    'Dim insertPnt(0 To 2), leaderPnt(0 To 3) As Double
    'Dim item, item2 As Variant
    'Dim layerObj As AcadLayer
    'Dim lwpPnt(0 To 3) As Double
    'Dim lineObj As AcadLWPolyline
    
  On Error Resume Next
  
    If cbType.Value = "" Then GoTo Exit_Sub
    If tbPoleNum.Value = "" Then GoTo Exit_Sub
    
    Select Case Left(cbType.Value, 2)
        Case "FP"
            strBlock = "dFP"
        Case "BD"
            strBlock = "PED"
        Case "BU"
            strBlock = "Map splice"
        Case Else
            strBlock = "dHH"
    End Select
    
    Me.Hide
   
    dScale = CDbl(cbScale.Value) / 100
    If Err <> 0 Then dScale = 0.75
    Err = 0
    
    returnPnt = ThisDrawing.Utility.GetPoint(, "Place " & cbType.Value & ": ")
    
    Set objBlock = ThisDrawing.ModelSpace.InsertBlock(returnPnt, strBlock, dScale, dScale, dScale, 0#)
    attList = objBlock.GetAttributes
    
    vLevel1 = Split(tbPoleNum.Value, "/")
    vLevel2 = Split(vLevel1(UBound(vLevel1)), "L")
    vLevel3 = Split(vLevel2(UBound(vLevel2)), "R")
    iNumber = CInt(vLevel3(UBound(vLevel3)))
    
    Select Case iNumber
        Case Is < 10
            strRoute = Left(tbPoleNum.Value, Len(tbPoleNum.Value) - 1)
        Case Is < 100
            strRoute = Left(tbPoleNum.Value, Len(tbPoleNum.Value) - 2)
        Case Else
            strRoute = Left(tbPoleNum.Value, Len(tbPoleNum.Value) - 3)
    End Select
    
    If cbType.Value = "FP" Then
        strNumber = iNumber & tbLetter.Value
        tbLetter.Value = Chr(Asc(tbLetter.Value) + 1)
    Else
        strNumber = tbPoleNum.Value
        tbPoleNum.Value = strRoute & (iNumber + 1)
    End If
    
    attList(0).TextString = strNumber
    attList(1).TextString = cbType.Value
    If cbHousingStatus.Value = "Future" Then attList(1).TextString = attList(1).TextString & " (FUTURE)"
    objBlock.Update
    
    Select Case cbHousingStatus.Value
        Case "New"
            objBlock.Layer = "Integrity Proposed"
        Case "Existing"
            objBlock.Layer = "Integrity Existing-Buried"
        Case "Future"
            objBlock.Layer = "Integrity Future"
    End Select
    
    objBlock.Update

Exit_Sub:
    Me.show
End Sub

Private Sub Label1_Click()
    Me.Hide
    Call Get_Pole
    
    If cbType.Value = "FP" Then tbLetter.Value = "A"
    
    Me.show
End Sub

Private Sub UserForm_Initialize()
    cbType.AddItem "BHF(30X48X36)T"
    cbType.AddItem "UHF(24X36X24)"
    cbType.AddItem "UHF(30X48X36)"
    cbType.AddItem "UHF(17X30X18)"
    cbType.AddItem "FP"
    cbType.AddItem "BDO3"
    cbType.AddItem "BDO5"
    cbType.AddItem "BDO7"
    cbType.AddItem "BUDI"
    cbType.AddItem "FDH"

    cbUDType.AddItem "BM60(1.5)D"
    cbUDType.AddItem "BM60(1.25)D"
    cbUDType.AddItem "UD(1X1-2)"
    cbUDType.AddItem "UD(1X1-4)"
    cbUDType.AddItem "UD(1X1-1.25)"
    cbUDType.AddItem "UD(1X2-2)"
    cbUDType.AddItem "UD(1X2-4)"
    'Call Get_Pole
    
    cbScale.AddItem "50"
    cbScale.AddItem "75"
    cbScale.AddItem "100"
    cbScale.Value = "100"
    
    cbHousingStatus.AddItem "Existing"
    cbHousingStatus.AddItem "New"
    cbHousingStatus.AddItem "Future"
    cbHousingStatus.Value = "New"
    
    cbUDStatus.AddItem "Existing"
    cbUDStatus.AddItem "New"
    cbUDStatus.AddItem "Future"
    cbUDStatus.Value = "New"
    
    Pi = 3.14159265359
End Sub

Private Sub Get_Pole()
    Dim entPole As AcadObject
    Dim obrGP As AcadBlockReference
    Dim attItem, basePnt As Variant

  On Error Resume Next
    
    ThisDrawing.Utility.GetEntity entPole, basePnt, "Select Block: "
    If TypeOf entPole Is AcadBlockReference Then
        Set obrGP = entPole
    Else
        MsgBox "Not a valid block."
        Exit Sub
    End If
    
    attItem = obrGP.GetAttributes
    tbPoleNum.Value = attItem(0).TextString
End Sub

Attribute VB_Name = "ChangeAttData"
Attribute VB_Base = "0{4B0D7B07-2DF9-4179-A5FF-BCCE79385B08}{2B71D373-22AC-4B62-90B7-681E6E66F1B9}"
Attribute VB_GlobalNameSpace = False
Attribute VB_Creatable = False
Attribute VB_PredeclaredId = True
Attribute VB_Exposed = False
Attribute VB_TemplateDerived = False
Attribute VB_Customizable = False
Private Sub cbQuit_Click()
    Me.Hide
End Sub

Private Sub cbRunAll_Click()
    Dim objEntity As AcadEntity
    Dim objBlock As AcadBlockReference
    Dim vAttList, vReturnPnt As Variant
    Dim strLine As String
    Dim dRotation As Double
    'Dim vLine As Variant
    
    If Not tbRotation.Value = "" Then dRotation = CDbl(tbRotation.Value) * 3.14159265359 / 180
    Me.Hide
    
    On Error Resume Next
Get_Another:
    Err = 0
    ThisDrawing.Utility.GetEntity objEntity, vReturnPnt, vbCr & "Select Callout:"
    If Not Err = 0 Then GoTo Exit_Sub
    
    If Not TypeOf objEntity Is AcadBlockReference Then GoTo Exit_Sub
    
    Set objBlock = objEntity
    If objBlock.HasAttributes = False Then GoTo Get_Another
    
    vAttList = objBlock.GetAttributes
    
    For i = 0 To UBound(vAttList)
        If Not tbRotation.Value = "" Then vAttList(i).Rotation = dRotation
        If Not tbHeight.Value = "" Then vAttList(i).Height = CDbl(tbHeight.Value)
        Select Case cbJustification.Value
            Case "Aligned"
                vAttList(i).Alignment = acAlignmentAligned
            Case "BottomCenter"
                vAttList(i).Alignment = acAlignmentBottomCenter
            Case "BottomLeft"
                vAttList(i).Alignment = acAlignmentBottomLeft
            Case "BottomRight"
                vAttList(i).Alignment = acAlignmentBottomRight
            Case "Center"
                vAttList(i).Alignment = acAlignmentCenter
            Case "Fit"
                vAttList(i).Alignment = acAlignmentFit
            Case "Left"
                vAttList(i).Alignment = acAlignmentLeft
            Case "Middle"
                vAttList(i).Alignment = acAlignmentMiddle
            Case "MiddleCenter"
                vAttList(i).Alignment = acAlignmentMiddleCenter
            Case "MiddleLeft"
                vAttList(i).Alignment = acAlignmentMiddleLeft
            Case "MiddleRight"
                vAttList(i).Alignment = acAlignmentMiddleRight
            Case "Right"
                vAttList(i).Alignment = acAlignmentRight
            Case "TopCenter"
                vAttList(i).Alignment = acAlignmentTopCenter
            Case "TopLeft"
                vAttList(i).Alignment = acAlignmentTopLeft
            Case "TopRight"
                vAttList(i).Alignment = acAlignmentTopRight
        End Select
        vAttList(i).Backward = cbBackwards.Value
        vAttList(i).UpsideDown = cbUpsideDown.Value
    Next i
    
    If Not tbFirstAtt.Value = "" Then vAttList(0).TextString = tbFirstAtt.Value
    objBlock.Update
    
    GoTo Get_Another
Exit_Sub:
    Me.show
End Sub

Private Sub cbRunCustomer_Click()
    Dim objEntity As AcadEntity
    Dim objBlock As AcadBlockReference
    Dim vAttList, vReturnPnt As Variant
    Dim strLine As String
    Dim dRotation As Double
    'Dim vLine As Variant
    
    If Not tbRotation.Value = "" Then dRotation = CDbl(tbRotation.Value) * 3.14159265359 / 180
    Me.Hide
    
    On Error Resume Next
Get_Another:
    
    ThisDrawing.Utility.GetEntity objEntity, vReturnPnt, vbCr & "Select Callout:"
    If Not Err = 0 Then GoTo Exit_Sub
    
    If Not TypeOf objEntity Is AcadBlockReference Then GoTo Exit_Sub
    
    Set objBlock = objEntity
    If objBlock.HasAttributes = False Then GoTo Get_Another
    
    vAttList = objBlock.GetAttributes
    
    If Not tbRotation.Value = "" Then vAttList(1).Rotation = dRotation
    If Not tbHeight.Value = "" Then vAttList(1).Height = CDbl(tbHeight.Value)
    Select Case cbJustification.Value
        Case "Aligned"
            vAttList(1).Alignment = acAlignmentAligned
        Case "BottomCenter"
            vAttList(1).Alignment = acAlignmentBottomCenter
        Case "BottomLeft"
            vAttList(1).Alignment = acAlignmentBottomLeft
        Case "BottomRight"
            vAttList(1).Alignment = acAlignmentBottomRight
        Case "Center"
            vAttList(1).Alignment = acAlignmentCenter
        Case "Fit"
            vAttList(1).Alignment = acAlignmentFit
        Case "Left"
            vAttList(1).Alignment = acAlignmentLeft
        Case "Middle"
            vAttList(1).Alignment = acAlignmentMiddle
        Case "MiddleCenter"
            vAttList(1).Alignment = acAlignmentMiddleCenter
        Case "MiddleLeft"
            vAttList(1).Alignment = acAlignmentMiddleLeft
        Case "MiddleRight"
            vAttList(1).Alignment = acAlignmentMiddleRight
        Case "Right"
            vAttList(1).Alignment = acAlignmentRight
        Case "TopCenter"
            vAttList(1).Alignment = acAlignmentTopCenter
        Case "TopLeft"
            vAttList(1).Alignment = acAlignmentTopLeft
        Case "TopRight"
            vAttList(1).Alignment = acAlignmentTopRight
    End Select
    vAttList(1).Backward = cbBackwards.Value
    vAttList(1).UpsideDown = cbUpsideDown.Value
    If Not tbFirstAtt.Value = "" Then vAttList(1).TextString = tbFirstAtt.Value
    objBlock.Update
    
    GoTo Get_Another
Exit_Sub:
    Me.show
End Sub

Private Sub cbRunFirst_Click()
    Dim objEntity As AcadEntity
    Dim objBlock As AcadBlockReference
    Dim vAttList, vReturnPnt As Variant
    Dim strLine As String
    Dim dRotation As Double
    'Dim vLine As Variant
    
    If Not tbRotation.Value = "" Then dRotation = CDbl(tbRotation.Value) * 3.14159265359 / 180
    Me.Hide
    
    On Error Resume Next
Get_Another:
    
    ThisDrawing.Utility.GetEntity objEntity, vReturnPnt, vbCr & "Select Callout:"
    If Not Err = 0 Then GoTo Exit_Sub
    
    If Not TypeOf objEntity Is AcadBlockReference Then GoTo Exit_Sub
    
    Set objBlock = objEntity
    If objBlock.HasAttributes = False Then GoTo Get_Another
    
    vAttList = objBlock.GetAttributes
    
    If Not tbRotation.Value = "" Then vAttList(0).Rotation = dRotation
    If Not tbHeight.Value = "" Then vAttList(0).Height = CDbl(tbHeight.Value)
    Select Case cbJustification.Value
        Case "Aligned"
            vAttList(0).Alignment = acAlignmentAligned
        Case "BottomCenter"
            vAttList(0).Alignment = acAlignmentBottomCenter
        Case "BottomLeft"
            vAttList(0).Alignment = acAlignmentBottomLeft
        Case "BottomRight"
            vAttList(0).Alignment = acAlignmentBottomRight
        Case "Center"
            vAttList(0).Alignment = acAlignmentCenter
        Case "Fit"
            vAttList(0).Alignment = acAlignmentFit
        Case "Left"
            vAttList(0).Alignment = acAlignmentLeft
        Case "Middle"
            vAttList(0).Alignment = acAlignmentMiddle
        Case "MiddleCenter"
            vAttList(0).Alignment = acAlignmentMiddleCenter
        Case "MiddleLeft"
            vAttList(0).Alignment = acAlignmentMiddleLeft
        Case "MiddleRight"
            vAttList(0).Alignment = acAlignmentMiddleRight
        Case "Right"
            vAttList(0).Alignment = acAlignmentRight
        Case "TopCenter"
            vAttList(0).Alignment = acAlignmentTopCenter
        Case "TopLeft"
            vAttList(0).Alignment = acAlignmentTopLeft
        Case "TopRight"
            vAttList(0).Alignment = acAlignmentTopRight
    End Select
    vAttList(0).Backward = cbBackwards.Value
    vAttList(0).UpsideDown = cbUpsideDown.Value
    If Not tbFirstAtt.Value = "" Then vAttList(0).TextString = tbFirstAtt.Value
    objBlock.Update
    
    GoTo Get_Another
Exit_Sub:
    Me.show
End Sub

Private Sub UserForm_Initialize()
    cbJustification.AddItem "Aligned"
    cbJustification.AddItem "BottomCenter"
    cbJustification.AddItem "BottomLeft"
    cbJustification.AddItem "BottomRight"
    cbJustification.AddItem "Center"
    cbJustification.AddItem "Fit"
    cbJustification.AddItem "Left"
    cbJustification.AddItem "Middle"
    cbJustification.AddItem "MiddleCenter"
    cbJustification.AddItem "MiddleLeft"
    cbJustification.AddItem "MiddleRight"
    cbJustification.AddItem "Right"
    cbJustification.AddItem "TopCenter"
    cbJustification.AddItem "TopLeft"
    cbJustification.AddItem "TopRight"
    
    'cbJustification.Value = "MiddleCenter"
End Sub

Attribute VB_Name = "CleanupForm"
Attribute VB_Base = "0{9A73688B-6644-4C0B-B009-29A57356E636}{58052A15-04FF-4A47-8639-DF0B9206FDB6}"
Attribute VB_GlobalNameSpace = False
Attribute VB_Creatable = False
Attribute VB_PredeclaredId = True
Attribute VB_Exposed = False
Attribute VB_TemplateDerived = False
Attribute VB_Customizable = False

Dim vPnt1, vPnt2 As Variant

Private Sub cbParcels_Click()
    Dim objSS6 As AcadSelectionSet
    Dim objEntity As AcadEntity
    Dim objLWP As AcadPolyline
    Dim objLayer As AcadLayer
    Dim strLineType As String
    Dim filterType, filterValue As Variant
    Dim grpCode(0) As Integer
    Dim grpValue(0) As Variant
    
  On Error Resume Next
    
    Me.Hide
    
    strLineType = "PHANTOM"
    ThisDrawing.Linetypes.Load strLineType, "acad.lin"
    
    strLineType = "DASHED"
    ThisDrawing.Linetypes.Load strLineType, "acad.lin"
    
    Set objLayer = ThisDrawing.Layers("Parcels")
    objLayer.color = acYellow
    objLayer.Linetype = "PHANTOM"
    
    ThisDrawing.SendCommand "REGEN" & vbCr
    
    Exit Sub

    grpCode(0) = 0
    grpValue(0) = "AcadLWPolyline"
    grpCode(0) = 8
    grpValue(0) = "Parcels"
    filterType = grpCode
    filterValue = grpValue
    
    Err = 0
    Set objSS6 = ThisDrawing.SelectionSets.Add("objSS6")
    objSS6.Select acSelectionSetAll, , , filterType, filterValue
    If Not Err = 0 Then GoTo Exit_Sub
    
    For Each objEntity In objSS6
        Set objLWP = objEntity
        objLWP.LinetypeGeneration = True 'Not objLWP.LinetypeGeneration
        objLWP.Update
    Next objEntity
    
    Err = 0
    ThisDrawing.SendCommand "-OVERKILL" & vbCr & "P" & vbCr & vbCr & vbCr
    If Not Err = 0 Then
        MsgBox "Broke"
        GoTo Exit_Sub
    End If
    
Exit_Sub:
    objSS6.Clear
    objSS6.Delete
    
    Me.show
End Sub

Private Sub cbResize_Click()
    Dim objSS6 As AcadSelectionSet
    
    Me.Hide
    
    vPnt1 = ThisDrawing.Utility.GetPoint(, "Get BL Corner: ")
    vPnt2 = ThisDrawing.Utility.GetCorner(vPnt1, vbCr & "Get UR Corner: ")
    
    If cbPoles Then ResizeBldgType ("sPole")
    If cbBldg Then Call ResizeBldgs
    If cbGuy Then Call ResizeGuys
    If cbPEDs Then Call ResizePeds
    If cbRoads Then Call ResizeRoads
    If cbDynamic Then Call ResizeDynamicType
    
    Me.show
End Sub

Private Sub cbQuit_Click()
    Me.Hide
End Sub

Private Sub UserForm_Initialize()
    cbScale.AddItem ""
    cbScale.AddItem "50"
    cbScale.AddItem "75"
    cbScale.AddItem "100"
    cbScale.Value = "75"
End Sub

Private Sub ResizeBldgs()
    ResizeBldgType ("Customer")
    'ResizeBldgType ("RES")
    'ResizeBldgType ("TRLR")
    'ResizeBldgType ("MDU")
    'ResizeBldgType ("SCHOOL")
    'ResizeBldgType ("CHURCH")
    'ResizeBldgType ("EXTENTION")
    'ResizeBldgType ("NONRES")
End Sub

Private Sub ResizePeds()
    ResizeBldgType ("sPED")
    ResizeBldgType ("sFP")
    ResizeBldgType ("sHH")
    'ResizeDynamicType ("dHH")
End Sub

Private Sub ResizeGuys()
    ResizeBldgType ("ExAncOL")
    ResizeBldgType ("ExAncOR")
    
    ResizeBldgType ("ExGuyOL")
    ResizeBldgType ("ExGuyOR")
    
    ResizeBldgType ("ohgL")
    ResizeBldgType ("ohgR")
End Sub

Private Sub ResizeRoads()
    Dim objSS5 As AcadSelectionSet
    'Dim objPointBlock As AcadBlockReference
    Dim txtRoads As AcadMText
    Dim objEntity As AcadEntity
    Dim filterType, filterValue As Variant
    Dim grpCode(0 To 1) As Integer
    Dim grpValue(0 To 1) As Variant
    Dim dScale As Double
    
    On Error Resume Next
    
    dScale = CDbl(cbScale.Value) / 100

    grpCode(0) = 0
    grpValue(0) = "MTEXT"
    grpCode(1) = 8
    grpValue(1) = "Roads_MText"
    filterType = grpCode
    filterValue = grpValue
    
    Err = 0
    Set objSS5 = ThisDrawing.SelectionSets.Add("objSS5")
    'objSS5.Select acSelectionSetAll, , , filterType, filterValue
    objSS5.Select acSelectionSetWindow, vPnt1, vPnt2, filterType, filterValue
    If Not Err = 0 Then GoTo Exit_Sub
    
    'MsgBox strLayer & ": " & objSS5.count
        
    For Each objEntity In objSS5
        'If Not objEntity.ObjectName = "AcDbBlockReference" Then GoTo Next_objEntity
        Set txtRoads = objEntity
        
        txtRoads.Height = 8
Next_objEntity:
    Next objEntity
    
Exit_Sub:
    objSS5.Clear
    objSS5.Delete
End Sub

Private Sub ResizeBldgType(strLayer As String)
    Dim objSS5 As AcadSelectionSet
    Dim objPointBlock As AcadBlockReference
    Dim objEntity As AcadEntity
    Dim filterType, filterValue As Variant
    Dim grpCode(0) As Integer
    Dim grpValue(0) As Variant
    Dim dScale As Double
    
    On Error Resume Next
    
    dScale = CDbl(cbScale.Value) / 100

    grpCode(0) = 2
    grpValue(0) = strLayer
    filterType = grpCode
    filterValue = grpValue
    
    Err = 0
    Set objSS5 = ThisDrawing.SelectionSets.Add("objSS5")
    'objSS5.Select acSelectionSetAll, , , filterType, filterValue
    objSS5.Select acSelectionSetWindow, vPnt1, vPnt2, filterType, filterValue
    If Not Err = 0 Then GoTo Exit_Sub
    
    'MsgBox strLayer & ": " & objSS5.count
        
    For Each objEntity In objSS5
        If Not objEntity.ObjectName = "AcDbBlockReference" Then GoTo Next_objEntity
        Set objPointBlock = objEntity
        
        objPointBlock.XScaleFactor = dScale
        objPointBlock.YScaleFactor = dScale
        objPointBlock.ZScaleFactor = dScale
Next_objEntity:
    Next objEntity
    
Exit_Sub:
    objSS5.Clear
    objSS5.Delete
End Sub

Private Sub ResizeDynamicType()
    Dim objSS5 As AcadSelectionSet
    Dim objPointBlock As AcadBlockReference
    Dim objEntity As AcadEntity
    Dim filterType, filterValue As Variant
    Dim grpCode(0) As Integer
    Dim grpValue(0) As Variant
    Dim vProp As Variant
    Dim dScale As Double
    Dim strDBName As String
    Dim strDBList As String
    
    On Error Resume Next
    
    dScale = CDbl(cbScale.Value) / 100

    grpCode(0) = 0
    grpValue(0) = "INSERT"
    filterType = grpCode
    filterValue = grpValue
    
    Err = 0
    Set objSS5 = ThisDrawing.SelectionSets.Add("objSS5")
    objSS5.Select acSelectionSetWindow, vPnt1, vPnt2, filterType, filterValue
    If Not Err = 0 Then GoTo Exit_Sub
    
    For Each objEntity In objSS5
        Set objPointBlock = objEntity
        
        If objPointBlock.IsDynamicBlock Then
            strDBName = objPointBlock.Name
            MsgBox strDBName

            'If Left(strDBName, 1) = "*" Then
                strDBName = "`" + strDBName
                If strDBList = "" Then
                    strDBList = strDBName
                Else
                    If InStr(strDBList, strDBName) = 0 Then
                        strDBList = strDBList & "," & strDBName
                    End If
                End If
            'End If
        End If
    Next objEntity
    
    MsgBox strDBList
    
    objSS5.Clear
    
    Dim grpCode2(0 To 1)
    Dim grpValue2(0 To 1)
    grpCode2(0) = 0: grpValue2(0) = "Insert"
    grpCode2(1) = 2: grpValue2(1) = strDBList
    filterType = grpCode2
    filterValue = grpValue2
    
    objSS5.Select acSelectionSetWindow, vPnt1, vPnt2, filterType, filterValue
        
    For Each objEntity In objSS5
        'If Not objEntity.ObjectName = "AcDbBlockReference" Then GoTo Next_objEntity
        Set objPointBlock = objEntity
        
        objPointBlock.XScaleFactor = dScale
        objPointBlock.YScaleFactor = dScale
        objPointBlock.ZScaleFactor = dScale
Next_objEntity:
    Next objEntity
    
Exit_Sub:
    objSS5.Clear
    objSS5.Delete
End Sub

Attribute VB_Name = "ClosureLocations"
Attribute VB_Base = "0{80266F2B-21C1-4934-9883-2B7067AEDF95}{2C8FB91F-DA75-4800-803D-F9E678DCF0D0}"
Attribute VB_GlobalNameSpace = False
Attribute VB_Creatable = False
Attribute VB_PredeclaredId = True
Attribute VB_Exposed = False
Attribute VB_TemplateDerived = False
Attribute VB_Customizable = False
Private Sub cbAddPoles_Click()
    Dim objSS As AcadSelectionSet
    Dim objEntity As AcadEntity
    Dim objBlock As AcadBlockReference
    Dim vAttList, vLine, vItem As Variant
    Dim vReturnPnt As Variant
    Dim iIndex As Integer
    Dim strClosure, strHO1, strCounts As String
    
    On Error Resume Next
    
    Me.Hide
    
Get_Unit:
    
    ThisDrawing.Utility.GetEntity objEntity, vReturnPnt, vbCr & "Get Closure Unit:"
    If Not Err = 0 Then GoTo Exit_Sub
    
    If Not TypeOf objEntity Is AcadBlockReference Then GoTo Exit_Sub
    
    Set objBlock = objEntity
    
    If Not objBlock.Name = "pole_unit" Then GoTo Exit_Sub
    
    vAttList = objBlock.GetAttributes
                    
    If InStr(vAttList(3).TextString, "HACO") > 0 Then GoTo Found_Closure
    If Not InStr(vAttList(3).TextString, "HBFO") > 0 Then GoTo Exit_Sub
                    
Found_Closure:
    strClosure = Replace(vAttList(3).TextString, "+", "")
    vLine = Split(strClosure, "=")
    strClosure = vLine(0)
    vItem = Split(vLine(1), "  ")
    strClosure = strClosure & "  " & vItem(1)
    If InStr(vAttList(3).TextString, "+WH") > 0 Then strClosure = "Existing"
    
    If lbClosures.ListCount < 1 Then
        lbClosures.AddItem vAttList(0).TextString
        lbClosures.List(0, 1) = strClosure
        
        iIndex = 0
        
        GoTo Get_Closure
    Else
        'For i = 0 To lbClosures.ListCount - 1
            'If lbClosures.List(i, 0) = vAttList(0).TextString Then
                'lbClosures.List(i, 1) = strClosure
                
                'iIndex = i
                
                'GoTo Get_Closure
            'End If
        'Next i
        
        lbClosures.AddItem vAttList(0).TextString
        iIndex = lbClosures.ListCount - 1
        lbClosures.List(iIndex, 1) = strClosure
    End If
    
Get_Closure:
    
    Err = 0
    ThisDrawing.Utility.GetEntity objEntity, vReturnPnt, vbCr & "Get Closure Callout:"
    If Not Err = 0 Then GoTo Exit_Sub
    
    If Not TypeOf objEntity Is AcadBlockReference Then GoTo Exit_Sub
    
    Set objBlock = objEntity
    
    If Not objBlock.Name = "terminal" Then GoTo Exit_Sub
    
    vAttList = objBlock.GetAttributes
    
    strCounts = Replace(vAttList(0).TextString, " ", "")
    strCounts = Replace(strCounts, "\P", " + ")
    'strCounts = Replace(strCounts, vbLf, "")
    
    vLine = Split(vAttList(1).TextString, "=")
    strHO1 = vLine(1)
    
    lbClosures.List(iIndex, 2) = strHO1
    lbClosures.List(iIndex, 3) = strCounts
    
    GoTo Get_Unit
    
Exit_Sub:
    Call GetTotals
    
    Me.show
End Sub

Private Sub cbExport_Click()
    If lbClosures.ListCount < 1 Then Exit Sub
    
    Dim strPath, strName, strFile As String
    Dim vTemp As Variant
    
    strPath = ThisDrawing.Path
    strName = ThisDrawing.Name
    vTemp = Split(strName, " ")
    
    strFile = strPath & "\" & vTemp(0) & " Closure Locations.csv"
    
    Open strFile For Output As #1
    
    Print #1, "Location,Closure Type,HO1,Counts Spliced"
    
    For i = 0 To lbClosures.ListCount - 1
        Print #1, lbClosures.List(i, 0) & "," & lbClosures.List(i, 1) & "," & lbClosures.List(i, 2) & "," & lbClosures.List(i, 3)
    Next i
    
    Close #1
End Sub

Private Sub cbGetPoles_Click()
    Dim objSS As AcadSelectionSet
    Dim objEntity As AcadEntity
    Dim objBlock As AcadBlockReference
    Dim vAttList As Variant
    Dim filterType, filterValue As Variant
    Dim vPnt1, vPnt2 As Variant
    Dim grpCode(0) As Integer
    Dim grpValue(0) As Variant
    Dim dPnt1(0 To 2) As Double
    Dim dPnt2(0 To 2) As Double
    Dim iAtt As Integer
    Dim vUnits, vItem, vCounts As Variant
    Dim strSpliced, strClosure As String
    Dim strCoords As String
    Dim iHO1 As Integer
    
    
    'Dim vTemp As Variant
    'Dim str1, str2, strUnit As String
    'Dim iRes, iBus As Integer
    'Dim iAF, iBF, iUF, iUNK As Integer
    'Dim strExchange As String

    grpCode(0) = 2
    grpValue(0) = "sPole,sPed,sHH"
    filterType = grpCode
    filterValue = grpValue
    
    lbClosures.Clear
    
    iHO1 = 0
    
  On Error Resume Next
    Me.Hide
    
    vPnt1 = ThisDrawing.Utility.GetPoint(, "Get BL Corner: ")
    vPnt2 = ThisDrawing.Utility.GetCorner(vPnt1, vbCr & "Get UR Corner: ")
    
    dPnt1(0) = vPnt1(0)
    dPnt1(1) = vPnt1(1)
    dPnt1(2) = vPnt1(2)
    
    dPnt2(0) = vPnt2(0)
    dPnt2(1) = vPnt2(1)
    dPnt2(2) = vPnt2(2)
    
    Set objSS = ThisDrawing.SelectionSets.Add("objSS")
    If Not Err = 0 Then
        Set objSS = ThisDrawing.SelectionSets.Item("objSS")
        Err = 0
    End If
    objSS.Select acSelectionSetWindow, dPnt1, dPnt2, filterType, filterValue
    
    For Each objBlock In objSS
        iHO1 = 0
        
        vAttList = objBlock.GetAttributes
        
        If objBlock.Name = "sPole" Then
            iAtt = 27
        Else
            iAtt = 7
        End If
        
        If vAttList(iAtt).TextString = "" Then GoTo Next_Object
        If Len(vAttList(iAtt).TextString) < 6 Then GoTo Next_Object
        
        vUnits = Split(vAttList(iAtt).TextString, ";;")
        
        For i = 0 To UBound(vUnits)
            Select Case Left(vUnits(i), 5)
                Case "+HACO", "+HBFO", "+WHAC", "+WHBF"
                    vItem = Split(vUnits(i), "=")
                    strClosure = Replace(vItem(0), "+", "")
                    
                    strCoords = objBlock.InsertionPoint(0) & "," & objBlock.InsertionPoint(1)
                    
                    strSpliced = Replace(vAttList(iAtt - 1).TextString, "[A1] ", "")
                    
                    If strSpliced = "" Then
                        iHO1 = 0
                    Else
                        vItem = Split(strSpliced, " + ")
                        
                        For j = 0 To UBound(vItem)
                            If Not vItem(j) = "" Then
                                vTemp = Split(vItem(j), ": ")
                                vCounts = Split(vTemp(1), "-")
                            
                                If UBound(vCounts) = 0 Then
                                    iHO1 = iHO1 + 1
                                Else
                                    iHO1 = iHO1 + CInt(Replace(vCounts(1), ":", "")) - CInt(vCounts(0)) + 1
                                End If
                            End If
                        Next j
                    End If
                    
                    lbClosures.AddItem vAttList(0).TextString
                    lbClosures.List(lbClosures.ListCount - 1, 1) = strClosure
                    lbClosures.List(lbClosures.ListCount - 1, 2) = iHO1
                    lbClosures.List(lbClosures.ListCount - 1, 3) = strSpliced
                    lbClosures.List(lbClosures.ListCount - 1, 4) = strCoords
                    
                    GoTo Next_Object
            End Select
        Next i
        
Next_Object:
    Next objBlock
    
Exit_Sub:
    objSS.Clear
    objSS.Delete
    
    Call GetTotals
    
    Me.show
End Sub

Private Sub cbImport_Click()
    Dim strPath, strName, strFile As String
    Dim strLine As String
    Dim vTemp As Variant
    Dim iIndex As Integer
    
    strPath = ThisDrawing.Path
    strName = ThisDrawing.Name
    vTemp = Split(strName, " ")
    
    strFile = strPath & "\" & vTemp(0) & " Closure Locations.csv"
    
    On Error Resume Next
    
    Open strFile For Input As #1
    If Not Err = 0 Then
        MsgBox "No file found"
        Exit Sub
    End If
    
    lbClosures.Clear
    Line Input #1, strLine
    
    While Not EOF(1)
        Line Input #1, strLine
        
        vTemp = Split(strLine, ",")
        
        lbClosures.AddItem vTemp(0)
        iIndex = lbClosures.ListCount - 1
        lbClosures.List(iIndex, 1) = vTemp(1)
        lbClosures.List(iIndex, 2) = vTemp(2)
        lbClosures.List(iIndex, 3) = vTemp(3)
    Wend
    
    Close #1
End Sub

Private Sub cbQuit_Click()
    Me.Hide
End Sub

Private Sub lbClosures_DblClick(ByVal Cancel As MSForms.ReturnBoolean)
    Dim vCoords As Variant
    Dim viewCoordsB(0 To 2) As Double
    Dim viewCoordsE(0 To 2) As Double
    
    vCoords = Split(lbClosures.List(lbClosures.ListIndex, 4), ",")
    
    viewCoordsB(0) = CDbl(vCoords(0)) - 300
    viewCoordsB(1) = CDbl(vCoords(1)) - 300
    viewCoordsB(2) = 0#
    viewCoordsE(0) = CDbl(vCoords(0)) + 300
    viewCoordsE(1) = CDbl(vCoords(1)) + 300
    viewCoordsE(2) = 0#
    
    Me.Hide
    
    ThisDrawing.Application.ZoomWindow viewCoordsB, viewCoordsE
    
    Me.show
End Sub

Private Sub lbClosures_KeyDown(ByVal KeyCode As MSForms.ReturnInteger, ByVal Shift As Integer)
    If lbClosures.ListIndex < 0 Then Exit Sub
    
    Dim iIndex As Integer
    
    iIndex = lbClosures.ListIndex
    
    Select Case KeyCode
        Case vbKeyDelete
            lbClosures.RemoveItem iIndex
            
            iIndex = iIndex - 1
            If iIndex < 0 Then iIndex = 0
            
            lbClosures.ListIndex = iIndex
    End Select
    
    Call GetTotals
End Sub

Private Sub UserForm_Initialize()
    lbClosures.ColumnCount = 5
    lbClosures.ColumnWidths = "120;108;36;190;10"
End Sub

Private Sub GetTotals()
    If lbClosures.ListCount < 1 Then Exit Sub
    
    Dim iCount, iNew, iHO1 As Integer
    
    iCount = lbClosures.ListCount
    iHO1 = 0
    iNew = 0
    
    For i = 0 To iCount - 1
        If Not lbClosures.List(i, 1) = "Existing" Then iNew = iNew + 1
        
        If lbClosures.List(i, 2) = "" Then GoTo Next_I
        
        iHO1 = iHO1 + CInt(lbClosures.List(i, 2))
Next_I:
    Next i
    
    tbTotalCount = iCount
    tbTotalNew = iNew
    tbTotalHO1 = iHO1
End Sub

Attribute VB_Name = "ConvertBlockLayers"
Attribute VB_Base = "0{210E3EFF-0EFD-4E79-B76E-165ABA2DB10C}{E2997169-C3B3-458A-9149-A18BAEE60DB2}"
Attribute VB_GlobalNameSpace = False
Attribute VB_Creatable = False
Attribute VB_PredeclaredId = True
Attribute VB_Exposed = False
Attribute VB_TemplateDerived = False
Attribute VB_Customizable = False

Private Sub cbClear_Click()
    lbConditions.Clear
    cbValue.Clear
    cbValue.Value = ""
    lAttTag.Caption = "Attribute Tag"
    cbUpdate.Enabled = False
    lbTo.Enabled = True
    cbToList.Enabled = True
End Sub

Private Sub cbConvert_Click()
    Dim filterType, filterValue As Variant
    Dim grpCode(0) As Integer
    Dim grpValue(0) As Variant
    Dim objSS2 As AcadSelectionSet
    Dim objBlock As AcadBlockReference
    Dim vBlockAtt As Variant
    
    Dim iAttList As Integer
    Dim strValue, strLayer As String
    
    On Error Resume Next
    
    grpCode(0) = 2
    grpValue(0) = cbToList.Value
    filterType = grpCode
    filterValue = grpValue
    
    Err = 0
    Set objSS2 = ThisDrawing.SelectionSets.Add("objSS2")
    If Not Err = 0 Then
        Set objSS2 = ThisDrawing.SelectionSets.Item("objSS2")
        objSS2.Clear
    End If
    
    objSS2.Select acSelectionSetAll, , , filterType, filterValue
    MsgBox cbToList.Value & " found:  " & objSS2.count
    
    For Each objBlock In objSS2
        vBlockAtt = objBlock.GetAttributes
        
        For i = 0 To lbConditions.ListCount - 1
            iAttList = CInt(lbConditions.List(i, 0))
            strValue = lbConditions.List(i, 1)
            strLayer = lbConditions.List(i, 2)
            
            If vBlockAtt(iAttList).TextString = strValue Then
                objBlock.Layer = strLayer
                objBlock.Update
            End If
        Next i
    Next objBlock

End Sub

Private Sub cbQuit_Click()
    Me.Hide
End Sub

Private Sub cbToList_Change()
    Dim filterType, filterValue As Variant
    Dim grpCode(0) As Integer
    Dim grpValue(0) As Variant
    Dim objSS2 As AcadSelectionSet
    
    On Error Resume Next
    
    Dim objBlock As AcadBlockReference
    Dim vAttList As Variant
    
    grpCode(0) = 2
    grpValue(0) = cbToList.Value
    filterType = grpCode
    filterValue = grpValue
    
    Err = 0
    Set objSS2 = ThisDrawing.SelectionSets.Add("objSS2")
    If Not Err = 0 Then
        Set objSS2 = ThisDrawing.SelectionSets.Item("objSS2")
        objSS2.Clear
    End If
    
    objSS2.Select acSelectionSetAll, , , filterType, filterValue
        
    For Each objBlock In objSS2
        vAttList = objBlock.GetAttributes
        lbTo.Clear
        For i = 0 To UBound(vAttList)
            lbTo.AddItem
            lbTo.List(i, 0) = i
            lbTo.List(i, 1) = vAttList(i).TagString
            'lbTo.List(i, 2) = ""
        Next i
        GoTo Exit_Next
    Next objBlock
Exit_Next:
End Sub

Private Sub cbUpdate_Click()
    lbConditions.AddItem
    lbConditions.List(lbConditions.ListCount - 1, 0) = lbTo.List(lbTo.ListIndex, 0)
    lbConditions.List(lbConditions.ListCount - 1, 1) = cbValue.Value
    lbConditions.List(lbConditions.ListCount - 1, 2) = cbToLayer.Value
End Sub

Private Sub lbConditions_KeyDown(ByVal KeyCode As MSForms.ReturnInteger, ByVal Shift As Integer)
    Select Case KeyCode
        Case vbKeyDelete
            lbConditions.RemoveItem lbConditions.ListIndex
    End Select
End Sub

Private Sub lbTo_DblClick(ByVal Cancel As MSForms.ReturnBoolean)
    lAttTag.Caption = lbTo.List(lbTo.ListIndex, 1)
    'cbValue.Value = lbTo.List(lbTo.ListIndex, 2)
    cbUpdate.Enabled = True
    lbTo.Enabled = False
    cbToList.Enabled = False
    cbValue.SetFocus
    
    Call GetValues
End Sub

Private Sub UserForm_Initialize()
    lbConditions.Clear
    lbConditions.ColumnCount = 3
    lbConditions.ColumnWidths = "20;80;100"
    
    lbTo.Clear
    lbTo.ColumnCount = 2
    lbTo.ColumnWidths = "20;80"
    
    Dim objBlocks As AcadBlocks
    Dim strLine As String
            
    Set objBlocks = ThisDrawing.Blocks
    For i = 0 To objBlocks.count - 1
        strLine = objBlocks(i).Name
        If Not Left(strLine, 1) = "*" Then cbToList.AddItem objBlocks(i).Name
    Next i
    
    Dim objLayers As AcadLayers
    Dim objLayer As AcadLayer
    
    Set objLayers = ThisDrawing.Layers
    For Each objLayer In objLayers
        cbToLayer.AddItem objLayer.Name
    Next objLayer
    cbToLayer.Value = "0"
End Sub

Private Sub GetValues()
    Dim filterType, filterValue As Variant
    Dim grpCode(0) As Integer
    Dim grpValue(0) As Variant
    Dim objSS2 As AcadSelectionSet
    
    Dim iCount As Integer
    Dim strTest As String
    
    On Error Resume Next
    
    Dim objBlock As AcadBlockReference
    Dim vAttList As Variant
    
    grpCode(0) = 2
    grpValue(0) = cbToList.Value
    filterType = grpCode
    filterValue = grpValue
    
    Err = 0
    Set objSS2 = ThisDrawing.SelectionSets.Add("objSS2")
    If Not Err = 0 Then
        Set objSS2 = ThisDrawing.SelectionSets.Item("objSS2")
        objSS2.Clear
    End If
    
    objSS2.Select acSelectionSetAll, , , filterType, filterValue
    
    cbValue.Clear
        
    For Each objBlock In objSS2
        vAttList = objBlock.GetAttributes
        strTest = vAttList(lbTo.ListIndex).TextString
        iCount = 0
        
        For i = 0 To cbValue.ListCount - 1
            If strTest = cbValue.List(i) Then GoTo Exit_Next_I
        Next i
        
        cbValue.AddItem strTest
Exit_Next_I:
    Next objBlock
End Sub

Attribute VB_Name = "ConvertBlockText"
Attribute VB_Base = "0{38E2872F-2318-4E82-821D-C2082418EC6F}{73DAE8F6-5336-4772-AC47-89A3D8BF8F0F}"
Attribute VB_GlobalNameSpace = False
Attribute VB_Creatable = False
Attribute VB_PredeclaredId = True
Attribute VB_Exposed = False
Attribute VB_TemplateDerived = False
Attribute VB_Customizable = False

Private Sub cbClear_Click()
    lbConditions.Clear
    cbValue.Clear
    cbValue.Value = ""
    lAttTag.Caption = "Attribute Tag"
    cbUpdate.Enabled = False
    lbTo.Enabled = True
    cbToList.Enabled = True
End Sub

Private Sub cbConvert_Click()
    Dim filterType, filterValue As Variant
    Dim grpCode(0) As Integer
    Dim grpValue(0) As Variant
    Dim objSS2 As AcadSelectionSet
    Dim objBlock As AcadBlockReference
    Dim vBlockAtt As Variant
    Dim vLine, vItem As String
    Dim strType, strFind As String
    Dim iAttList, iCopy As Integer
    Dim strValue, strLayer As String
    
    On Error Resume Next
    
    grpCode(0) = 2
    grpValue(0) = cbToList.Value
    filterType = grpCode
    filterValue = grpValue
    
    Err = 0
    Set objSS2 = ThisDrawing.SelectionSets.Add("objSS2")
    If Not Err = 0 Then
        Set objSS2 = ThisDrawing.SelectionSets.Item("objSS2")
        objSS2.Clear
    End If
    
    objSS2.Select acSelectionSetAll, , , filterType, filterValue
    MsgBox cbToList.Value & " found:  " & objSS2.count
    
    For Each objBlock In objSS2
        vBlockAtt = objBlock.GetAttributes
        
        For i = 0 To lbConditions.ListCount - 1
            iAttList = CInt(lbConditions.List(i, 0))
            
            strValue = lbConditions.List(i, 1)
            If Not strValue = vBlockAtt(iAttList).TextString Then
                If Not strValue = "<<all>>" Then GoTo Next_objBlock
            End If
            If strValue = "<<blank>>" Then strValue = ""
            
            strLayer = lbConditions.List(i, 2)
            If strLayer = "<<blank>>" Then strLayer = ""
            
            strType = "R"
            
            If InStr(strLayer, "++") > 0 Then
                If Left(strLayer, 2) = "++" Then
                    strType = "AE"
                Else
                    strType = "AB"
                End If
                
                strLayer = Replace(strLayer, "++", "")
            End If
            
            If InStr(strLayer, "--") > 0 Then
                strType = "MM"
                strLayer = Replace(strLayer, "--", "")
            End If
            
            'If InStr(strLayer, "}") > 0 Then
                'strType = "RA"
                'vLine = Split(strLayer, "}")
                'vItem = Split(vLine(0), "{")
                'iCopy = CInt(vItem(1))
                'strFind = "{" & iCopy & "}"
                
                'strLayer = Replace(strLayer, strFind, vBlockAtt(iCopy).TextString)
            'End If
            
            Select Case strType
                Case "AB"
                    vBlockAtt(iAttList).TextString = strLayer & vBlockAtt(iAttList).TextString
                Case "AE"
                    vBlockAtt(iAttList).TextString = vBlockAtt(iAttList).TextString & strLayer
                Case "MM"
                    vBlockAtt(iAttList).TextString = Replace(vBlockAtt(iAttList).TextString, strLayer, "")
                'Case "RA"
                    'vBlockAtt(iAttList).TextString = strLayer
                Case Else
                    If strValue = "" Then
                        vBlockAtt(iAttList).TextString = strLayer
                    Else
                        If InStr(vBlockAtt(iAttList).TextString, strValue) > 0 Then vBlockAtt(iAttList).TextString = Replace(vBlockAtt(iAttList).TextString, strValue, strLayer)
                    End If
            End Select
            
        Next i
Next_objBlock:
    Next objBlock
    lbConditions.Clear
End Sub

Private Sub cbQuit_Click()
    Me.Hide
End Sub

Private Sub cbToList_Change()
    Dim filterType, filterValue As Variant
    Dim grpCode(0) As Integer
    Dim grpValue(0) As Variant
    Dim objSS2 As AcadSelectionSet
    
    On Error Resume Next
    
    Dim objBlock As AcadBlockReference
    Dim vAttList As Variant
    
    grpCode(0) = 2
    grpValue(0) = cbToList.Value
    filterType = grpCode
    filterValue = grpValue
    
    Err = 0
    Set objSS2 = ThisDrawing.SelectionSets.Add("objSS2")
    If Not Err = 0 Then
        Set objSS2 = ThisDrawing.SelectionSets.Item("objSS2")
        objSS2.Clear
    End If
    
    objSS2.Select acSelectionSetAll, , , filterType, filterValue
        
    For Each objBlock In objSS2
        vAttList = objBlock.GetAttributes
        lbTo.Clear
        For i = 0 To UBound(vAttList)
            lbTo.AddItem
            lbTo.List(i, 0) = i
            lbTo.List(i, 1) = vAttList(i).TagString
            'lbTo.List(i, 2) = ""
        Next i
        GoTo Exit_Next
    Next objBlock
Exit_Next:
End Sub

Private Sub cbUpdate_Click()
    lbConditions.AddItem
    lbConditions.List(lbConditions.ListCount - 1, 0) = lbTo.List(lbTo.ListIndex, 0)
    If tbChange.Value = "" Then
        lbConditions.List(lbConditions.ListCount - 1, 1) = "<<blank>>"
    Else
        lbConditions.List(lbConditions.ListCount - 1, 1) = cbValue.Value
    End If
    If tbChange.Value = "" Then
        lbConditions.List(lbConditions.ListCount - 1, 2) = "<<blank>>"
    Else
        lbConditions.List(lbConditions.ListCount - 1, 2) = tbChange.Value
    End If
End Sub

Private Sub lbConditions_KeyDown(ByVal KeyCode As MSForms.ReturnInteger, ByVal Shift As Integer)
    Select Case KeyCode
        Case vbKeyDelete
            lbConditions.RemoveItem lbConditions.ListIndex
    End Select
End Sub

Private Sub lbTo_DblClick(ByVal Cancel As MSForms.ReturnBoolean)
    lAttTag.Caption = lbTo.List(lbTo.ListIndex, 1)
    'cbValue.Value = lbTo.List(lbTo.ListIndex, 2)
    cbUpdate.Enabled = True
    lbTo.Enabled = False
    cbToList.Enabled = False
    cbValue.SetFocus
    
    Call GetValues
End Sub

Private Sub UserForm_Initialize()
    lbConditions.Clear
    lbConditions.ColumnCount = 3
    lbConditions.ColumnWidths = "20;80;100"
    
    lbTo.Clear
    lbTo.ColumnCount = 2
    lbTo.ColumnWidths = "20;80"
    
    Dim objBlocks As AcadBlocks
    Dim strLine As String
            
    Set objBlocks = ThisDrawing.Blocks
    For i = 0 To objBlocks.count - 1
        strLine = objBlocks(i).Name
        If Not Left(strLine, 1) = "*" Then cbToList.AddItem objBlocks(i).Name
    Next i
    
    Dim objLayers As AcadLayers
    Dim objLayer As AcadLayer
    
    'Set objLayers = ThisDrawing.Layers
    'For Each objLayer In objLayers
        'cbToLayer.AddItem objLayer.Name
    'Next objLayer
    'cbToLayer.Value = "0"
End Sub

Private Sub GetValues()
    Dim filterType, filterValue As Variant
    Dim grpCode(0) As Integer
    Dim grpValue(0) As Variant
    Dim objSS2 As AcadSelectionSet
    
    Dim iCount As Integer
    Dim strTest As String
    
    On Error Resume Next
    
    Dim objBlock As AcadBlockReference
    Dim vAttList As Variant
    
    grpCode(0) = 2
    grpValue(0) = cbToList.Value
    filterType = grpCode
    filterValue = grpValue
    
    Err = 0
    Set objSS2 = ThisDrawing.SelectionSets.Add("objSS2")
    If Not Err = 0 Then
        Set objSS2 = ThisDrawing.SelectionSets.Item("objSS2")
        objSS2.Clear
    End If
    
    objSS2.Select acSelectionSetAll, , , filterType, filterValue
    
    cbValue.Clear
    cbValue.AddItem "<<all>>"
        
    For Each objBlock In objSS2
        vAttList = objBlock.GetAttributes
        strTest = vAttList(lbTo.ListIndex).TextString
        iCount = 0
        
        For i = 0 To cbValue.ListCount - 1
            If strTest = cbValue.List(i) Then GoTo Exit_Next_I
        Next i
        
        cbValue.AddItem strTest
Exit_Next_I:
    Next objBlock
End Sub

Attribute VB_Name = "ConvertBlocks"
Attribute VB_Base = "0{63DA685B-1885-44BA-AB75-4A8C883C5212}{F555DDB4-0EC2-45B1-A72F-ADEDB386AC2A}"
Attribute VB_GlobalNameSpace = False
Attribute VB_Creatable = False
Attribute VB_PredeclaredId = True
Attribute VB_Exposed = False
Attribute VB_TemplateDerived = False
Attribute VB_Customizable = False
Dim objSS As AcadSelectionSet

Private Sub cbConvert_Click()
    Dim filterType, filterValue As Variant
    Dim grpCode(0) As Integer
    Dim grpValue(0) As Variant
    
    Dim objEntity As AcadEntity
    Dim objPoint As AcadPoint
    Dim objBlock As AcadBlockReference
    Dim objLWP As AcadLWPolyline
    Dim vBlockAtt As Variant
    
    Dim objPlace As AcadBlockReference
    Dim vAttList As Variant
    Dim dInsertPnt(0 To 2) As Double
    Dim dScale As Double
    
    Dim amap As AcadMap
    Dim ODRcs As ODRecords
    Dim ODRc As ODRecord
    Dim tbl As ODTable
    Dim tbls As ODTables
    
    Dim strAttList() As String
    Dim strAttTemp() As String
    Dim strLine, strTemp As String
    Dim str1, str2, str3 As String
    Dim iCount, iTest As Integer
    Dim iTemp As Integer
    Dim vLine, vTemp, vForm As Variant
    Dim vData As Variant
    
    Dim vPnt1, vPnt2 As Variant
    Dim dCoords() As Double
    Dim vReturnPnt, vCoords As Variant
    Dim iCounter As Integer
    Dim dPnt1(0 To 2) As Double
    Dim dPnt2(0 To 2) As Double
    
    On Error Resume Next
    
    ReDim strAttList(lbTo.ListCount - 1)
    ReDim strAttTemp(lbTo.ListCount - 1)
    
    iCount = 0
    strLine = ""
    dScale = CDbl(cbScale.Value)
    
    For i = 0 To UBound(strAttList)
        strAttList(i) = lbTo.List(i, 2)
    Next i
    
    For i = 0 To UBound(strAttList)
        If InStr(strAttList(i), "{") > 0 Then
            iCount = iCount + 1
        End If
    Next i
    
    If cbFromType.Value = "Block" Then
        grpCode(0) = 2
    Else
        grpCode(0) = 8
    End If
    
    grpValue(0) = cbFromList.Value
    filterType = grpCode
    filterValue = grpValue
            
    objSS.Clear
    
    Err = 0
    
    Me.Hide
    
    Select Case cbSelection.Value
        Case "All"
            objSS.Select acSelectionSetAll, , , filterType, filterValue
        Case "Window"
            vPnt1 = ThisDrawing.Utility.GetPoint(, "Get BL Corner: ")
            vPnt2 = ThisDrawing.Utility.GetCorner(vPnt1, vbCr & "Get UR Corner: ")
            
            dPnt1(0) = vPnt1(0)
            dPnt1(1) = vPnt1(1)
            dPnt1(2) = vPnt1(2)
            
            dPnt2(0) = vPnt2(0)
            dPnt2(1) = vPnt2(1)
            dPnt2(2) = vPnt2(2)
            
            objSS.Select acSelectionSetWindow, dPnt1, dPnt2, filterType, filterValue
        Case "Polygon"
                ThisDrawing.Utility.GetEntity objEntity, vReturnPnt, "Select Polygon Border: "
                If Not objEntity.ObjectName = "AcDbPolyline" Then
                    MsgBox "Error: Invalid Selection."
                    Me.show
                    Exit Sub
                End If
            
                Set objLWP = objEntity
                vCoords = objLWP.Coordinates
                
                iTemp = (UBound(vCoords) + 1) / 2 * 3 - 1
                ReDim dCoords(iTemp) As Double
                
                iCounter = 0
                For i = 0 To UBound(vCoords) Step 2
                    dCoords(iCounter) = vCoords(i)
                    iCounter = iCounter + 1
                    dCoords(iCounter) = vCoords(i + 1)
                    iCounter = iCounter + 1
                    dCoords(iCounter) = 0#
                    iCounter = iCounter + 1
                Next i
                
                objSS.SelectByPolygon acSelectionSetCrossingPolygon, dCoords, filterType, filterValue
    End Select
    
    MsgBox cbFromType.Value & " found:  " & objSS.count
    
    For Each objEntity In objSS
        If TypeOf objEntity Is AcadPoint Then       '<------------------------------------------------- From Point w/OD
            Set objPoint = objEntity
            dInsertPnt(0) = objPoint.Coordinates(0)
            dInsertPnt(1) = objPoint.Coordinates(1)
            dInsertPnt(2) = objPoint.Coordinates(2)
            
            If iCount = 0 Then
                For i = 0 To UBound(strAttList)
                    strAttTemp(i) = strAttList(i)
                Next i
                GoTo Place_Block
            End If
    
            Set amap = ThisDrawing.Application.GetInterfaceObject("AutoCADMap.Application")
    
            Set tbls = amap.Projects(ThisDrawing).ODTables
            If tbls.count > 0 Then
                For Each tbl In tbls
                    If tbl.Name = cbFromList.Value Then GoTo Exit_For
                Next
            End If
Exit_For:

            Set ODRcs = tbl.GetODRecords
            
            boolVal = ODRcs.Init(objEntity, True, False)
            Set ODRc = ODRcs.Record
            
            For i = 0 To UBound(strAttList)
                If InStr(strAttList(i), "}") Then
                    vLine = Split(strAttList(i), "}")
                    iTest = UBound(vLine)
                    
                    If vLine(iTest) = "" Then iTest = iTest - 1
                    
                    strLine = ""
                    
                    For j = 0 To iTest
                        If InStr(vLine(j), "{") Then
                            vTemp = Split(vLine(j), "{")
                            strLine = strLine & vTemp(0)
                            strTemp = vTemp(1)
                            
                            vTemp = Split(strTemp, "~")
                            iTemp = CInt(vTemp(0))
                            
                            Select Case UBound(vTemp)
                                Case Is = 0
                                    If strLine = "" Then
                                        strLine = ODRc.Item(iTemp).Value
                                    Else
                                        strLine = strLine & ODRc.Item(iTemp).Value
                                    End If
                                    
                                Case Is = 1
                                    str1 = ODRc.Item(iTemp).Value
                                    vData = Split(str1, " ")
                                    
                                    Select Case UCase(vTemp(1))
                                        Case "L"
                                            If strLine = "" Then
                                                strLine = vData(UBound(vData))
                                            Else
                                                strLine = strLine & " " & vData(UBound(vData))
                                            End If
                                        Case "-L"
                                            For h = 0 To UBound(vData) - 1
                                                If strLine = "" Then
                                                    strLine = vData(h)
                                                Else
                                                    strLine = strLine & " " & vData(h)
                                                End If
                                            Next h
                                    End Select
                                    
                                Case Is = 2
                                    str1 = ODRc.Item(iTemp).Value
                                    str2 = vTemp(1)
                                    str3 = vTemp(2)
                                    
                                    strTemp = GetTextSegment((str1), (str2), (str3))
                                    If strLine = "" Then
                                        strLine = strTemp
                                    Else
                                        strLine = strLine & " " & strTemp
                                    End If
                            End Select
                        Else
                            If strLine = "" Then
                                strLine = vLine(j)
                            Else
                                strLine = strLine & " " & vLine(j)
                            End If
                        End If
                    Next j
                    strAttTemp(i) = strLine
                Else
                    strAttTemp(i) = strAttList(i)
                End If
            Next i
            
            
            
            
        Else                                        '<------------------------------------------------- From Block
            Set objBlock = objEntity
            dInsertPnt(0) = objBlock.InsertionPoint(0)
            dInsertPnt(1) = objBlock.InsertionPoint(1)
            dInsertPnt(2) = objBlock.InsertionPoint(2)
            
            If iCount = 0 Then
                For i = 0 To UBound(strAttList)
                    strAttTemp(i) = strAttList(i)
                Next i
                GoTo Place_Block
            End If
            
            vBlockAtt = objBlock.GetAttributes
            
            For i = 0 To UBound(strAttList)
                If InStr(strAttList(i), "}") Then
                    vLine = Split(strAttList(i), "}")
                    iTest = UBound(vLine)
                    
                    If vLine(iTest) = "" Then iTest = iTest - 1
                    
                    strLine = ""
                    
                    For j = 0 To iTest
                        If InStr(vLine(j), "{") Then 'Left(vLine(j), 1) = "{" Then
                            vTemp = Split(vLine(j), "{")
                            strLine = strLine & vTemp(0)
                            strTemp = vTemp(1)
                            'vLine(j) = Replace(vLine(j), "{", "")
                            
                            vTemp = Split(strTemp, "~")
                            iTemp = CInt(vTemp(0))
                            
                            Select Case UBound(vTemp)
                                Case Is = 0
                                    If strLine = "" Then
                                        strLine = vBlockAtt(iTemp).TextString
                                    Else
                                        strLine = strLine & " " & vBlockAtt(iTemp).TextString
                                    End If
                                    
                                Case Is = 2
                                    str1 = vBlockAtt(iTemp).TextString
                                    str2 = vTemp(1)
                                    str3 = vTemp(2)
                                    
                                    strTemp = GetTextSegment((str1), (str2), (str3))
                                    If strLine = "" Then
                                        strLine = strTemp
                                    Else
                                        strLine = strLine & " " & strTemp
                                    End If
                            End Select
                        Else
                            If strLine = "" Then
                                strLine = vLine(j)
                            Else
                                strLine = strLine & " " & vLine(j)
                            End If
                        End If
                    Next j
                    strAttTemp(i) = strLine
                Else
                    strAttTemp(i) = strAttList(i)
                End If
            Next i
        End If                                        '<------------------------------------------------- Finish Getting Data
        
Place_Block:
            
        Set objPlace = ThisDrawing.ModelSpace.InsertBlock(dInsertPnt, cbToList.Value, dScale, dScale, dScale, 0#)
        objPlace.Layer = cbToLayer.Value
        vAttList = objPlace.GetAttributes
            
        For i = 0 To UBound(strAttList)
            vAttList(i).TextString = strAttTemp(i)
        Next i
        objPlace.Update
            
        If cbDelete.Value = True Then objEntity.Delete
    Next objEntity
    
            '<------------------------------------------------------------------------------
    Select Case cbFromType.Value
        Case "Blocks"
        Case Else
    End Select
    
            '<------------------------------------------------------------------------------
    
Exit_Sub:
    
    cbConvert.Enabled = False
    
    Me.show
End Sub

Private Sub cbFromList_Change()
    Dim filterType, filterValue As Variant
    Dim grpCode(0) As Integer
    Dim grpValue(0) As Variant
    Dim objSS2 As AcadSelectionSet
    
    On Error Resume Next
    
    If cbFromType.Value = "Block" Then
        Dim objBlock As AcadBlockReference
        Dim vAttList As Variant
    
        grpCode(0) = 2
        grpValue(0) = cbFromList.Value
        filterType = grpCode
        filterValue = grpValue
    
        Err = 0
        Set objSS2 = ThisDrawing.SelectionSets.Add("objSS2")
        If Not Err = 0 Then
            Set objSS2 = ThisDrawing.SelectionSets.Item("objSS2")
            objSS2.Clear
        End If
    
        objSS2.Select acSelectionSetAll, , , filterType, filterValue
        
        For Each objBlock In objSS2
            vAttList = objBlock.GetAttributes
            lbFrom.Clear
            For i = 0 To UBound(vAttList)
                lbFrom.AddItem
                lbFrom.List(i, 0) = i
                lbFrom.List(i, 1) = vAttList(i).TagString
            Next i
            GoTo Exit_Next
        Next objBlock
Exit_Next:
    Else
        Dim amap As AcadMap
        Dim ODRcs As ODRecords
        Dim ODRc As ODRecord
        Dim tbl As ODTable
        Dim tbls As ODTables
        Dim refColumn As ODFieldDef
        Dim objEntity As AcadEntity
        Dim boolVal As Boolean
        Dim iCount As Integer
        Dim strTest As String
    
        Set amap = ThisDrawing.Application.GetInterfaceObject("AutoCADMap.Application")
    
        Set tbls = amap.Projects(ThisDrawing).ODTables
        If tbls.count > 0 Then
            For Each tbl In tbls
                If tbl.Name = cbFromList.Value Then GoTo Exit_For
            Next
        End If
Exit_For:

        Set ODRcs = tbl.GetODRecords
        
        iCount = 0
        Err = 0
        
        While Err = 0
            Set refColumn = tbl.ODFieldDefs(iCount)
            strTest = refColumn.Name
            If Not Err = 0 Then GoTo Exit_objEntity
            
            lbFrom.AddItem
            lbFrom.List(iCount, 0) = iCount
            lbFrom.List(iCount, 1) = strTest
            iCount = iCount + 1
        Wend
        
Exit_objEntity:
    End If
    
    objSS2.Clear
    objSS2.Delete
End Sub

Private Sub cbFromType_Change()
    Select Case cbFromType.Value
        Case "Block"
            Dim objBlocks As AcadBlocks
            Dim strLine As String
            
            Set objBlocks = ThisDrawing.Blocks
            For i = 0 To objBlocks.count - 1
                strLine = objBlocks(i).Name
                If Not Left(strLine, 1) = "*" Then cbFromList.AddItem objBlocks(i).Name
            Next i
        Case "Point w/OD"
            Dim amap As AcadMap
            Dim tbl As ODTable
            Dim tbls As ODTables
    
            Set amap = ThisDrawing.Application.GetInterfaceObject("AutoCADMap.Application")
    
            Set tbls = amap.Projects(ThisDrawing).ODTables
            If tbls.count > 0 Then
                cbFromList.Clear
                For Each tbl In tbls
                    cbFromList.AddItem tbl.Name
                Next
            End If
    End Select
End Sub

Private Sub cbQuit_Click()
    Me.Hide
End Sub

Private Sub cbToList_Change()
    Dim filterType, filterValue As Variant
    Dim grpCode(0) As Integer
    Dim grpValue(0) As Variant
    Dim objSS2 As AcadSelectionSet
    
    On Error Resume Next
    
    Dim objBlock As AcadBlockReference
    Dim vAttList As Variant
    
    grpCode(0) = 2
    grpValue(0) = cbToList.Value
    filterType = grpCode
    filterValue = grpValue
    
    Err = 0
    Set objSS2 = ThisDrawing.SelectionSets.Add("objSS2")
    If Not Err = 0 Then
        Set objSS2 = ThisDrawing.SelectionSets.Item("objSS2")
        objSS2.Clear
    End If
    
    objSS2.Select acSelectionSetAll, , , filterType, filterValue
        
    Set objBlock = objSS2.Item(0)
    
    vAttList = objBlock.GetAttributes
    lbTo.Clear
    For i = 0 To UBound(vAttList)
        lbTo.AddItem
        lbTo.List(i, 0) = i
        lbTo.List(i, 1) = vAttList(i).TagString
        lbTo.List(i, 2) = ""
    Next i
    
End Sub

Private Sub cbToList_Exit(ByVal Cancel As MSForms.ReturnBoolean)
    cbFromType.SetFocus
End Sub

Private Sub cbTransferAll_Click()
    'If lbTo.ListIndex < 0 Then Exit Sub
    'If lbFrom.ListIndex < 0 Then Exit Sub
    If Not lbTo.ListCount = lbFrom.ListCount Then Exit Sub
    
    For i = 0 To lbTo.ListCount - 1
        lbTo.List(i, 2) = "{" & lbFrom.List(i, 0) & "}"
    Next i
End Sub

Private Sub cbTransferOne_Click()
    If lbTo.ListIndex < 0 Then Exit Sub
    If lbFrom.ListIndex < 0 Then Exit Sub
    
    lbTo.List(lbTo.ListIndex, 2) = "{" & lbFrom.List(lbFrom.ListIndex, 0) & "}"
End Sub

Private Sub cbUpdate_Click()
    lbTo.List(lbTo.ListIndex, 1) = lAttTag.Caption
    lbTo.List(lbTo.ListIndex, 2) = tbValue.Value
    cbUpdate.Enabled = False
    
    lAttTag.Caption = "Attribute Tag"
    tbValue.Value = ""
End Sub

Private Sub lbFrom_DblClick(ByVal Cancel As MSForms.ReturnBoolean)
    If cbUpdate.Enabled = True Then
        tbValue = tbValue & "{" & lbFrom.List(lbFrom.ListIndex, 0) & "}"
        tbValue.SetFocus
    End If
End Sub

Private Sub lbTo_DblClick(ByVal Cancel As MSForms.ReturnBoolean)
    lAttTag.Caption = lbTo.List(lbTo.ListIndex, 1)
    tbValue.Value = lbTo.List(lbTo.ListIndex, 2)
    cbUpdate.Enabled = True
    tbValue.SetFocus
End Sub

Private Sub lbTo_KeyDown(ByVal KeyCode As MSForms.ReturnInteger, ByVal Shift As Integer)
    Select Case KeyCode
        Case vbKeyDelete
            lbTo.List(lbTo.ListIndex, 2) = ""
    End Select
End Sub

Private Sub UserForm_Deactivate()
    objSS.Clear
    objSS.Delete
End Sub

Private Sub UserForm_Initialize()
    cbScale.AddItem ""
    cbScale.AddItem "0.5"
    cbScale.AddItem "0.75"
    cbScale.AddItem "1.0"
    cbScale.AddItem "2.0"
    cbScale.AddItem "10"
    cbScale.AddItem "12"
    cbScale.Value = "1.0"
    
    cbSelection.AddItem "All"
    cbSelection.AddItem "Window"
    cbSelection.AddItem "Polygon"
    cbSelection.Value = "Window"
    
    cbFromType.AddItem "Block"
    cbFromType.AddItem "Point w/OD"
    cbFromType.Value = "Block"
    
    lbFrom.Clear
    lbFrom.ColumnCount = 2
    lbFrom.ColumnWidths = "20;90"
    
    lbTo.Clear
    lbTo.ColumnCount = 3
    lbTo.ColumnWidths = "20;80;70"
    
    cbToList.SetFocus
    
    On Error Resume Next
    
    Dim objBlocks As AcadBlocks
    Dim strLine As String
            
    Set objBlocks = ThisDrawing.Blocks
    For i = 0 To objBlocks.count - 1
        strLine = objBlocks(i).Name
        If Not Left(strLine, 1) = "*" Then cbToList.AddItem objBlocks(i).Name
    Next i
    
    Dim objLayers As AcadLayers
    Dim objLayer As AcadLayer
    
    Set objLayers = ThisDrawing.Layers
    For Each objLayer In objLayers
        cbToLayer.AddItem objLayer.Name
    Next objLayer
    cbToLayer.Value = "0"
    
    Set objSS = ThisDrawing.SelectionSets.Add("objSS")
    If Not Err = 0 Then
        Set objSS = ThisDrawing.SelectionSets.Item("objSS")
        objSS.Clear
    End If
End Sub

Private Function GetTextSegment(strText As String, strSearch As String, strSegment As String)
    Dim vText As Variant
    Dim iSegment As Integer
    Dim strResult As String

    iSegment = CInt(strSegment)
    vText = Split(strText, strSearch)

    Select Case iSegment
        Case Is < 0
            iSegment = Abs(iSegment) - 1
            strResult = ""

            For i = 0 To UBound(vText)
                If Not i = iSegment Then
                    If strResult = "" Then
                        strResult = vText(i)
                    Else
                        strResult = strResult & strSearch & vText(i)
                    End If
                End If
            Next i
        Case Is > 0
            iSegment = iSegment - 1
            If Not iSegment > UBound(vText) Then
                strResult = vText(iSegment)
            End If
    End Select

    GetTextSegment = strResult
End Function

Attribute VB_Name = "ConvertCSV"
Attribute VB_Base = "0{23708899-DDB2-4417-8C00-C8D6EAB5B6EE}{D0431D64-0137-4230-AD1A-2EE08761CCFE}"
Attribute VB_GlobalNameSpace = False
Attribute VB_Creatable = False
Attribute VB_PredeclaredId = True
Attribute VB_Exposed = False
Attribute VB_TemplateDerived = False
Attribute VB_Customizable = False
Private Sub cbPlace_Click()
    If tbPasted.Value = "" Then Exit Sub
    If cbLat.ListIndex < 0 Then Exit Sub
    If cbLong.ListIndex < 0 Then Exit Sub
    
    Dim vLine, vItem, vTemp As Variant
    Dim vList As Variant
    Dim vCoords, vNE As Variant
    Dim strLine As String
    Dim strFind, strReplace As String
    Dim dCoords(2) As Double
    Dim iIndex, iLat, iLong As Integer
    
    tbPasted.Value = Replace(tbPasted.Value, """", "")
    strLine = Replace(tbPasted.Value, vbLf, "")
    vItem = Split(strLine, vbCr)
    
    For i = 1 To UBound(vItem)
        If vItem(i) = "" Then GoTo Exit_Loop
        
        vLine = Split(vItem(i), ",")
        
        iLat = cbLat.ListIndex
        iLong = cbLong.ListIndex
        
        vNE = LLtoTN83F(CDbl(vLine(iLat)), CDbl(vLine(iLong)))
        dCoords(0) = CDbl(vNE(1))
        dCoords(1) = CDbl(vNE(0))
        dCoords(2) = 0#
        
        Set objBlock = ThisDrawing.ModelSpace.InsertBlock(dCoords, cbToList.Value, 1#, 1#, 1#, 0#)
        If lbTo.ListCount > 0 Then
            vAttList = objBlock.GetAttributes
            
            For j = 0 To lbTo.ListCount - 1
                strLine = lbTo.List(j, 2)
                
                If InStr(strLine, "}") > 0 Then
                    vList = Split(strLine, "}")
                    
                    For k = 0 To UBound(vList)
                        vTemp = Split(vList(k), "{")
                        If UBound(vTemp) < 1 Then GoTo Next_K
                        
                        iIndex = CInt(vTemp(1))
                        strFind = "{" & iIndex & "}"
                        strLine = Replace(strLine, strFind, vLine(iIndex))
Next_K:
                    Next k
                End If
                If Not strLine = "" Then vAttList(j).TextString = strLine
            Next j
        End If
        
        objBlock.Layer = cbToLayer.Value
        objBlock.Update
    Next i
    
Exit_Loop:
    
    MsgBox "Done."
End Sub

Private Sub cbToList_Change()
    Dim filterType, filterValue As Variant
    Dim grpCode(0) As Integer
    Dim grpValue(0) As Variant
    Dim objSS2 As AcadSelectionSet
    
    On Error Resume Next
    
    Dim objBlock As AcadBlockReference
    Dim vAttList As Variant
    
    grpCode(0) = 2
    grpValue(0) = cbToList.Value
    filterType = grpCode
    filterValue = grpValue
    
    Err = 0
    Set objSS2 = ThisDrawing.SelectionSets.Add("objSS2")
    If Not Err = 0 Then
        Set objSS2 = ThisDrawing.SelectionSets.Item("objSS2")
        objSS2.Clear
    End If
    
    objSS2.Select acSelectionSetAll, , , filterType, filterValue
        
    For Each objBlock In objSS2
        vAttList = objBlock.GetAttributes
        lbTo.Clear
        For i = 0 To UBound(vAttList)
            lbTo.AddItem
            lbTo.List(i, 0) = i
            lbTo.List(i, 1) = vAttList(i).TagString
            lbTo.List(i, 2) = ""
        Next i
        GoTo Exit_Next
    Next objBlock
Exit_Next:
    
    objSS2.Clear
    objSS2.Delete
End Sub

Private Sub lbTo_DblClick(ByVal Cancel As MSForms.ReturnBoolean)
    If cbColumns.Value = "" Then Exit Sub
    If lbTo.ListCount < 1 Then Exit Sub
    
    Dim vLine As Variant
    
    vLine = Split(cbColumns.Value, " ")
    vLine(0) = "{" & vLine(0) & "}"
    
    If lbTo.List(lbTo.ListIndex, 2) = "" Then
        lbTo.List(lbTo.ListIndex, 2) = vLine(0)
    Else
        lbTo.List(lbTo.ListIndex, 2) = lbTo.List(lbTo.ListIndex, 2) & cbSeperator.Value & vLine(0)
    End If
    
    If lbTo.ListIndex < lbTo.ListCount - 1 Then
        lbTo.ListIndex = lbTo.ListIndex + 1
        lbTo.Selected(lbTo.ListIndex) = True
    End If
End Sub

Private Sub tbPasted_Change()
    If tbPasted.Value = "" Then Exit Sub
    
    Dim vLine, vItem, vTemp As Variant
    Dim strLine As String
    Dim iIndex As Integer
    
    tbPasted.Value = Replace(tbPasted.Value, """", "")
    strLine = Replace(tbPasted.Value, vbLf, "")
    vItem = Split(strLine, vbCr)
    vLine = Split(vItem(0), ",")
    
    For i = 0 To UBound(vLine)
        strLine = i & " - " & vLine(i)
        
        cbLat.AddItem strLine
        cbLong.AddItem strLine
        cbColumns.AddItem strLine
    Next i
End Sub

Private Sub UserForm_Initialize()
    lbTo.Clear
    lbTo.ColumnCount = 3
    lbTo.ColumnWidths = "20;80;70"
    
    cbSeperator.AddItem ","
    cbSeperator.AddItem "-"
    cbSeperator.AddItem " "
    cbSeperator.AddItem ";"
    cbSeperator.Value = ","
    
    On Error Resume Next
    
    Dim objBlocks As AcadBlocks
    Dim strLine As String
            
    Set objBlocks = ThisDrawing.Blocks
    For i = 0 To objBlocks.count - 1
        strLine = objBlocks(i).Name
        If Not Left(strLine, 1) = "*" Then cbToList.AddItem objBlocks(i).Name
    Next i
    
    Dim objLayers As AcadLayers
    Dim objLayer As AcadLayer
    
    Set objLayers = ThisDrawing.Layers
    For Each objLayer In objLayers
        cbToLayer.AddItem objLayer.Name
    Next objLayer
    cbToLayer.Value = "0"
End Sub

Private Function LLtoTN83F(dLat As Double, dLong As Double)
    Dim dDLat As Double
    Dim dEast, dDiffE, dEast0 As Double
    Dim dNorth, dDiffN, dNorth0 As Double
    Dim dU, dR, dCA, dK As Double
    Dim NE(2) As Double
    
    dDLat = dLat - 35.8340607459
    dU = dDLat * (110950.2019 + dDLat * (9.25072 + dDLat * (5.64572 + dDLat * 0.017374)))
    dR = 8842127.1422 - dU
    dCA = ((86 + dLong) * 0.585439726459) * 3.14159265359 / 180
    
    dDiffE = dR * Sin(dCA)
    dDiffN = dU + dDiffE * Tan(dCA / 2)
    
    dEast = (dDiffE + 600000) / 0.3048006096
    dNorth = (dDiffN + 166504.1691) / 0.3048006096
    
    dK = 0.999948401424 + (1.23188E-14 * dU * dU) + (4.54E-22 * dU * dU * dU)
    
    NE(0) = dNorth
    NE(1) = dEast
    NE(2) = dK
    
    LLtoTN83F = NE
End Function

Attribute VB_Name = "ConvertChangeBlocks"
Attribute VB_Base = "0{E1143731-BDE3-4E6E-B5B4-1DB3A6BC6D49}{BC225EC2-777A-42D8-9FFF-BAD972207F59}"
Attribute VB_GlobalNameSpace = False
Attribute VB_Creatable = False
Attribute VB_PredeclaredId = True
Attribute VB_Exposed = False
Attribute VB_TemplateDerived = False
Attribute VB_Customizable = False

Private Sub cbClear_Click()
    lbConditions.Clear
    cbValue.Clear
    cbValue.Value = ""
    lAttTag.Caption = "Attribute Tag"
    cbUpdate.Enabled = False
    lbTo.Enabled = True
    cbToList.Enabled = True
End Sub

Private Sub cbConvert_Click()
    Dim filterType, filterValue As Variant
    Dim grpCode(0) As Integer
    Dim grpValue(0) As Variant
    Dim objSS2 As AcadSelectionSet
    Dim objBlock As AcadBlockReference
    Dim vBlockAtt As Variant
    
    Dim objNewBlock As AcadBlockReference
    Dim vNewBlockAtt As Variant
    Dim dCoords(0 To 2) As Double
    Dim dScale As Double
    
    Dim iAttList As Integer
    Dim strValue, strBlock As String
    Dim strLayer As String
    
    On Error Resume Next
    
    grpCode(0) = 2
    grpValue(0) = cbToList.Value
    filterType = grpCode
    filterValue = grpValue
    
    Err = 0
    Set objSS2 = ThisDrawing.SelectionSets.Add("objSS2")
    If Not Err = 0 Then
        Set objSS2 = ThisDrawing.SelectionSets.Item("objSS2")
        objSS2.Clear
    End If
    
    objSS2.Select acSelectionSetAll, , , filterType, filterValue
    MsgBox cbToList.Value & " found:  " & objSS2.count
    
    For Each objBlock In objSS2
        vBlockAtt = objBlock.GetAttributes
        dScale = objBlock.XScaleFactor
        dCoords(0) = objBlock.InsertionPoint(0)
        dCoords(1) = objBlock.InsertionPoint(1)
        dCoords(2) = objBlock.InsertionPoint(2)
        
        For i = 0 To lbConditions.ListCount - 1
            iAttList = CInt(lbConditions.List(i, 0))
            strValue = lbConditions.List(i, 1)
            strBlock = lbConditions.List(i, 2)
            strLayer = lbConditions.List(i, 3)
            
            If Left(strValue, 1) = "{" Then
                strValue = Replace(strValue, "{", "")
                strValue = Replace(strValue, "}", "")
            End If
            
            If InStr(UCase(vBlockAtt(iAttList).TextString), UCase(strValue)) Then
            'If vBlockAtt(iAttList).TextString = strValue Then
                Set objNewBlock = ThisDrawing.ModelSpace.InsertBlock(dCoords, strBlock, dScale, dScale, dScale, 0#)
                vNewBlockAtt = objNewBlock.GetAttributes
                
                If UBound(vBlockAtt) < UBound(vNewBlockAtt) Then
                    For m = 0 To UBound(vBlockAtt)
                        vNewBlockAtt(m).TextString = vBlockAtt(m).TextString
                    Next m
                Else
                    For m = 0 To UBound(vNewBlockAtt)
                        vNewBlockAtt(m).TextString = vBlockAtt(m).TextString
                    Next m
                End If
                
                objNewBlock.Layer = strLayer
                objNewBlock.Update
                
                objBlock.Delete
                GoTo Exit_Next
            End If
        Next i
Exit_Next:
    Next objBlock
    MsgBox "Done"
End Sub

Private Sub cbQuit_Click()
    Me.Hide
End Sub

Private Sub cbToBlock_Change()
    Select Case cbToBlock.Value
        Case "RES"
            cbToLayer.Value = "Integrity Building-RES"
        Case "BUSINESS"
            cbToLayer.Value = "Integrity Building-BUS"
        Case "TRLR"
            cbToLayer.Value = "Integrity Building-TRL"
        Case "MDU"
            cbToLayer.Value = "Integrity Building-MDU"
        Case "SCHOOL"
            cbToLayer.Value = "Integrity Building-SCH"
        Case "CHURCH"
            cbToLayer.Value = "Integrity Building-CHU"
        Case "EXTENTION", "NONRES"
            cbToLayer.Value = "Integrity Building Misc"
    End Select
End Sub

Private Sub cbToList_Change()
    Dim filterType, filterValue As Variant
    Dim grpCode(0) As Integer
    Dim grpValue(0) As Variant
    Dim objSS2 As AcadSelectionSet
    
    On Error Resume Next
    
    Dim objBlock As AcadBlockReference
    Dim vAttList As Variant
    
    grpCode(0) = 2
    grpValue(0) = cbToList.Value
    filterType = grpCode
    filterValue = grpValue
    
    Err = 0
    Set objSS2 = ThisDrawing.SelectionSets.Add("objSS2")
    If Not Err = 0 Then
        Set objSS2 = ThisDrawing.SelectionSets.Item("objSS2")
        objSS2.Clear
    End If
    
    objSS2.Select acSelectionSetAll, , , filterType, filterValue
        
    For Each objBlock In objSS2
        vAttList = objBlock.GetAttributes
        lbTo.Clear
        For i = 0 To UBound(vAttList)
            lbTo.AddItem
            lbTo.List(i, 0) = i
            lbTo.List(i, 1) = vAttList(i).TagString
            'lbTo.List(i, 2) = ""
        Next i
        GoTo Exit_Next
    Next objBlock
Exit_Next:
End Sub

Private Sub cbUpdate_Click()
    lbConditions.AddItem
    lbConditions.List(lbConditions.ListCount - 1, 0) = lbTo.List(lbTo.ListIndex, 0)
    If tbInStr.Value = "" Then
        lbConditions.List(lbConditions.ListCount - 1, 1) = cbValue.Value
    Else
        lbConditions.List(lbConditions.ListCount - 1, 1) = "{" & tbInStr.Value & "}"
    End If
    'lbConditions.List(lbConditions.ListCount - 1, 1) = cbValue.Value
    lbConditions.List(lbConditions.ListCount - 1, 2) = cbToBlock.Value
    lbConditions.List(lbConditions.ListCount - 1, 3) = cbToLayer.Value
End Sub

Private Sub lbTo_DblClick(ByVal Cancel As MSForms.ReturnBoolean)
    lAttTag.Caption = lbTo.List(lbTo.ListIndex, 1)
    'cbValue.Value = lbTo.List(lbTo.ListIndex, 2)
    cbUpdate.Enabled = True
    lbTo.Enabled = False
    cbToList.Enabled = False
    cbValue.SetFocus
    
    Call GetValues
End Sub

Private Sub UserForm_Initialize()
    lbConditions.Clear
    lbConditions.ColumnCount = 4
    lbConditions.ColumnWidths = "20;80;100;100"
    
    lbTo.Clear
    lbTo.ColumnCount = 2
    lbTo.ColumnWidths = "20;80"
    
    Dim objBlocks As AcadBlocks
    Dim strLine As String
            
    Set objBlocks = ThisDrawing.Blocks
    For i = 0 To objBlocks.count - 1
        strLine = objBlocks(i).Name
        If Not Left(strLine, 1) = "*" Then
            cbToList.AddItem objBlocks(i).Name
            cbToBlock.AddItem objBlocks(i).Name
        End If
    Next i
    
    Dim objLayers As AcadLayers
    Dim objLayer As AcadLayer
    
    Set objLayers = ThisDrawing.Layers
    For Each objLayer In objLayers
        cbToLayer.AddItem objLayer.Name
    Next objLayer
    cbToLayer.Value = "0"
End Sub

Private Sub GetValues()
    Dim filterType, filterValue As Variant
    Dim grpCode(0) As Integer
    Dim grpValue(0) As Variant
    Dim objSS2 As AcadSelectionSet
    
    Dim iCount As Integer
    Dim strTest As String
    
    On Error Resume Next
    
    Dim objBlock As AcadBlockReference
    Dim vAttList As Variant
    
    grpCode(0) = 2
    grpValue(0) = cbToList.Value
    filterType = grpCode
    filterValue = grpValue
    
    Err = 0
    Set objSS2 = ThisDrawing.SelectionSets.Add("objSS2")
    If Not Err = 0 Then
        Set objSS2 = ThisDrawing.SelectionSets.Item("objSS2")
        objSS2.Clear
    End If
    
    objSS2.Select acSelectionSetAll, , , filterType, filterValue
    
    cbValue.Clear
        
    For Each objBlock In objSS2
        vAttList = objBlock.GetAttributes
        strTest = vAttList(lbTo.ListIndex).TextString
        iCount = 0
        
        For i = 0 To cbValue.ListCount - 1
            If strTest = cbValue.List(i) Then GoTo Exit_Next_I
        Next i
        
        cbValue.AddItem strTest
Exit_Next_I:
    Next objBlock
End Sub

Attribute VB_Name = "ConvertCustomers"
Attribute VB_Base = "0{ECB1F6FC-00EC-4C17-9CB5-BF869944FBD7}{2D3202CF-49E3-4626-AC7C-8BA9ED0C0535}"
Attribute VB_GlobalNameSpace = False
Attribute VB_Creatable = False
Attribute VB_PredeclaredId = True
Attribute VB_Exposed = False
Attribute VB_TemplateDerived = False
Attribute VB_Customizable = False
Private Sub cbAdd_Click()
    If tbText.Value = "" Then Exit Sub
    If cbType.Value = "" Then Exit Sub
    
    lbList.AddItem UCase(tbText.Value)
    lbList.List(lbList.ListCount - 1, 1) = cbType.Value
    
    tbText.Value = ""
    cbType.Value = ""
    
    tbText.SetFocus
End Sub

Private Sub cbConvert_Click()
    If lbList.ListCount < 1 Then Exit Sub
    
    Dim filterType, filterValue As Variant
    Dim grpCode(0) As Integer
    Dim grpValue(0) As Variant
    Dim objSS As AcadSelectionSet
    Dim objBlock As AcadBlockReference
    Dim vAttList As Variant
    Dim iCount As Integer
    
    On Error Resume Next
    
    iCount = 0
    
    grpCode(0) = 2
    grpValue(0) = "Customer"
    filterType = grpCode
    filterValue = grpValue
    
    Err = 0
    Set objSS = ThisDrawing.SelectionSets.Add("objSS")
    If Not Err = 0 Then
        Set objSS = ThisDrawing.SelectionSets.Item("objSS")
        objSS.Clear
    End If
    
    objSS.Select acSelectionSetAll, , , filterType, filterValue
    MsgBox "Found:  " & objSS.count
    
    For Each objBlock In objSS
        vAttList = objBlock.GetAttributes
        
        For i = 0 To lbList.ListCount - 1
            If InStr(UCase(vAttList(3).TextString), lbList.List(i, 0)) > 0 Then
                vAttList(0).TextString = lbList.List(i, 1)
                
                Select Case Left(lbList.List(i, 1), 1)
                    Case "R"
                        vAttList(5).TextString = ""
                    Case "E"
                        vAttList(5).TextString = "X"
                    Case Else
                        vAttList(5).TextString = Left(lbList.List(i, 1), 1)
                End Select
                
                objBlock.Update
                
                iCount = iCount + 1
                
                GoTo Next_objBlock
            End If
        Next i
Next_objBlock:
    Next objBlock
    
    MsgBox "Converted  " & iCount & "  customers"
    lbList.Clear
End Sub

Private Sub cbQuit_Click()
    Me.Hide
End Sub

Private Sub lbList_KeyDown(ByVal KeyCode As MSForms.ReturnInteger, ByVal Shift As Integer)
    If lbList.ListCount < 1 Then Exit Sub
    
    Select Case KeyCode
        Case vbKeyDelete
            lbList.RemoveItem lbList.ListIndex
    End Select
End Sub

Private Sub lbNotes_DblClick(ByVal Cancel As MSForms.ReturnBoolean)
    If lbNotes.ListIndex < 0 Then Exit Sub
    
    tbText.Value = lbNotes.List(lbNotes.ListIndex, 1)
End Sub

Private Sub lbNotes_KeyDown(ByVal KeyCode As MSForms.ReturnInteger, ByVal Shift As Integer)
    If lbNotes.ListIndex < 0 Then Exit Sub
    
    Select Case KeyCode
        Case vbKeyDelete
            lbNotes.RemoveItem lbNotes.ListIndex
            
            tbListCount.Value = lbNotes.ListCount
    End Select
End Sub

Private Sub UserForm_Initialize()
    lbNotes.ColumnCount = 2
    lbNotes.ColumnWidths = "36;100"
    
    lbList.ColumnCount = 2
    lbList.ColumnWidths = "72;66"
    
    cbType.AddItem "BUSINESS"
    cbType.AddItem "CHURCH"
    cbType.AddItem "MDU"
    cbType.AddItem "RESIDENCE"
    cbType.AddItem "SCHOOL"
    cbType.AddItem "TRAILER"
    cbType.AddItem "EXTENSION"
    
    'Dim vDwgLL, vDwgUR As Variant
    Dim filterType, filterValue As Variant
    Dim grpCode(0) As Integer
    Dim grpValue(0) As Variant
    Dim objSS As AcadSelectionSet
    Dim objBlock As AcadBlockReference
    Dim vAtt As Variant
    Dim strLine As String
    
    'vDwgLL = ThisDrawing.Utility.GetPoint(, "Get DWG LL Corner: ")
    'vDwgUR = ThisDrawing.Utility.GetCorner(vDwgLL, vbCr & "Get DWG UR Corner: ")
    
    grpCode(0) = 2
    grpValue(0) = "Customer"
    filterType = grpCode
    filterValue = grpValue
    
    Set objSS = ThisDrawing.SelectionSets.Add("objSS")
    objSS.Select acSelectionSetAll, , , filterType, filterValue
    tbBlocks.Value = objSS.count
    If objSS.count < 1 Then GoTo Exit_Sub
    
    For Each objBlock In objSS
        vAtt = objBlock.GetAttributes
        strLine = vAtt(3).TextString
        
        If lbNotes.ListCount > 0 Then
            For i = 0 To lbNotes.ListCount - 1
                If lbNotes.List(i, 1) = strLine Then GoTo Found_Note
            Next i
        End If
        
        Select Case vAtt(5).TextString
            Case ""
                lbNotes.AddItem "R"
            Case Else
                lbNotes.AddItem vAtt(5).TextString
        End Select
        
        lbNotes.List(lbNotes.ListCount - 1, 1) = strLine
        
Found_Note:
    Next objBlock
    
    tbListCount.Value = lbNotes.ListCount
    
Exit_Sub:
    objSS.Clear
    objSS.Delete
End Sub

Attribute VB_Name = "ConvertKML"
Attribute VB_Base = "0{BA93F117-63E8-4800-B4C5-57D0BA21BA71}{7F933836-ED3B-458F-9A0C-472A8A7CFED4}"
Attribute VB_GlobalNameSpace = False
Attribute VB_Creatable = False
Attribute VB_PredeclaredId = True
Attribute VB_Exposed = False
Attribute VB_TemplateDerived = False
Attribute VB_Customizable = False
Private Sub cbConvert_Change()
    If lbDesc.ListCount < 1 Then Exit Sub
    
    If cbConvert.Value Then
        lbDesc.AddItem "<TN83F>"
    Else
        lbDesc.RemoveItem lbDesc.ListCount - 1
    End If
End Sub

Private Sub cbConvertKML_Click()
    If tbFile.Value = "" Then Exit Sub
    
    Dim objBlock As AcadBlockReference
    Dim vAttList As Variant
    Dim strFile, strTemp, strPre As String
    Dim strValue As String
    Dim vFile, vTemp As Variant
    Dim lCount, lNum As Long
    Dim strAtt() As String
    Dim iCount As Integer
    Dim dLat, dLong As Double
    Dim vNE As Variant
    Dim dInsert(0 To 2) As Double
    Dim dScale As Double
    
    dScale = CDbl(cbScale.Value)
    For i = 0 To lbTo.ListCount - 1
        If Not lbTo.List(i, 2) = "" Then iCount = i
    Next i
    
    ReDim strAtt(iCount)
    
    For i = 0 To iCount
        strAtt(i) = lbTo.List(i, 2)
    Next i
    
    strFile = tbFile.Value
    
    On Error Resume Next
    
    Open strFile For Input As #1
    If Not Err = 0 Then
        MsgBox "Error opening file."
        Exit Sub
    End If
    
    vFile = Split(Input$(LOF(1), 1), vbLf)
    Close #1
    
    If Not Err = 0 Then
        MsgBox Err.Description
        Err = 0
    End If
    
    For lNum = 0 To UBound(vFile)
        strTemp = Replace(vFile(lNum), vbTab, "")
        If LCase(Left(strTemp, 5)) = "</pla" Then GoTo Next_L
        
        If Not LCase(Left(strTemp, 4)) = "<pla" Then
            GoTo Next_lNum
        Else
            lNum = lNum + 1
            
            strTemp = Replace(vFile(lNum), vbTab, "")
            'MsgBox strTemp
            While Not LCase(Left(strTemp, 5)) = "</pla"
                If LCase(Left(strTemp, 5)) = "<name" Then
                    'MsgBox strTemp & vbCr & InStr(lbTo.List(0, 2), "<name>")
                    If InStr(lbTo.List(0, 2), "<name>") > 0 Then
                        strTemp = Replace(strTemp, "<name>", "")
                        strTemp = Replace(strTemp, "</name>", "")
                        
                        For j = 0 To iCount
                            If InStr(strAtt(j), "<name>") > 0 Then
                                strPre = "{<name>}"

                                If Left(strTemp, 1) = "&" Then
                                    strAtt(j) = Replace(strAtt(j), strPre, "NA")
                                Else
                                    strAtt(j) = Replace(strAtt(j), strPre, strTemp)
                                End If
                            End If
                        Next j
                    End If
                End If
                
                If LCase(Left(strTemp, 3)) = "<th" Then
                    strValue = Replace(strTemp, "<th>", "")
                    strValue = Replace(strValue, "</th>", "")
                    
                    lNum = lNum + 1
                    strTemp = Replace(vFile(lNum), vbTab, "")
                    If Left(strTemp, 3) = "<td" Then
                        strTemp = Replace(strTemp, "<td>", "")
                        strTemp = Replace(strTemp, "</td>", "")
                        
                        For j = 0 To iCount
                            If InStr(strAtt(j), strValue) > 0 Then
                                strPre = "{" & strValue & "}"

                                If Left(strTemp, 1) = "&" Then
                                    strAtt(j) = Replace(strAtt(j), strPre, "NA")
                                Else
                                    strAtt(j) = Replace(strAtt(j), strPre, strTemp)
                                End If
                            End If
                        Next j
                    End If
                End If
                
'                If LCase(Left(strTemp, 3)) = "<tr" Then
'                    lNum = lNum + 2
'                    strTemp = Replace(vFile(lNum), vbTab, "")
'                    If Left(strTemp, 3) = "<td" Then
'                        strTemp = Replace(strTemp, "<td>", "")
'                        strTemp = Replace(strTemp, "</td>", "")
'
'                        For j = 0 To iCount
'                            If InStr(strAtt(j), strTemp) > 0 Then
'                                strPre = "{" & strTemp & "}"
'
'                                'lNum = lNum + 2
'                                'strTemp = Replace(vFile(lNum), vbTab, "")
'                                'strTemp = Replace(strTemp, "<td>", "")
'                                'strTemp = Replace(strTemp, "</td>", "")
'                                If Left(strTemp, 1) = "&" Then
'                                    strAtt(j) = Replace(strAtt(j), strPre, "NA")
'                                Else
'                                    strAtt(j) = Replace(strAtt(j), strPre, strTemp)
'                                End If
'                            End If
'                        Next j
'                    End If
'                End If
                
                If LCase(Left(strTemp, 5)) = "<coor" Then
                    
                    'MsgBox "Here"
                    strTemp = Replace(strTemp, "<coordinates>", "")
                    strTemp = Replace(strTemp, "</coordinates>", "")
                    vTemp = Split(strTemp, ",")
                        
                    For j = 0 To iCount
                        If lbTo.List(j, 2) = "{<LL>}" Then
                            strAtt(j) = vTemp(1) & "," & vTemp(0)
                        End If
                    Next j
                        
                    If cbConvert.Value Then
                        vNE = LLtoTN83F(CDbl(vTemp(1)), CDbl(vTemp(0)))
                        'MsgBox vTemp(1) & " , " & vTemp(0) & vbCr & vNE(0) & vbCr & vNE(1)
                        
                        For j = 0 To iCount
                            If lbTo.List(j, 2) = "{<TN83F>}" Then
                                strAtt(j) = vNE(0) & "," & vNE(1)
                            End If
                        Next j
                            
                        dInsert(0) = CDbl(vNE(1))
                        dInsert(1) = CDbl(vNE(0))
                        dInsert(2) = 0#
                    Else
                        dInsert(0) = CDbl(vTemp(0))
                        dInsert(1) = CDbl(vTemp(1))
                        dInsert(2) = 0#
                    End If
                    'MsgBox dInsert(0) & vbCr & dInsert(1) & vbCr & dInsert(2)
                End If
                
                lNum = lNum + 1
                strTemp = Replace(vFile(lNum), vbTab, "")
            Wend
        End If
Next_L:
        'MsgBox dInsert(0) & vbCr & dInsert(1) & vbCr & dInsert(2)
        'MsgBox cbToList.Value & vbCr & strAtt(0) & vbCr & UBound(strAtt)
        'Exit Sub
        
        Set objBlock = ThisDrawing.ModelSpace.InsertBlock(dInsert, cbToList.Value, dScale, dScale, dScale, 0#)
        objBlock.Layer = cbToLayer.Value
        vAttList = objBlock.GetAttributes
        
        For k = 0 To iCount
            vAttList(k).TextString = strAtt(k)
        Next k
        objBlock.Update
    
        For i = 0 To iCount
            strAtt(i) = lbTo.List(i, 2)
        Next i
Next_lNum:
    Next lNum
Exit_For:

    MsgBox "Done"
    
End Sub

Private Sub cbFile_Click()
    Dim objSS As AcadSelectionSet
    Dim filterType, filterValue As Variant
    Dim grpCode(0) As Integer
    Dim grpValue(0) As Variant
    
    Dim objBlock As AcadBlockReference
    Dim vAtt As Variant
    
    Dim strPath, strFile As String
    Dim strLine As String
    
  On Error Resume Next
    
    strPath = ThisDrawing.Path & "\"
    strFile = strPath & "Pole Data.txt"
    
    Open strFile For Output As #1
    If Not Err = 0 Then
        MsgBox "Error opening file."
        Exit Sub
    End If

    grpCode(0) = 2
    grpValue(0) = "iPole"
    filterType = grpCode
    filterValue = grpValue
    
    Set objSS = ThisDrawing.SelectionSets.Add("objSS")
    If Not Err = 0 Then
        Set objSS = ThisDrawing.SelectionSets.Item("objSS")
        Err = 0
    End If
    
    objSS.Select acSelectionSetAll, , , filterType, filterValue
    If Not Err = 0 Then
        MsgBox "Error: " & Err.Number & vbCr & Err.Description
        Exit Sub
    End If
    
    For Each objBlock In objSS
        vAtt = objBlock.GetAttributes
        
        If vAtt(0).TextString = "" Then GoTo Next_objBlock
        
        strLine = vAtt(0).TextString & vbTab & vAtt(1).TextString & vbTab & vAtt(5).TextString & vbTab & vAtt(7).TextString
        
        Print #1, strLine
        
Next_objBlock:
    Next objBlock
    
    Close #1
End Sub

Private Sub cbQuit_Click()
    Me.Hide
End Sub

Private Sub cbToList_Change()
    Dim filterType, filterValue As Variant
    Dim grpCode(0) As Integer
    Dim grpValue(0) As Variant
    Dim objSS2 As AcadSelectionSet
    
    On Error Resume Next
    
    Dim objBlock As AcadBlockReference
    Dim vAttList As Variant
    
    grpCode(0) = 2
    grpValue(0) = cbToList.Value
    filterType = grpCode
    filterValue = grpValue
    
    Err = 0
    Set objSS2 = ThisDrawing.SelectionSets.Add("objSS2")
    If Not Err = 0 Then
        Set objSS2 = ThisDrawing.SelectionSets.Item("objSS2")
        objSS2.Clear
    End If
    
    objSS2.Select acSelectionSetAll, , , filterType, filterValue
        
    For Each objBlock In objSS2
        vAttList = objBlock.GetAttributes
        lbTo.Clear
        For i = 0 To UBound(vAttList)
            lbTo.AddItem
            lbTo.List(i, 0) = i
            lbTo.List(i, 1) = vAttList(i).TagString
            lbTo.List(i, 2) = ""
        Next i
        GoTo Exit_Next
    Next objBlock
Exit_Next:
End Sub

Private Sub cbUpdate_Click()
    lbTo.List(lbTo.ListIndex, 1) = lAttTag.Caption
    lbTo.List(lbTo.ListIndex, 2) = tbValue.Value
    cbUpdate.Enabled = False
    
    lAttTag.Caption = "Attribute Tag"
    tbValue.Value = ""
End Sub

Private Sub lbDesc_DblClick(ByVal Cancel As MSForms.ReturnBoolean)
    If cbUpdate.Enabled = True Then
        tbValue = tbValue & "{" & lbDesc.List(lbDesc.ListIndex, 0) & "}"
        tbValue.SetFocus
    End If
End Sub

Private Sub lbFiles_DblClick(ByVal Cancel As MSForms.ReturnBoolean)
    Dim strFile, strTemp As String
    Dim vFile, vTemp As Variant
    Dim lCount, l As Long
    
    strFile = ThisDrawing.Path & "\" & lbFiles.List(lbFiles.ListIndex)
    tbFile.Value = strFile
    
    On Error Resume Next
    
    Open strFile For Input As #1
    If Not Err = 0 Then
        MsgBox "Error opening file."
        Exit Sub
    End If
    
    lbDesc.Clear
    
    vFile = Split(Input$(LOF(1), 1), vbLf)
    Close #1
    
    For l = 0 To UBound(vFile)
        strTemp = Replace(vFile(l), vbTab, "")
        If LCase(Left(strTemp, 5)) = "</pla" Then GoTo Exit_For
        
        If Left(strTemp, 3) = "<th" Then
            'l = l + 2
            'strTemp = Replace(vFile(l), vbTab, "")
            'If Left(strTemp, 3) = "<td" Then
                strTemp = Replace(strTemp, "<th>", "")
                strTemp = Replace(strTemp, "</th>", "")
                
                If Not strTemp = "" Then lbDesc.AddItem strTemp
            'End If
        End If
        
        'If Left(strTemp, 3) = "<tr" Then
            'l = l + 2
            'strTemp = Replace(vFile(l), vbTab, "")
            'If Left(strTemp, 3) = "<td" Then
                'strTemp = Replace(strTemp, "<td>", "")
                'strTemp = Replace(strTemp, "</td>", "")
                
                'If Not strTemp = "" Then lbDesc.AddItem strTemp
            'End If
        'End If
    Next l
Exit_For:
    
    lbDesc.AddItem "<name>"
    lbDesc.AddItem "<LL>"
    lbDesc.AddItem "<TN83F>"
    
    'Close #1
End Sub

Private Sub lbTo_DblClick(ByVal Cancel As MSForms.ReturnBoolean)
    lAttTag.Caption = lbTo.List(lbTo.ListIndex, 1)
    tbValue.Value = lbTo.List(lbTo.ListIndex, 2)
    cbUpdate.Enabled = True
    tbValue.SetFocus
End Sub

Private Sub UserForm_Initialize()
    cbScale.AddItem ""
    cbScale.AddItem "0.5"
    cbScale.AddItem "0.75"
    cbScale.AddItem "1.0"
    cbScale.AddItem "2.0"
    cbScale.AddItem "10"
    cbScale.AddItem "12"
    cbScale.Value = "1.0"
    
    lbTo.Clear
    lbTo.ColumnCount = 3
    lbTo.ColumnWidths = "20;80;70"
    
    
    Dim objFSO As Object
    Dim objFolder As Object
    Dim objFile As Object
    Dim i As Integer
    Dim vName As Variant
    
    Set objFSO = CreateObject("Scripting.FileSystemObject")
    Set objFolder = objFSO.getfolder(ThisDrawing.Path)
    
    For Each objFile In objFolder.Files
        vName = Split(objFile.Name, ".")
        If LCase(vName(UBound(vName))) = "kml" Then lbFiles.AddItem objFile.Name
    Next objFile
    
    
    Dim objBlocks As AcadBlocks
    Dim strLine As String
            
    Set objBlocks = ThisDrawing.Blocks
    For i = 0 To objBlocks.count - 1
        strLine = objBlocks(i).Name
        If Not Left(strLine, 1) = "*" Then cbToList.AddItem objBlocks(i).Name
    Next i
    
    Dim objLayers As AcadLayers
    Dim objLayer As AcadLayer
    
    Set objLayers = ThisDrawing.Layers
    For Each objLayer In objLayers
        cbToLayer.AddItem objLayer.Name
    Next objLayer
    cbToLayer.Value = "0"
    
End Sub

Private Function TN83FtoLL(dNorth As Double, dEast As Double)
    Dim dLat, dLong, dDLat As Double
    Dim dDiffE, dEast0 As Double
    Dim dDiffN, dNorth0 As Double
    Dim dR, dCAR, dCA, dU, dK As Double
    Dim LL(2) As Double
    
    dEast = dEast * 0.3048006096
    dNorth = dNorth * 0.3048006096
    
    dDiffE = dEast - 600000
    dDiffN = dNorth - 166504.1691
    
    dR = 8842127.1422 - dDiffN
    dCAR = Atn(dDiffE / dR)
    dCA = dCAR * 180 / 3.14159265359
    dLong = -86 + dCA / 0.585439726459
    
    dU = dDiffN - dDiffE * Tan(dCAR / 2)
    dDLat = dU * (0.00000901305249 + dU * (-6.77268E-15 + dU * (-3.72351E-20 + dU * -9.2828E-28)))
    dLat = 35.8340607459 + dDLat
    
    dK = 0.999948401424 + (1.23188E-14 * dU * dU) + (4.54E-22 * dU * dU * dU)
    
    LL(0) = dLat
    LL(1) = dLong
    LL(2) = dK
    
    TN83FtoLL = LL
End Function

Private Function LLtoTN83F(dLat As Double, dLong As Double)
    Dim dDLat As Double
    Dim dEast, dDiffE, dEast0 As Double
    Dim dNorth, dDiffN, dNorth0 As Double
    Dim dU, dR, dCA, dK As Double
    Dim NE(2) As Double
    
    dDLat = dLat - 35.8340607459
    dU = dDLat * (110950.2019 + dDLat * (9.25072 + dDLat * (5.64572 + dDLat * 0.017374)))
    dR = 8842127.1422 - dU
    dCA = ((86 + dLong) * 0.585439726459) * 3.14159265359 / 180
    
    dDiffE = dR * Sin(dCA)
    dDiffN = dU + dDiffE * Tan(dCA / 2)
    
    dEast = (dDiffE + 600000) / 0.3048006096
    dNorth = (dDiffN + 166504.1691) / 0.3048006096
    
    'dEast = (dDiffE + 600000) / 0.3048
    'dNorth = (dDiffN + 166504.1691) / 0.3048
    
    dK = 0.999948401424 + (1.23188E-14 * dU * dU) + (4.54E-22 * dU * dU * dU)
    
    NE(0) = dNorth
    NE(1) = dEast
    NE(2) = dK
    
    LLtoTN83F = NE
End Function

Attribute VB_Name = "ConvertToSPole"
Attribute VB_Base = "0{4AE348C7-1392-4B63-8E9B-3DA8A53F0680}{07571976-82E4-45DD-BD9D-D071692DE94F}"
Attribute VB_GlobalNameSpace = False
Attribute VB_Creatable = False
Attribute VB_PredeclaredId = True
Attribute VB_Exposed = False
Attribute VB_TemplateDerived = False
Attribute VB_Customizable = False
Dim objPole As AcadBlockReference

Private Sub cbGetInfo_Click()
    Dim objSS As AcadSelectionSet
    Dim objEntity As AcadEntity
    Dim objBlock As AcadBlockReference
    Dim vAttList As Variant
    Dim strTemp As String
    Dim iCable, iSplice As Integer
    
    On Error Resume Next
    
    Err = 0
    Set objSS = ThisDrawing.SelectionSets.Add("objSS")
    If Not Err = 0 Then
        Set objSS = ThisDrawing.SelectionSets.Item("objSS")
        objSS.Clear
        Err = 0
    End If
    
    iCable = 1
    iSplice = 1
    
    Me.Hide
    
    objSS.SelectOnScreen
    For Each objEntity In objSS
        If Not TypeOf objEntity Is AcadBlockReference Then GoTo Next_objEntity
        
        Set objBlock = objEntity
        
        Select Case objBlock.Name
            Case "iPole"
                vAttList = objBlock.GetAttributes
    
                tbIPoleNum.Value = vAttList(0).TextString
                tbiStatus.Value = vAttList(1).TextString
                    cbStatus.Value = True
                tbiOwner.Value = vAttList(2).TextString
                    If Not vAttList(2).TextString = "" Then cbOwner.Value = True
                tbiOwnerNum.Value = vAttList(3).TextString
                    If Not vAttList(3).TextString = "" Then cbOwnerNum.Value = True
                tbiOtherNum.Value = vAttList(4).TextString
                    If Not vAttList(4).TextString = "" Then cbOtherNum.Value = True
                tbiHC.Value = vAttList(5).TextString
                    If Not vAttList(5).TextString = "" Then cbHC.Value = True
                tbiYear.Value = vAttList(6).TextString
                tbiLL.Value = vAttList(7).TextString
                tbiGRD.Value = vAttList(8).TextString
                    If Not vAttList(8).TextString = "" Then cbGRD.Value = True
            Case "pole_attach"
                vAttList = objBlock.GetAttributes
            
                lbAttach.AddItem vAttList(2).TextString, 0
            
                strTemp = Replace(vAttList(3).TextString, "'", "-")
                strTemp = Replace(strTemp, """", "")
            
                If vAttList(4).TextString = "" Then
                    lbAttach.List(0, 1) = strTemp
                    lbAttach.List(0, 2) = ""
                Else
                    Select Case Left(vAttList(4).TextString, 1)
                        Case "N", "F"
                            lbAttach.List(0, 1) = ""
                            lbAttach.List(0, 2) = strTemp
                        Case "A"
                            lbAttach.List(0, 1) = "X"
                            lbAttach.List(0, 2) = strTemp
                        Case "R", "L"
                            lbAttach.List(0, 2) = strTemp
                        
                            vLine = Split(strTemp, "-")
                            iFeet = CInt(vLine(0))
                            If UBound(vLine) < 1 Then
                                iInch = 0
                            Else
                                iInch = CInt(vLine(1))
                            End If
                            iTotal = iFeet * 12 + iInch
                        
                            vLine = Split(vAttList(4).TextString, " ")
                            strLine = Replace(vLine(1), """", "")
                        
                            If Left(vAttList(4).TextString, 1) = "R" Then
                                iRL = 0 - CInt(strLine)
                            Else
                                iRL = CInt(strLine)
                            End If
                        
                            iTotal = iTotal + iRL
                            iFeet = Int(iTotal / 12)
                            iInch = iTotal - (iFeet * 12)
                        
                            lbAttach.List(0, 1) = iFeet & "-" & iInch
                        Case "T"
                            lbAttach.List(0, 1) = strTemp
                            lbAttach.List(0, 2) = strTemp
                        Case Else
                            lbAttach.List(0, 1) = strTemp
                            lbAttach.List(0, 2) = ""
                    End Select
            
                    lbAttach.List(0, 3) = vAttList(4).TextString
                End If
            Case "pole_unit"
                vAttList = objBlock.GetAttributes
                
                lbUnits.AddItem vAttList(3).TextString, 0
            Case "terminal"
                vAttList = objBlock.GetAttributes
                
                strTemp = Replace(vAttList(0).TextString, "\P", " + ")
                If tbSplices.Value = "" Then
                    tbSplices.Value = "[A" & iSplice & "] " & strTemp
                Else
                    tbSplices.Value = tbSplices.Value & vbCr & "[A" & iSplice & "] " & strTemp
                End If
                iSplice = iSplice + 1
            Case "CableCounts"
                vAttList = objBlock.GetAttributes
                
                strTemp = vAttList(1).TextString & " / " & Replace(vAttList(0).TextString, "\P", " + ")
                If tbCable.Value = "" Then
                    tbCable.Value = "  A" & iCable & ": " & strTemp
                Else
                    tbCable.Value = tbCable.Value & vbCr & "  A" & iCable & ": " & strTemp
                End If
                iCable = iCable + 1
            Case Else
        End Select
        
Next_objEntity:
    Next objEntity
    
    objSS.Clear
    objSS.Delete
    
    Call SortAttachments
    
    cbUpdatesPole.SetFocus
    
    Me.show
End Sub

Private Sub cbGetsPole_Click()
    Dim objEntity As AcadEntity
    'Dim objBlock As AcadBlockReference
    Dim vAttList, vReturnPnt, vLine As Variant
    Dim strLine As String
    
    Dim vCoords As Variant
    Dim viewCoordsB(0 To 2) As Double
    Dim viewCoordsE(0 To 2) As Double
    
    On Error Resume Next
    
    Me.Hide
    
    If Not objPole Is Nothing Then
        vCoords = objPole.InsertionPoint
    
        viewCoordsB(0) = vCoords(0) - 300
        viewCoordsB(1) = vCoords(1) - 300
        viewCoordsB(2) = 0#
        viewCoordsE(0) = vCoords(0) + 300
        viewCoordsE(1) = vCoords(1) + 300
        viewCoordsE(2) = 0#
        
        ThisDrawing.Application.ZoomWindow viewCoordsB, viewCoordsE
    End If
    
    Err = 0
    ThisDrawing.Utility.GetEntity objEntity, vReturnPnt, vbCr & "Select sPole:"
    If Not Err = 0 Then GoTo Exit_Sub
    If Not TypeOf objEntity Is AcadBlockReference Then GoTo Exit_Sub
    
    Set objPole = objEntity
    If Not objPole.Name = "sPole" Then GoTo Exit_Sub
    
    Call ClearForm
    
    vAttList = objPole.GetAttributes
    
    tbSPoleNum.Value = vAttList(0).TextString
    tbsStatus.Value = vAttList(1).TextString
    tbsOwner.Value = vAttList(2).TextString
    tbsOwnerNum.Value = vAttList(3).TextString
    tbsOtherNum.Value = vAttList(4).TextString
    tbsHC.Value = vAttList(5).TextString
    tbsYear.Value = vAttList(6).TextString
    tbsLL.Value = vAttList(7).TextString
    tbsGRD.Value = vAttList(8).TextString
    
    If Not vAttList(25).Value = "" Then tbCable.Value = vAttList(25).TextString
    
    If Not vAttList(26).Value = "" Then tbSplices.Value = vAttList(26).TextString
    
    If Not vAttList(27).Value = "" Then
        vLine = Split(vAttList(27).TextString, ";;")
        For i = 0 To UBound(vLine)
            lbUnits.AddItem vLine(i)
        Next i
    End If
    
Exit_Sub:
    cbGetInfo.SetFocus
    
    Me.show
End Sub

Private Sub cbQuit_Click()
    Me.Hide
End Sub

Private Sub cbUpdateAtt_Click()
    If lbAttach.ListCount < 1 Then Exit Sub
    
    For i = 0 To lbAttach.ListCount - 1
        If Not lbAttach.List(i, 2) = "" Then
            If InStr(lbAttach.List(i, 0), "NEW") > 0 Then lbAttach.List(i, 0) = "UTC"
            If lbAttach.List(i, 3) = "FUTURE" Then lbAttach.List(i, 0) = lbAttach.List(i, 0) & " FUTURE"
            
            lbAttach.List(i, 1) = lbAttach.List(i, 2)
            lbAttach.List(i, 2) = ""
            lbAttach.List(i, 3) = ""
        End If
    Next i
End Sub

Private Sub cbUpdatesPole_Click()
    Dim strLine, strUnits As String
    Dim vAttList, vLine As Variant
    Dim iAtt As Integer
    
    strLine = ""
    strUnits = ""
    
    Call ClearAttributes
    
    vAttList = objPole.GetAttributes
    
    If cbPoleNum.Value = True Then vAttList(0).TextString = UCase(tbIPoleNum.Value)
    If cbStatus.Value = True Then vAttList(1).TextString = UCase(tbiStatus.Value)
    If cbOwner.Value = True Then vAttList(2).TextString = UCase(tbiOwner.Value)
    If cbOwnerNum.Value = True Then vAttList(3).TextString = UCase(tbiOwnerNum.Value)
    If cbOtherNum.Value = True Then vAttList(4).TextString = UCase(tbiOtherNum.Value)
    If cbHC.Value = True Then vAttList(5).TextString = UCase(tbiHC.Value)
    If cbYear.Value = True Then vAttList(6).TextString = UCase(tbiYear.Value)
    If cbLL.Value = True Then vAttList(7).TextString = UCase(tbiLL.Value)
    If cbGRD.Value = True Then vAttList(8).TextString = UCase(tbiGRD.Value)
    
    If lbAttach.ListCount < 1 Then GoTo Exit_Sub
    
    iAtt = 16
    
    For i = 0 To lbAttach.ListCount - 1
        strLine = lbAttach.List(i, 1)
        If Not lbAttach.List(i, 2) = "" Then
            strLine = "(" & strLine & ")" & lbAttach.List(i, 2)
        End If
        
        If lbAttach.List(i, 0) = "NEUTRAL" Then
            If vAttList(9).TextString = "" Then
                vAttList(9).TextString = strLine
            Else
                vAttList(9).TextString = vAttList(9).TextString & " " & strLine
            End If
            GoTo Next_I
        End If
        
        If lbAttach.List(i, 0) = "TRANSFORMER" Then
            If vAttList(10).TextString = "" Then
                vAttList(10).TextString = strLine
            Else
                vAttList(10).TextString = vAttList(10).TextString & " " & strLine
            End If
            GoTo Next_I
        End If
        
        If lbAttach.List(i, 0) = "LOW POWER" Then
            If vAttList(11).TextString = "" Then
                vAttList(11).TextString = strLine
            Else
                vAttList(11).TextString = vAttList(11).TextString & " " & strLine
            End If
            GoTo Next_I
        End If
        
        If lbAttach.List(i, 0) = "ANTENNA" Then
            If vAttList(12).TextString = "" Then
                vAttList(12).TextString = strLine
            Else
                vAttList(12).TextString = vAttList(12).TextString & " " & strLine
            End If
            GoTo Next_I
        End If
        
        If InStr(lbAttach.List(i, 0), "ST LT C") > 0 Then
            If vAttList(13).TextString = "" Then
                vAttList(13).TextString = strLine
            Else
                vAttList(13).TextString = vAttList(13).TextString & " " & strLine
            End If
            GoTo Next_I
        End If
        
        If lbAttach.List(i, 0) = "ST LT" Then
            If vAttList(14).TextString = "" Then
                vAttList(14).TextString = strLine
            Else
                vAttList(14).TextString = vAttList(14).TextString & " " & strLine
            End If
            GoTo Next_I
        End If
        
        If InStr(strLine, "()") > 0 Then
            strLine = Replace(strLine, "()", "")
            
            If vAttList(15).TextString = "" Then
                vAttList(15).TextString = strLine
            Else
                vAttList(15).TextString = vAttList(15).TextString & " " & strLine
            End If
            GoTo Next_I
        End If
        
        If iAtt = 16 Then
            vAttList(16).TextString = lbAttach.List(i, 0) & "=" & strLine
            iAtt = iAtt + 1
            GoTo Next_I
        End If
        
        For j = 16 To iAtt
            If vAttList(j).TextString = "" Then GoTo New_COMM
            
            vLine = Split(vAttList(j).TextString, "=")
            If vLine(0) = lbAttach.List(i, 0) Then
                vAttList(j).TextString = vAttList(j).TextString & " " & strLine
                iAtt = iAtt + 1
                GoTo Next_I
            End If
        Next j
        
New_COMM:
        vAttList(j).TextString = lbAttach.List(i, 0) & "=" & strLine
        iAtt = iAtt + 1
        
Next_I:
    Next i
    
    If Not tbCable.Value = "" Then
        strUnits = Replace(tbCable.Value, vbLf, "")
        
        vAttList(25).TextString = strUnits
    End If
    
    If Not tbSplices.Value = "" Then
        strUnits = Replace(tbSplices.Value, vbLf, "")
        
        vAttList(26).TextString = strUnits
    End If
    
    If lbUnits.ListCount > 0 Then
        strUnits = lbUnits.List(0)
        If lbUnits.ListCount > 1 Then
            For i = 1 To lbUnits.ListCount - 1
                strUnits = strUnits & ";;" & lbUnits.List(i)
            Next i
        End If
        
        vAttList(27).TextString = strUnits
    End If
    
Exit_Sub:
    lbAttach.Clear
    lbUnits.Clear
    
    cbGetSPole.SetFocus
    
    objPole.Update
End Sub

Private Sub Label10_Click()
    cbUpdateAtt.Enabled = True
End Sub

Private Sub lbUnits_KeyDown(ByVal KeyCode As MSForms.ReturnInteger, ByVal Shift As Integer)
    Select Case KeyCode
        Case vbKeyDelete
            lbUnits.RemoveItem lbUnits.ListIndex
    End Select
End Sub

Private Sub UserForm_Initialize()
    lbAttach.ColumnCount = 4
    lbAttach.ColumnWidths = "84;36;36;84"
End Sub

Private Sub SortAttachments()
    Dim strArrayList(), strArraySorted(), strData() As String
    Dim strListItem() As String     '<---------------------------------------------Sort
    'Dim attArray, attItem As Variant
    'Dim str1, str2 As String
    'Dim i, iDWGNum, test1, place1, temp1 As Integer
    Dim vLine As Variant
    Dim strTemp As String
    Dim iFeet, iInch As Integer
    'Dim tempFt, tempIn As Integer
    'Dim iNewFt, iNewIn As Integer
    Dim i As Integer
    
    'test1 = 0
    
    ReDim strData(0 To lbAttach.ListCount - 1)
    ReDim strListItem(0 To lbAttach.ListCount - 1)
    ReDim strArraySorted(0 To lbAttach.ListCount - 1)
    
    For i = 0 To UBound(strListItem)
        strListItem(i) = i
    Next i
    
    For i = 0 To UBound(strData)
        If lbAttach.List(i, 2) = "" Then
            vLine = Split(lbAttach.List(i, 1), "-")
        Else
            vLine = Split(lbAttach.List(i, 2), "-")
        End If
        
        iFeet = CInt(vLine(0))
        iInch = CInt(vLine(1)) + iFeet * 12
        
        strData(i) = iInch
    Next i
    
    'test1 = UBound(strData) - 1

    For i = UBound(strData) To (LBound(strData) + 1) Step -1
        For j = LBound(strData) To (i - 1)
            If CInt(strData(j)) < CInt(strData(j + 1)) Then
                strTemp = strData(j + 1)
                strData(j + 1) = strData(j)
                strData(j) = strTemp
                
                strTemp = strListItem(j + 1)
                strListItem(j + 1) = strListItem(j)
                strListItem(j) = strTemp
            End If
        Next j
    Next i
    
    For i = LBound(strListItem) To UBound(strListItem)
        strArraySorted(i) = lbAttach.List(strListItem(i), 0) & vbTab & lbAttach.List(strListItem(i), 1) & vbTab & lbAttach.List(strListItem(i), 2) & vbTab & lbAttach.List(strListItem(i), 3)
    Next i
        
    lbAttach.Clear
    For i = LBound(strListItem) To UBound(strListItem)
        vLine = Split(strArraySorted(i), vbTab)
        
        lbAttach.AddItem vLine(0)
        lbAttach.List(lbAttach.ListCount - 1, 1) = vLine(1)
        lbAttach.List(lbAttach.ListCount - 1, 2) = vLine(2)
        lbAttach.List(lbAttach.ListCount - 1, 3) = vLine(3)
    Next i
End Sub

Private Sub ClearForm()
    tbSPoleNum.Value = ""
    tbIPoleNum.Value = ""
    cbPoleNum.Value = False
    
    tbsStatus.Value = ""
    tbiStatus.Value = ""
    cbStatus.Value = False
    
    tbsOwner.Value = ""
    tbiOwner.Value = ""
    cbOwner.Value = False
    
    tbsOwnerNum.Value = ""
    tbiOwnerNum.Value = ""
    cbOwnerNum.Value = False
    
    tbsOtherNum.Value = ""
    tbiOtherNum.Value = ""
    cbOtherNum.Value = False
    
    tbsHC.Value = ""
    tbiHC.Value = ""
    cbHC.Value = False
    
    tbsYear.Value = ""
    tbiYear.Value = ""
    cbYear.Value = False
    
    tbsLL.Value = ""
    tbiLL.Value = ""
    cbLL.Value = False
    
    tbsGRD.Value = ""
    tbiGRD.Value = ""
    cbGRD.Value = False
    
    lbAttach.Clear
    lbUnits.Clear
    
    tbCable.Value = ""
    tbSplices.Value = ""
End Sub

Private Sub ClearAttributes()
    Dim vAttList As Variant
    
    vAttList = objPole.GetAttributes
    
    For i = 9 To 23
        vAttList(i).TextString = ""
    Next i
    
    objPole.Update
End Sub

Attribute VB_Name = "CountFileView"
Attribute VB_Base = "0{E5853688-DEED-4109-BC78-23ACC19B73F0}{909E8AD5-A492-44AC-9824-5F04AFD17611}"
Attribute VB_GlobalNameSpace = False
Attribute VB_Creatable = False
Attribute VB_PredeclaredId = True
Attribute VB_Exposed = False
Attribute VB_TemplateDerived = False
Attribute VB_Customizable = False
Private Sub cbQuit_Click()
    Me.Hide
End Sub

Private Sub UserForm_Initialize()
    lbCounts.ColumnCount = 6
    lbCounts.ColumnWidths = "26;70;36;140;24;84"
End Sub

Attribute VB_Name = "CountsBackspan"
Attribute VB_Base = "0{E2BFAD2E-0BFC-4A3F-8678-D5929950C5D0}{4B49C6D4-47DA-4AB8-94D5-D1899E0B453D}"
Attribute VB_GlobalNameSpace = False
Attribute VB_Creatable = False
Attribute VB_PredeclaredId = True
Attribute VB_Exposed = False
Attribute VB_TemplateDerived = False
Attribute VB_Customizable = False
Dim objCurrent As AcadBlockReference
Dim iSave, iSavePole As Integer

Private Sub cbAddToPole_Click()
    Call UpdatePole
End Sub

Private Sub cbDrop_Click()
    If lbBackspan.ListCount < 1 Then Exit Sub
    
    Dim strCable, strCounts, strSpliced, strCallout As String
    Dim vLine, vItem As Variant
    Dim iIndex As Integer
    
    Load CountsTap
        'CountsTap.lbMain.ColumnCount = 4
        'CountsTap.lbMain.ColumnWidths = "24;72;36;30"
        
        CountsTap.tbStructure.Value = tbStructure.Value
        
        For i = 0 To lbBackspan.ListCount - 1
            CountsTap.lbMain.AddItem lbBackspan.List(i, 0)
            
            If lbBackspan.List(i, 3) = "<>" Then
                CountsTap.lbMain.List(i, 1) = lbBackspan.List(i, 1)
                CountsTap.lbMain.List(i, 2) = lbBackspan.List(i, 2)
            Else
                CountsTap.lbMain.List(i, 1) = "XD"
                CountsTap.lbMain.List(i, 2) = i
            End If
            CountsTap.lbMain.List(i, 3) = ""
        Next i
        
        CountsTap.show
        
        If CountsTap.cbChanged.Value = False Then GoTo Exit_Sub
        
        strLine = CountsTap.tbPosition.Value & ": " & CountsTap.cbCblType.Value & "(" & CountsTap.cbCableSize.Value & ")"
        If Not CountsTap.cbSuffix.Value = "" Then strLine = strLine & CountsTap.cbSuffix.Value
        strLine = strLine & " / " & Replace(CountsTap.tbResult.Value, vbCr, " + ")
        strLine = Replace(strLine, vbLf, "")
        
        'strLine = cable callout
        
        strSpliced = Replace(CountsTap.tbResult.Value, vbLf, "")
        vLine = Split(strSpliced, vbCr)
        strSpliced = ""
        For i = 0 To UBound(vLine)
            vItem = Split(vLine(i), ": ")
            If Not vItem(0) = "XD" Then
                If strSpliced = "" Then
                    strSpliced = vLine(i)
                Else
                    strSpliced = strSpliced & " + " & vLine(i)
                End If
            End If
        Next i
        
        strCallout = Replace(vLine(1), " + ", vbCr)
        
        For i = 0 To CountsTap.lbMain.ListCount - 1
            If Left(CountsTap.lbMain.List(i, 3), 1) = "Y" Then
                lbBackspan.List(i, 3) = tbStructure.Value
                lbBackspan.List(i, 6) = "TAP"
                
                iIndex = CInt(lbBackspan.List(i, 0))
                lbCounts.List(iIndex, 3) = tbStructure.Value
                lbCounts.List(iIndex, 6) = "TAP"
            End If
        Next i
        
        If tbTerminal.Value = "" Then
            tbTerminal.Value = strCallout
        Else
           tbTerminal.Value = tbTerminal.Value & vbCr & strCallout
        End If
        
        Dim objEntity As AcadEntity
        Dim objBlock As AcadBlockReference
        Dim vReturnPnt, vAttList As Variant
        Dim iAtt As Integer
        
        Me.Hide
        
        On Error Resume Next
        
        Err = 0
        ThisDrawing.Utility.GetEntity objEntity, vReturnPnt, vbCr & "Select Block:"
        If Not Err = 0 Then Exit Sub
        
        If Not TypeOf objEntity Is AcadBlockReference Then Exit Sub
        Set objBlock = objEntity
        
        Select Case objBlock.Name
            Case "sPole"
                iAtt = 25
            Case "sPed", "sHH", "sPanel"
                iAtt = 5
            Case Else
                Exit Sub
        End Select
            
        vAttList = objBlock.GetAttributes
        vAttList(iAtt).TextString = strLine
        
        objBlock.Update
        
        'Call CreateCallout
        
        iSave = 1
        iSavePole = 1
        
        Me.show
Exit_Sub:
    Unload CountsTap
End Sub

Private Sub cbGetPole_Click()
    If cbGetPole.Caption = "Get Start Pole" Then
        Call GetInfo
        Exit Sub
    End If
    
    Dim objEntity As AcadEntity
    Dim vBasePnt As Variant
    Dim vAttList As Variant
    Dim vLine, vItem, vTemp, vCount As Variant
    Dim strLine, strTerm, strTemp As String
    Dim result As Integer
    Dim iSFiber, iEFiber As Integer
    Dim iStart, iEnd, iIndex As Integer
    
    If lbBackspan.ListCount < 1 Then
        strLine = "No backspan fibers added to list." & vbCr & "They are needed to know which fibers to move back."
        strLine = strLine & vbCr & "Double click the fibers in the Current Structure Counts list to add them."
        MsgBox strLine
        Exit Sub
    End If
    
    If iSavePole > 0 Then
        result = MsgBox("Update changes to Structure attributes?", vbYesNo, "Update Changes")
        If result = vbYes Then
            Call UpdatePole
        End If
    End If
    
  On Error Resume Next
    Me.Hide
    
    ThisDrawing.Utility.GetEntity objEntity, vBasePnt, "Select Pole: "
    If TypeOf objEntity Is AcadBlockReference Then
        Set objCurrent = objEntity
    Else
        MsgBox "Not a valid object."
        Exit Sub
    End If
    
    lbCurrentCounts.Clear
    
    Select Case objCurrent.Name
        Case "sPole"
            vAttList = objCurrent.GetAttributes
            strLine = vAttList(25).TextString
            strTerm = vAttList(26).TextString
        Case "sPed", "sHH", "sPanel", "sMH"
            vAttList = objCurrent.GetAttributes
            strLine = vAttList(5).TextString
            strTerm = vAttList(6).TextString
        Case Else
            MsgBox "Not a valid block."
            Exit Sub
    End Select
    
    tbStructure.Value = vAttList(0).TextString
    
    strTerm = Replace(strTerm, " + ", vbCr)
    strTerm = Replace(strTerm, "] ", "]" & vbCr)
    tbTerminal.Value = strTerm
    
    vLine = Split(strLine, " / ")
    tbCableType.Value = vLine(0)
    If UBound(vLine) > 0 Then
        vItem = Split(vLine(1), " + ")
        iSFiber = 1
        iEFiber = 1
        vTemp = Split(vItem(0), ": ")
        vCount = Split(vTemp(1), "-")
        If UBound(vCount) = 0 Then
            iEFiber = 1
        Else
            iEFiber = iSFiber + CInt(vCount(1)) - CInt(vCount(0))
        End If
        
        lbCurrentCounts.AddItem iSFiber & "-" & iEFiber
        lbCurrentCounts.List(0, 1) = vTemp(0)
        lbCurrentCounts.List(0, 2) = vTemp(1)
        lbCurrentCounts.List(0, 3) = vTemp(2)
        
        iSFiber = iEFiber + 1
        If UBound(vItem) > 0 Then
            For i = 1 To UBound(vItem)
                vTemp = Split(vItem(i), ": ")
                vCount = Split(vTemp(1), "-")
                If UBound(vCount) > 0 Then
                    iEFiber = iSFiber + CInt(vCount(1)) - CInt(vCount(0))
                End If
        
                lbCurrentCounts.AddItem iSFiber & "-" & iEFiber
                lbCurrentCounts.List(lbCurrentCounts.ListCount - 1, 1) = vTemp(0)
                lbCurrentCounts.List(lbCurrentCounts.ListCount - 1, 2) = vTemp(1)
                lbCurrentCounts.List(lbCurrentCounts.ListCount - 1, 3) = vTemp(2)
                
                iSFiber = iEFiber + 1
            Next i
        End If
    End If
    
    lbCounts.Clear
    lbCounts.AddItem ""
    
    If lbCurrentCounts.ListCount > 0 Then
        For i = 0 To lbCurrentCounts.ListCount - 1
            vLine = Split(lbCurrentCounts.List(i, 0), "-")
            iFStart = CInt(vLine(0))
            If UBound(vLine) > 0 Then
                iFEnd = CInt(vLine(1))
            Else
                iFEnd = iFStart
            End If
            
            vLine = Split(lbCurrentCounts.List(i, 2), "-")
            iStart = CInt(vLine(0)) - iFStart
            
            For j = iFStart To iFEnd
                lbCounts.AddItem j
                lbCounts.List(j, 1) = lbCurrentCounts.List(i, 1)
                lbCounts.List(j, 2) = iStart + j
                lbCounts.List(j, 3) = "<>"
                lbCounts.List(j, 4) = "<>"
                lbCounts.List(j, 5) = "<>"
                lbCounts.List(j, 6) = "<>"
                lbCounts.List(j, 7) = "<>"
            Next j
            
        Next i
    End If
    
    If lbBackspan.ListCount > 0 Then
        For i = 0 To lbBackspan.ListCount - 1
            If lbBackspan.List(i, 3) = "<>" Then
                iStart = CInt(lbBackspan.List(i, 0))
                
                lbCounts.List(iStart, 1) = lbBackspan.List(i, 1)
                lbCounts.List(iStart, 2) = lbBackspan.List(i, 2)
            End If
        Next i
    
        Call GetTapCallout
    End If
    
    'If lbCurrentCounts.ListCount > 0 Then
        'For i = 0 To lbCurrentCounts.ListCount - 1
            'lbProposedCounts.AddItem lbCurrentCounts.List(i, 0)
            'lbProposedCounts.List(i, 1) = lbCurrentCounts.List(i, 1)
            'lbProposedCounts.List(i, 2) = lbCurrentCounts.List(i, 2)
            'lbProposedCounts.List(i, 3) = lbCurrentCounts.List(i, 3)
        'Next i
    'End If
    
Exit_Sub:
    If cbCutCounts.Enabled = False Then
        cbCutCounts.Enabled = True
        cbDrop.Enabled = True
        cbTerminal.Enabled = True
        cbRemoveWL.Enabled = True
        cbSaveSplitter.Enabled = True
        cbAddToPole.Enabled = True
    End If
    
    Me.show
End Sub

Private Sub cbRemoveWL_Click()
    
    iSave = 1
    iSavePole = 1
End Sub

Private Sub cbSaveSplitter_Click()
    Call SaveMCL
End Sub

Private Sub cbTerminal_Click()
    'If objCurrent Is Nothing Then
        'MsgBox "No Pole Selected"
        'Exit Sub
    'End If
    
    Dim iSelected As Integer
    
    For i = 0 To lbBackspan.ListCount - 1
        If lbBackspan.Selected(i) = True Then
            iSelected = i
            GoTo Found_Selected
        End If
    Next i
    
    MsgBox "No Count Selected."
    Exit Sub
    
Found_Selected:
    Dim result As Integer
    
    If Not lbBackspan.List(i, 3) = "<>" Then
        
        result = MsgBox("Overwrite previous assignment?", vbYesNo, "Fiber Assigned!")
        If result = vbNo Then Exit Sub
    End If
    
    Dim objEntity As AcadEntity
    Dim objRES As AcadBlockReference
    Dim vAttList, vBasePnt As Variant
    Dim strLine As String
    Dim strName As String
    Dim iBCount, iECount As Integer
    Dim iCountIndex As Integer
    
    iBCount = 0: iECount = 0
    
    Me.Hide
    On Error Resume Next
    
Next_One:
    
    Err = 0
    ThisDrawing.Utility.GetEntity objEntity, vBasePnt, "Select Building: "
    If Not Err = 0 Then GoTo Exit_Sub
    
    If Not lbBackspan.List(iSelected, 3) = "<>" Then
        
        result = MsgBox("Overwrite previous assignment?", vbYesNo, "Fiber Assigned!")
        If result = vbNo Then Exit Sub
    End If
    
    If TypeOf objEntity Is AcadBlockReference Then
        Set objRES = objEntity
        vAttList = objRES.GetAttributes
            
        Select Case objRES.Name
            'Case "RES", "BUSINESS", "MDU", "TRLR", "SCHOOL", "CHURCH", "LOT"
            Case "SG"
                lbBackspan.List(iSelected, 3) = tbStructure.Value
                lbBackspan.List(iSelected, 4) = "SG"
                lbBackspan.List(iSelected, 5) = vAttList(1).TextString
                lbBackspan.List(iSelected, 6) = "SMARTGRID"
                lbBackspan.List(iSelected, 7) = vAttList(0).TextString
                
                strLine = lbBackspan.List(iSelected, 1) & ": " & lbBackspan.List(iSelected, 2)
                'If cbDrop.Value = False Then strline = "(" & strline & ")"
                vAttList(2).TextString = tbStructure.Value & " - " & strLine
                objRES.Update
                
                strName = lbBackspan.List(iSelected, 1)
                If iECount = 0 Then
                    iECount = CInt(lbBackspan.List(iSelected, 2))
                Else
                    iBCount = CInt(lbBackspan.List(iSelected, 2))
                End If
                
                
            Case "Customer"
                lbBackspan.List(iSelected, 3) = tbStructure.Value
                lbBackspan.List(iSelected, 4) = vAttList(1).TextString
                lbBackspan.List(iSelected, 5) = vAttList(2).TextString
                lbBackspan.List(iSelected, 6) = vAttList(0).TextString
                If vAttList(3).TextString = "" Then
                    lbBackspan.List(iSelected, 7) = "<>"
                Else
                    lbBackspan.List(iSelected, 7) = vAttList(3).TextString
                End If
                
                strLine = lbBackspan.List(iSelected, 1) & ": " & lbBackspan.List(iSelected, 2)
                If cbDrop.Value = False Then strLine = "(" & strLine & ")"
                vAttList(4).TextString = tbStructure.Value & " - " & strLine
                objRES.Update
                
                strName = lbBackspan.List(iSelected, 1)
                If iECount = 0 Then
                    iECount = CInt(lbBackspan.List(iSelected, 2))
                Else
                    iBCount = CInt(lbBackspan.List(iSelected, 2))
                End If
        End Select
    End If
    
    iCountIndex = CInt(lbBackspan.List(iSelected, 0))
    
    lbCounts.List(iCountIndex, 3) = lbBackspan.List(iSelected, 3)
    lbCounts.List(iCountIndex, 4) = lbBackspan.List(iSelected, 4)
    lbCounts.List(iCountIndex, 5) = lbBackspan.List(iSelected, 5)
    lbCounts.List(iCountIndex, 6) = lbBackspan.List(iSelected, 6)
    lbCounts.List(iCountIndex, 7) = lbBackspan.List(iSelected, 7)
    
    iSelected = iSelected - 1
    
    GoTo Next_One
    
Exit_Sub:
    lbBackspan.ListIndex = iSelected
    
    If iECount > 0 Then
        If iBCount = 0 Then
            strName = strName & ": " & iECount
        Else
            strName = strName & ": " & iBCount & "-" & iECount
        End If
        
        strName = strName & ": " & tbStructure.Value
        
        If tbTerminal.Value = "" Then
            tbTerminal.Value = strName
        Else
            tbTerminal.Value = tbTerminal.Value & vbCr & strName
        End If
    End If
    
    'Call UpdateCountsList
    Call GetTapCallout
    
    iSave = 1
    iSavePole = 1
    
    Me.show
End Sub

Private Sub lbCurrentCounts_DblClick(ByVal Cancel As MSForms.ReturnBoolean)
    Dim vLine As Variant
    Dim iStart, iEnd As Integer
    Dim iIndex As Integer
    
    iIndex = lbCurrentCounts.ListIndex
    
    vLine = Split(lbCurrentCounts.List(iIndex, 0), "-")
    iStart = CInt(vLine(0))
    If UBound(vLine) > 0 Then
        iEnd = CInt(vLine(1))
    Else
        iEnd = iStart
    End If
    
    For i = iStart To iEnd
        lbBackspan.AddItem i
        lbBackspan.List(lbBackspan.ListCount - 1, 1) = lbCounts.List(i, 1)
        lbBackspan.List(lbBackspan.ListCount - 1, 2) = lbCounts.List(i, 2)
        lbBackspan.List(lbBackspan.ListCount - 1, 3) = lbCounts.List(i, 3)
        lbBackspan.List(lbBackspan.ListCount - 1, 4) = lbCounts.List(i, 4)
        lbBackspan.List(lbBackspan.ListCount - 1, 5) = lbCounts.List(i, 5)
        lbBackspan.List(lbBackspan.ListCount - 1, 6) = lbCounts.List(i, 6)
        lbBackspan.List(lbBackspan.ListCount - 1, 7) = lbCounts.List(i, 7)
    Next i
    
    'tbFibers.Enabled = True
End Sub

Private Sub tbF2_Exit(ByVal Cancel As MSForms.ReturnBoolean)
    Dim strFileName As String
    Dim vName, vLine, vItem As Variant
    Dim strLine As String
    Dim fName As String
    Dim iIndex As Integer
    
    vName = Split(ThisDrawing.Name, " ")
    strFileName = ThisDrawing.Path & "\" & vName(0) & " Counts -" & tbF2.Value & ".mcl"
    
    fName = Dir(strFileName)
    If fName = "" Then
        MsgBox "No MCL file."
        Exit Sub
    End If
    
    'Load CountFileView
    
    Open strFileName For Input As #2
    
    Line Input #2, strLine
    
    While Not EOF(2)
        Line Input #2, strLine
        vLine = Split(strLine, vbTab)
        
        lbCounts.AddItem vLine(0)
        iIndex = lbCounts.ListCount - 1
        
        lbCounts.List(iIndex, 1) = tbF2.Value
        lbCounts.List(iIndex, 2) = vLine(0)
        
        lbCounts.List(iIndex, 3) = vLine(1)
        lbCounts.List(iIndex, 4) = vLine(2)
        
        If vLine(4) = "TAP" Then
            lbCounts.List(iIndex, 5) = "<>"
            lbCounts.List(iIndex, 6) = "<>"
            lbCounts.List(iIndex, 7) = "<>"
        Else
            lbCounts.List(iIndex, 5) = vLine(3)
            lbCounts.List(iIndex, 6) = vLine(4)
            lbCounts.List(iIndex, 7) = vLine(5)
        End If
    Wend
    
    Close #2
    
    'For i = 0 To lbCounts.ListCount - 1
        'If lbCounts.List(i, 1) = tbF2Name.Value Then
            'iIndex = CInt(lbCounts.List(i, 2)) - 1
            
            'lbCounts.List(iIndex, 1) = lbCounts.List(i, 3)
            ''CountFileView.show
            'lbCounts.List(iIndex, 2) = lbCounts.List(i, 4)
            'lbCounts.List(iIndex, 3) = lbCounts.List(i, 5)
            'lbCounts.List(iIndex, 4) = lbCounts.List(i, 6)
            'lbCounts.List(iIndex, 5) = lbCounts.List(i, 7)
        'End If
    'Next i
    
    
    
    
    'Open strFileName For Output As #3
    
    'Print #3, tbF2Name.Value & " " & tbSplitterName.Value
    
    'For i = 0 To lbCounts.ListCount - 1
        'strLine = ""
        
        'strLine = lbCounts.List(i, 0)
        'If lbCounts.List(i, 1) = " " Then
            'strLine = strLine & vbTab & vbTab & vbTab & vbTab & vbTab
            'GoTo Next_I
        'End If
        
        'strLine = strLine & vbTab & lbCounts.List(i, 1)
        'strLine = strLine & vbTab & lbCounts.List(i, 2)
        'strLine = strLine & vbTab & lbCounts.List(i, 3)
        'strLine = strLine & vbTab & lbCounts.List(i, 4)
        'strLine = strLine & vbTab & lbCounts.List(i, 5)
        
'Next_I:
        'Print #3, strLine
    'Next i
    
    'Close #3
End Sub

Private Sub UserForm_Initialize()
    lbCounts.Clear
    lbCounts.ColumnCount = 8
    lbCounts.ColumnWidths = "24;72;30;66;36;136;48;96"
    
    lbBackspan.Clear
    lbBackspan.ColumnCount = 8
    lbBackspan.ColumnWidths = "24;72;30;66;36;136;48;96"
    
    lbCurrentCounts.Clear
    lbCurrentCounts.ColumnCount = 4
    lbCurrentCounts.ColumnWidths = "48;72;42;6"
    
    lbProposedCounts.Clear
    lbProposedCounts.ColumnCount = 4
    lbProposedCounts.ColumnWidths = "48;72;42;6"
    
    iSave = 0
    iSavePole = 0
End Sub

Private Sub GetTapCallout()
    If lbCounts.ListCount < 1 Then Exit Sub
    
    Dim strLine, strItem As String
    Dim strCurrent, strPrevious As String
    Dim iStart, iEnd As Integer
    Dim iFStart, iFEnd As Integer
    Dim iIndex As Integer
    
    lbCurrentCounts.Clear
    
    strPrevious = lbCounts.List(1, 1)
    If Not lbCounts.List(1, 3) = "<>" Then strPrevious = "XD"
    strCurrent = strPrevious
    iStart = CInt(lbCounts.List(1, 2))
    iEnd = iStart
    iFStart = 1
    iFEnd = 1
    
    For i = 2 To lbCounts.ListCount - 1
        strCurrent = lbCounts.List(i, 1)
        If Not lbCounts.List(i, 3) = "<>" Then strCurrent = "XD"
        
        If strCurrent = strPrevious Then
            iEnd = CInt(lbCounts.List(i, 2))
            iFEnd = iFEnd + 1
        Else
            strLine = iFStart
            If iFEnd > iFStart Then strLine = strLine & "-" & iFEnd
            strItem = iStart
            If iEnd > iStart Then strItem = strItem & "-" & iEnd
            
            lbCurrentCounts.AddItem strLine
            iIndex = lbCurrentCounts.ListCount - 1
            lbCurrentCounts.List(iIndex, 1) = strPrevious
            lbCurrentCounts.List(iIndex, 2) = strItem
            lbCurrentCounts.List(iIndex, 3) = tbStructure.Value
             
            strPrevious = strCurrent
            iStart = CInt(lbCounts.List(i, 2))
            iEnd = iStart
            iFStart = iFEnd + 1
            iFEnd = iFStart
        End If
    Next i
    
    strLine = iFStart
    If iFEnd > iFStart Then strLine = strLine & "-" & iFEnd
    strItem = iStart
    If iEnd > iStart Then strItem = strItem & "-" & iEnd
            
    lbCurrentCounts.AddItem strLine
    iIndex = lbCurrentCounts.ListCount - 1
    lbCurrentCounts.List(iIndex, 1) = strPrevious
    lbCurrentCounts.List(iIndex, 2) = strItem
    lbCurrentCounts.List(iIndex, 3) = tbStructure.Value
End Sub

Private Sub GetInfo()
    Dim objEntity As AcadEntity
    Dim objBlock As AcadBlockReference
    Dim vBasePnt As Variant
    Dim vAttList As Variant
    Dim strLine, strTerm, strTemp As String
    Dim vLine, vItem, vTemp, vCount As Variant
    Dim iSFiber, iEFiber As Integer
    Dim iStart, iEnd, iIndex As Integer
    
  On Error Resume Next
    Me.Hide
    
    ThisDrawing.Utility.GetEntity objEntity, vBasePnt, "Select Pole: "
    If TypeOf objEntity Is AcadBlockReference Then
        Set objBlock = objEntity
    Else
        MsgBox "Not a valid object."
        Exit Sub
    End If
    
    lbCurrentCounts.Clear
    
    Select Case objBlock.Name
        Case "sPole"
            vAttList = objBlock.GetAttributes
            strLine = vAttList(25).TextString
            strTerm = vAttList(26).TextString
        Case "sPed", "sHH", "sPanel", "sMH"
            vAttList = objBlock.GetAttributes
            strLine = vAttList(5).TextString
            strTerm = vAttList(6).TextString
        Case Else
            MsgBox "Not a valid block."
            Exit Sub
    End Select
    
    'tbStructure.Value = vAttList(0).TextString
    
    'strTerm = Replace(strTerm, " + ", vbCr)
    'strTerm = Replace(strTerm, "] ", "]" & vbCr)
    'tbTerminal.Value = strTerm
    
    vLine = Split(strLine, " / ")
    'tbCableType.Value = vLine(0)
    If UBound(vLine) > 0 Then
        vItem = Split(vLine(1), " + ")
        iSFiber = 1
        iEFiber = 1
        vTemp = Split(vItem(0), ": ")
        vCount = Split(vTemp(1), "-")
        If UBound(vCount) = 0 Then
            iEFiber = 1
        Else
            iEFiber = iSFiber + CInt(vCount(1)) - CInt(vCount(0))
        End If
        
        lbCurrentCounts.AddItem iSFiber & "-" & iEFiber
        lbCurrentCounts.List(0, 1) = vTemp(0)
        lbCurrentCounts.List(0, 2) = vTemp(1)
        lbCurrentCounts.List(0, 3) = vTemp(2)
        
        iSFiber = iEFiber + 1
        If UBound(vItem) > 0 Then
            For i = 1 To UBound(vItem)
                vTemp = Split(vItem(i), ": ")
                vCount = Split(vTemp(1), "-")
                If UBound(vCount) > 0 Then
                    iEFiber = iSFiber + CInt(vCount(1)) - CInt(vCount(0))
                End If
        
                lbCurrentCounts.AddItem iSFiber & "-" & iEFiber
                lbCurrentCounts.List(lbCurrentCounts.ListCount - 1, 1) = vTemp(0)
                lbCurrentCounts.List(lbCurrentCounts.ListCount - 1, 2) = vTemp(1)
                lbCurrentCounts.List(lbCurrentCounts.ListCount - 1, 3) = vTemp(2)
                
                iSFiber = iEFiber + 1
            Next i
        End If
    End If
    
    lbCounts.Clear
    lbCounts.AddItem ""
    
    If lbCurrentCounts.ListCount > 0 Then
        For i = 0 To lbCurrentCounts.ListCount - 1
            vLine = Split(lbCurrentCounts.List(i, 0), "-")
            iFStart = CInt(vLine(0))
            If UBound(vLine) > 0 Then
                iFEnd = CInt(vLine(1))
            Else
                iFEnd = iFStart
            End If
            
            vLine = Split(lbCurrentCounts.List(i, 2), "-")
            iStart = CInt(vLine(0)) - iFStart
            
            For j = iFStart To iFEnd
                lbCounts.AddItem j
                lbCounts.List(j, 1) = lbCurrentCounts.List(i, 1)
                lbCounts.List(j, 2) = iStart + j
                lbCounts.List(j, 3) = "<>"
                lbCounts.List(j, 4) = "<>"
                lbCounts.List(j, 5) = "<>"
                lbCounts.List(j, 6) = "<>"
                lbCounts.List(j, 7) = "<>"
            Next j
            
        Next i
    End If
    
    cbGetPole.Caption = "Get Backspan Pole"
    
    Me.show
End Sub

Private Sub UserForm_Terminate()
    Dim result As Integer
    
    If iSavePole > 0 Then
        result = MsgBox("Update changes to Structure attributes?", vbYesNo, "Update Changes")
        If result = vbYes Then
            Call UpdatePole
        End If
    End If
    
    If iSave > 0 Then
        result = MsgBox("Save changes to Master List?", vbYesNo, "Save Changes")
        If result = vbYes Then
            Call SaveMCL
        End If
    End If
End Sub

Private Sub SaveMCL()
    Dim strFileName, strText As String
    Dim vName, vLine, vItem, vList As Variant
    Dim vText As Variant
    Dim strLine, strList As String
    Dim fName As String
    Dim iIndex As Integer
    
    strList = ""
    For i = 0 To lbCounts.ListCount - 1
        If Not lbCounts.List(i, 1) = "XD" Then
            If lbCounts.List(i, 6) = "" Then GoTo Next_I
            If lbCounts.List(i, 6) = "TAP" Then GoTo Next_I
            
            If strList = "" Then
                strList = lbCounts.List(i, 1)
            Else
                vLine = Split(strList, ";;")
                For j = 0 To UBound(vLine)
                    If vLine(j) = lbCounts.List(i, 1) Then GoTo Found_Name
                Next j
                
                strList = strList & ";;" & lbCounts.List(i, 1)
Found_Name:
            End If
        End If
Next_I:
    Next i
    
    If strList = "" Then Exit Sub
    
    vList = Split(strList, ";;")
    For n = 0 To UBound(vList)
        vName = Split(ThisDrawing.Name, " ")
        strFileName = strSplitterFilePath & "\" & vName(0) & " Counts -" & vList(n) & ".mcl"
    
        fName = Dir(strFileName)
        If fName = "" Then
            MsgBox "No MCL file for  " & vList(n) & "."
            GoTo Next_N
        End If
        
        Open strFileName For Input As #1
        strText = Input(LOF(1), 1)
        Close #1
        
        strText = Replace(strText, vbLf, "")
        vText = Split(strText, vbCr)
        
        For i = 0 To lbCounts.ListCount - 1
            If lbCounts.List(i, 1) = vList(n) Then
                strLine = lbCounts.List(i, 2)
                If lbCounts.List(i, 6) = "TAP" Then
                    strLine = strLine & vbTab & "<>" & vbTab & "<>" & vbTab & "<>" & vbTab & "<>" & vbTab & "<>" & vbTab & "<>"
                Else
                    If lbCounts.List(i, 3) = "" Then
                        strLine = strLine & vbTab & "<>"
                    Else
                        strLine = strLine & vbTab & lbCounts.List(i, 3)
                    End If
                    If lbCounts.List(i, 4) = "" Then
                        strLine = strLine & vbTab & "<>"
                    Else
                        strLine = strLine & vbTab & lbCounts.List(i, 4)
                    End If
                    If lbCounts.List(i, 5) = "" Then
                        strLine = strLine & vbTab & "<>"
                    Else
                        strLine = strLine & vbTab & lbCounts.List(i, 5)
                    End If
                    If lbCounts.List(i, 6) = "" Then
                        strLine = strLine & vbTab & "<>"
                    Else
                        strLine = strLine & vbTab & lbCounts.List(i, 6)
                    End If
                    If lbCounts.List(i, 7) = "" Then
                        strLine = strLine & vbTab & "<>"
                    Else
                        strLine = strLine & vbTab & lbCounts.List(i, 7)
                    End If
                End If
                
                For j = 0 To UBound(vText)
                    vItem = Split(vText(j), vbTab)
                    If vItem(0) = lbCounts.List(i, 2) Then
                        vText(j) = strLine
                        GoTo Found_Line
                    End If
                Next j
Found_Line:
                
            End If
        Next i
        
        strText = vText(0)
        If UBound(vText) > 0 Then
            For j = 1 To UBound(vText)
                strText = strText & vbCr & vText(j)
            Next j
        End If
        
    
        Open strFileName For Output As #2
    
        'Print #2, vList(n) '& " " & tbSplitterName.Value
        Print #2, strText
    
        Close #2
Next_N:
    Next n
    
    iSave = 0
End Sub

Private Sub UpdatePole()
    If lbCurrentCounts.ListCount < 1 Then Exit Sub
    
    Dim vAttList As Variant
    Dim strCable, strTerm, strTemp As String
    
    strTemp = lbCurrentCounts.List(0, 1) & ": " & lbCurrentCounts.List(0, 2) & ": " & lbCurrentCounts.List(0, 3)
    strCable = tbCableType.Value & " / " & strTemp
    
    If lbCurrentCounts.ListCount > 1 Then
        For i = 1 To lbCurrentCounts.ListCount - 1
            strTemp = lbCurrentCounts.List(i, 1) & ": " & lbCurrentCounts.List(i, 2) & ": " & lbCurrentCounts.List(i, 3)
            strCable = strCable & " + " & strTemp
        Next i
    End If
    
    If tbTerminal.Value = "" Then
        strTerm = ""
    Else
        strTerm = Replace(tbTerminal.Value, "]" & vbCr, "] ")
        strTerm = Replace(strTerm, vbCr, " + ")
    End If
    
    Select Case objCurrent.Name
        Case "sPole"
            vAttList = objCurrent.GetAttributes
            vAttList(25).TextString = strCable
            vAttList(26).TextString = strTerm
        Case Else
            vAttList = objCurrent.GetAttributes
            vAttList(5).TextString = strCable
            vAttList(6).TextString = strTerm
    End Select
    
    objCurrent.Update
    iSavePole = 0
End Sub

Private Sub UpdateCountsList()
    Dim iIndex As Integer
    
    For i = 0 To lbBackspan.ListCount - 1
        iIndex = CInt(lbBackspan.List(i, 0))
        
        lbCounts.List(iIndex, 0) = lbBackspan.List(1, 0)
        lbCounts.List(iIndex, 1) = lbBackspan.List(1, 1)
        lbCounts.List(iIndex, 2) = lbBackspan.List(1, 2)
        lbCounts.List(iIndex, 3) = lbBackspan.List(1, 3)
        lbCounts.List(iIndex, 4) = lbBackspan.List(1, 4)
        lbCounts.List(iIndex, 5) = lbBackspan.List(1, 5)
        lbCounts.List(iIndex, 6) = lbBackspan.List(1, 6)
        lbCounts.List(iIndex, 7) = lbBackspan.List(1, 7)
    Next i
End Sub

Attribute VB_Name = "CountsForm"
Attribute VB_Base = "0{CF26F951-CB11-4FCE-A87E-833A4BBE569A}{7A163872-191D-4DC1-9C6A-B65A10D2242D}"
Attribute VB_GlobalNameSpace = False
Attribute VB_Creatable = False
Attribute VB_PredeclaredId = True
Attribute VB_Exposed = False
Attribute VB_TemplateDerived = False
Attribute VB_Customizable = False
Dim objBlock As AcadBlockReference
Dim strPreviousBlock As String
Dim strCableCallout As String
Dim strSplitterFilePath As String
Dim bSave, bUpdatePole As Boolean

Private Sub cbAddClosure_Click()
    If tbCallout.Value = "" Then Exit Sub
    
    Dim objCallout As AcadBlockReference
    Dim returnPnt As Variant
    Dim vBlockCoords(0 To 2) As Double
    Dim lwpCoords(0 To 3) As Double
    Dim dPrevious(0 To 2) As Double
    Dim dOrigin(0 To 2) As Double
    Dim dScale As Double
    Dim lineObj As AcadLWPolyline
    Dim objCircle As AcadCircle
    Dim objCircle2 As AcadCircle
    Dim objText As AcadText
    Dim objText2 As AcadText
    Dim vLine, vCounts, vItem As Variant
    Dim iIndex As Integer
    
    Dim strAtt0, strAtt1, strAtt2 As String
    Dim strLayer, strCounts As String
    Dim iHO1 As Integer
    
    strAtt0 = tbActivePole.Value & ": " & tbPosition.Value
    
    iHO1 = 0
    strCounts = Replace(tbCallout.Value, vbLf, "")
    vCounts = Split(tbCallout.Value, vbCr)
    
    For i = 0 To UBound(vCounts)
        vLine = Split(vCounts(i), ": ")
        vItem = Split(vLine(1), "-")
        
        If UBound(vItem) = 0 Then
            iHO1 = iHO1 + 1
        Else
            iHO1 = iHO1 + CInt(vItem(1)) - CInt(vItem(0)) + 1
        End If
    Next i
    
    If cbCblType.Value = "CO" Then
        strAtt1 = "+HO1A=" & iHO1
        strLayer = "Integrity Proposed-Aerial"
    Else
        strAtt1 = "+HO1B=" & iHO1
        strLayer = "Integrity Proposed-Buried"
    End If
    
    strAtt2 = Replace(tbCallout.Value, vbCr, "\P")
    strAtt2 = Replace(strAtt2, vbLf, "")
    
    dOrigin(0) = 0
    dOrigin(1) = 0
    dOrigin(2) = 0
    
    Me.Hide
    
    returnPnt = ThisDrawing.Utility.GetPoint(, "Select Point: ")
    lwpCoords(0) = returnPnt(0)
    lwpCoords(1) = returnPnt(1)
    dPrevious(0) = returnPnt(0)
    dPrevious(1) = returnPnt(1)
    dPrevious(2) = 0#
    
    returnPnt = ThisDrawing.Utility.GetPoint(dPrevious, "Select Point: ")
    vBlockCoords(0) = returnPnt(0)
    vBlockCoords(1) = returnPnt(1)
    vBlockCoords(2) = returnPnt(2)
    lwpCoords(2) = vBlockCoords(0)
    lwpCoords(3) = vBlockCoords(1)
    
    Set lineObj = ThisDrawing.ModelSpace.AddLightWeightPolyline(lwpCoords)
    lineObj.Layer = strLayer
    lineObj.Update
    
    dScale = CDbl(cbScale.Value) / 100
    If dScale = 0 Then dScale = 0.75
        
    Set objCallout = ThisDrawing.ModelSpace.InsertBlock(vBlockCoords, "Callout", dScale, dScale, dScale, 0)
    attItem = objCallout.GetAttributes
    
    attItem(0).TextString = strAtt0
    attItem(1).TextString = strAtt1
    attItem(2).TextString = strAtt2
    
    objCallout.Layer = strLayer
    
    If lwpCoords(2) < lwpCoords(0) Then
        vBlockCoords(0) = vBlockCoords(0) - (75 * dScale)
        objCallout.InsertionPoint = vBlockCoords
    End If
    objCallout.Update
    
    Me.show
End Sub

Private Sub cbAddToPole_Click()
    Me.Hide
    Call UpdateTerminal
    
    'Call UpdateCable
    Call UpdateCableCallout
    Me.show
End Sub

Private Sub cbCallout_Click()
    If tbCblCallout.Value = "" Then Exit Sub
    
    Dim objCallout As AcadBlockReference
    Dim returnPnt As Variant
    Dim vBlockCoords(0 To 2) As Double
    Dim lwpCoords(0 To 3) As Double
    Dim dPrevious(0 To 2) As Double
    Dim dOrigin(0 To 2) As Double
    Dim dScale As Double
    Dim lineObj As AcadLWPolyline
    Dim objCircle As AcadCircle
    Dim objCircle2 As AcadCircle
    Dim objText As AcadText
    Dim objText2 As AcadText
    Dim vLine, vCounts As Variant
    Dim iIndex As Integer
    
    Dim strAtt0, strAtt1, strAtt2 As String
    Dim strLayer As String
    
    strAtt0 = tbActivePole.Value & ": " & tbPosition.Value
    strAtt1 = cbCblType.Value & "(" & cbCableSize.Value & ")"
    If Not cbSuffix.Value = "" Then strAtt1 = strAtt1 & cbSuffix.Value
    strAtt2 = Replace(tbCblCallout.Value, vbCr, "\P")
    strAtt2 = Replace(strAtt2, vbLf, "")
    
    If Left(strAtt1, 2) = "CO" Then
        strLayer = "Integrity Proposed-Aerial"
    Else
        strLayer = "Integrity Proposed-Buried"
    End If
    
    dOrigin(0) = 0
    dOrigin(1) = 0
    dOrigin(2) = 0
    
    Me.Hide
    
    returnPnt = ThisDrawing.Utility.GetPoint(, "Select Point: ")
    lwpCoords(0) = returnPnt(0)
    lwpCoords(1) = returnPnt(1)
    dPrevious(0) = returnPnt(0)
    dPrevious(1) = returnPnt(1)
    dPrevious(2) = 0#
    
    returnPnt = ThisDrawing.Utility.GetPoint(dPrevious, "Select Point: ")
    vBlockCoords(0) = returnPnt(0)
    vBlockCoords(1) = returnPnt(1)
    vBlockCoords(2) = returnPnt(2)
    lwpCoords(2) = vBlockCoords(0)
    lwpCoords(3) = vBlockCoords(1)
    
    If cbPlacement.Value = "Leader" Then
        Set lineObj = ThisDrawing.ModelSpace.AddLightWeightPolyline(lwpCoords)
        lineObj.Layer = strLayer
        lineObj.Update
    Else
        Set objCircle = ThisDrawing.ModelSpace.AddCircle(dPrevious, 8)
        objCircle.Layer = strLayer
        objCircle.Update
        Set objCircle2 = ThisDrawing.ModelSpace.AddCircle(returnPnt, 8)
        objCircle2.Layer = strLayer
        objCircle2.Update
        
        strLetter = UCase(ThisDrawing.Utility.GetString(0, "Enter Callout Letter:"))
        Set objText = ThisDrawing.ModelSpace.AddText(strLetter, dOrigin, 8)
        Set objText2 = ThisDrawing.ModelSpace.AddText(strLetter, dOrigin, 8)
        objText.Layer = strLayer
        objText.Alignment = acAlignmentMiddle
        objText.TextAlignmentPoint = dPrevious
        objText2.Layer = strLayer
        objText2.Alignment = acAlignmentMiddle
        objText2.TextAlignmentPoint = vBlockCoords
        objText.Update
        objText2.Update
        
        vBlockCoords(0) = vBlockCoords(0) + 8
        lwpCoords(0) = 0
    End If
    
    
    dScale = CDbl(cbScale.Value) / 100
    If dScale = 0 Then dScale = 0.75
        
    Set objCallout = ThisDrawing.ModelSpace.InsertBlock(vBlockCoords, "Callout", dScale, dScale, dScale, 0)
    attItem = objCallout.GetAttributes
    
    attItem(0).TextString = strAtt0
    attItem(1).TextString = strAtt1
    attItem(2).TextString = strAtt2
    
    objCallout.Layer = strLayer
    
    If lwpCoords(2) < lwpCoords(0) Then
        vBlockCoords(0) = vBlockCoords(0) - (75 * dScale)
        objCallout.InsertionPoint = vBlockCoords
    End If
    objCallout.Update
    
    Me.show
End Sub

Private Sub cbCreateMCLfile_Click()
    Me.Hide
    
    Load CreateMCL
        CreateMCL.show
    Unload CreateMCL
    
    Me.show
End Sub

Private Sub cbCutCounts_Click()
    If tbTapNeeded.Value = "" Then tbTapNeeded.Value = "1"
    If Not lbCounts.List(i, 3) = "<>" Then Exit Sub
    If tbActivePole.Value = "" Then
        MsgBox "Need to select Active Pole."
        Call GetActivePole
    End If
    
    Dim iSelected As Integer
    
    For i = 0 To lbCounts.ListCount - 1
        If lbCounts.Selected(i) = True Then
            iSelected = i
            GoTo Found_Selected
        End If
    Next i
    
    MsgBox "No Count Selected."
    Exit Sub
    
Found_Selected:
    
    If Not lbCounts.List(i, 3) = "<>" Then
        Dim result As Integer
        
        result = MsgBox("Overwrite previous assignment?", vbYesNo, "Fiber Assigned!")
        If result = vbNo Then Exit Sub
    End If
    
    Dim iFirst, iNeeded, iIndex As Integer
    Dim strName, strLine As String
    Dim iBCount, iECount As Integer
    
    'If tbTapNeeded.Value = "" Then
        'iNeeded = 1
    'Else
        iNeeded = CInt(tbTapNeeded.Value)
    'End If
    
    iIndex = lbCounts.ListIndex
    iFirst = iIndex - iNeeded + 1
    
    If iFirst < 1 Then
        MsgBox "Out of range." & vbCr & "Fibers needed in cable don't exist."
        Exit Sub
    End If
    
    strName = lbCounts.List(iIndex, 1)
    iBCount = 0
    iECount = CInt(lbCounts.List(iIndex, 2))
    
    For i = iIndex To iFirst Step -1
        If strName = lbCounts.List(i, 1) And lbCounts.List(i, 3) = "<>" Then
            iBCount = CInt(lbCounts.List(i, 2))
            
            lbCounts.List(i, 3) = tbActivePole.Value
            lbCounts.List(i, 6) = "FUTURE"
        Else
            strLine = strName & ": " & i & " not available."
            MsgBox strLine
            GoTo Exit_Next
        End If
    Next i
Exit_Next:
    
    If iBCount = 0 Then
        strLine = strName & ": " & iECount
    Else
        If iBCount = iECount Then
            strLine = strName & ": " & iECount
        Else
            strLine = strName & ": " & iBCount & "-" & iECount
        End If
        
        
    End If
    
    If tbCallout.Value = "" Then
        tbCallout.Value = strLine & " FUTURE"
    Else
        tbCallout.Value = tbCallout.Value & vbCr & strLine & " FUTURE"
    End If
    
    lbCounts.ListIndex = i
    
    bUpdatePole = True
    
    Call CreateCallout
End Sub

Private Sub cbDrop_Click()
    If lbCounts.ListCount < 1 Then Exit Sub
    
    Dim strCable, strCounts, strSpliced, strCallout As String
    Dim vLine, vItem As Variant
    Dim iExist As Integer
    
    iExist = 0
    Me.Hide
    Load CountsTap
        'CountsTap.lbMain.ColumnCount = 4
        'CountsTap.lbMain.ColumnWidths = "24;72;36;30"
        
        CountsTap.tbStructure.Value = tbActivePole.Value
        
        For i = 1 To lbCounts.ListCount - 1
            CountsTap.lbMain.AddItem i
            
            If lbCounts.List(i, 3) = "<>" Then
                CountsTap.lbMain.List(i - 1, 1) = lbCounts.List(i, 1)
                CountsTap.lbMain.List(i - 1, 2) = lbCounts.List(i, 2)
            Else
                CountsTap.lbMain.List(i - 1, 1) = "XD"
                CountsTap.lbMain.List(i - 1, 2) = i
            End If
            CountsTap.lbMain.List(i - 1, 3) = ""
        Next i
        
        CountsTap.show
        
        If CountsTap.cbChanged.Value = False Then GoTo Exit_Sub
        If CountsTap.cbExisting.Value = True Then iExist = 1
        
        strLine = CountsTap.tbPosition.Value & ": " & CountsTap.cbCblType.Value & "(" & CountsTap.cbCableSize.Value & ")"
        If Not CountsTap.cbSuffix.Value = "" Then strLine = strLine & CountsTap.cbSuffix.Value
        strLine = strLine & " / " & Replace(CountsTap.tbResult.Value, vbCr, " + ")
        strLine = Replace(strLine, vbLf, "")
        
        'strLine = cable callout
        
        strSpliced = Replace(CountsTap.tbResult.Value, vbLf, "")
        vLine = Split(strSpliced, vbCr)
        strSpliced = ""
        For i = 0 To UBound(vLine)
            vItem = Split(vLine(i), ": ")
            If Not vItem(0) = "XD" Then
                If strSpliced = "" Then
                    strSpliced = vLine(i)
                Else
                    strSpliced = strSpliced & " + " & vLine(i)
                End If
            End If
        Next i
        
        strCallout = Replace(strSpliced, " + ", vbCr)
        
        For i = 0 To CountsTap.lbMain.ListCount - 1
            If Left(CountsTap.lbMain.List(i, 3), 1) = "Y" Then
                lbCounts.List(i + 1, 1) = "XD"
                lbCounts.List(i + 1, 2) = lbCounts.List(i + 1, 0)
                
                'lbCounts.List(i + 1, 3) = tbActivePole.Value
                'lbCounts.List(i + 1, 6) = "TAP"
            End If
        Next i
    
        If tbCallout.Value = "" Then
            tbCallout.Value = strCallout
        Else
            tbCallout.Value = tbCallout.Value & vbCr & strCallout
        End If
        
        Dim objEntity As AcadEntity
        Dim objBlock As AcadBlockReference
        Dim vReturnPnt, vAttList As Variant
        Dim iAtt As Integer
        
        On Error Resume Next
        
        Err = 0
        ThisDrawing.Utility.GetEntity objEntity, vReturnPnt, vbCr & "Select Block:"
        If Not Err = 0 Then Exit Sub
    
        If Not TypeOf objEntity Is AcadBlockReference Then Exit Sub
        Set objBlock = objEntity
        
        Select Case objBlock.Name
            Case "sPole"
                iAtt = 25
            Case "sPed", "sHH", "sPanel"
                iAtt = 5
            Case Else
                Exit Sub
        End Select
        
        vAttList = objBlock.GetAttributes
        vAttList(iAtt).TextString = strLine
           
        objBlock.Update
        
        bUpdatePole = True
        
        'lbCounts.ListIndex = i
        Call CreateCallout
        
Exit_Sub:
    
    Unload CountsTap
    Me.show
End Sub

Private Sub cbExistingCable_Click()
    Dim objEntity As AcadEntity
    Dim vAttList, vBasePnt As Variant
    Dim vCable, vCounts, vLine, vItem As Variant
    Dim strLine, strNames As String
    Dim strCables As String
    Dim iFiber As Integer
    Dim iAtt As Integer
    
    strNames = ""
    
    Me.Hide
    
  On Error Resume Next
    
    ThisDrawing.Utility.GetEntity objEntity, vBasePnt, "Select Pole: "
    If TypeOf objEntity Is AcadBlockReference Then
        Set objBlock = objEntity
    Else
        MsgBox "Not a valid object."
        Me.show
        Exit Sub
    End If
    
    Select Case objBlock.Name
        Case "sPole"
            iAtt = 25
        Case "sPed", "sHH", "sPanel", "sMH"
            iAtt = 5
        Case Else
            MsgBox "Not a valid block."
            Me.show
            Exit Sub
    End Select
    
    vAttList = objBlock.GetAttributes
    
    If vAttList(iAtt).TextString = "" Then
        MsgBox "Structure has no Cables."
        Me.show
        Exit Sub
    End If
    
    strCables = Replace(vAttList(iAtt).TextString, vbLf, "")
    vCable = Split(strCables, vbCr)
        
    If UBound(vCable) > 0 Then
        Load SelectCable
            SelectCable.cbNewCable.Enabled = False
                
            For i = 0 To UBound(vCable)
                SelectCable.lbCable.AddItem vCable(i)
            Next i
                
            SelectCable.show
                
            strCables = SelectCable.lbCable.List(SelectCable.lbCable.ListIndex)
        Unload SelectCable
    End If
        
    strCableCallout = strCables
        
    vCable = Split(strCables, " / ")
    strLine = Replace(vCable(1), " + ", vbCr)
        
    tbCblCallout.Value = strLine
    
    tbActivePole.Value = vAttList(0).TextString
    
    vCounts = Split(vCable(0), ")")
    vLine = Split(vCounts(0), "(")
    
    vItem = Split(vLine(0), ": ")
    
    cbCblType.Value = vItem(1)
    cbCableSize.Value = vLine(1)
    cbSuffix.Value = vCounts(1)
    tbPosition.Value = vItem(0)
    
    lbCounts.AddItem ""
    For i = 1 To CInt(vLine(1))
        lbCounts.AddItem i
    Next i
    
    iFiber = 1
    vCounts = Split(tbCblCallout.Value, vbCrLf)
    
    'MsgBox vCounts(0) & " + " & vCounts(1)
    
    For i = 0 To UBound(vCounts)
        If iFiber > CInt(cbCableSize.Value) Then
            MsgBox "Number of fibers in Counts > the cable size"
            GoTo Cable_Filled
        End If
        
        vLine = Split(vCounts(i), ": ")
        vItem = Split(vLine(1), "-")
        
        'If Not vLine(0) = "XD" Then
        If InStr(vLine(0), "XD") < 1 Then
            If strNames = "" Then
                strNames = vLine(0)
            Else
                strNames = strNames & ";" & vLine(0)
            End If
            strPreviousBlock = vLine(2)
            tbF2Name.Value = vLine(0)
        End If
        
        If UBound(vItem) = 0 Then
            lbCounts.List(iFiber, 1) = vLine(0)
            lbCounts.List(iFiber, 2) = vItem(0)
            lbCounts.List(iFiber, 3) = "<>"
            lbCounts.List(iFiber, 4) = "<>"
            lbCounts.List(iFiber, 5) = "<>"
            lbCounts.List(iFiber, 6) = "<>"
            lbCounts.List(iFiber, 7) = "<>"
            iFiber = iFiber + 1
        Else
            For j = CInt(vItem(0)) To CInt(vItem(1))
                lbCounts.List(iFiber, 1) = vLine(0)
                lbCounts.List(iFiber, 2) = j
                lbCounts.List(iFiber, 3) = "<>"
                lbCounts.List(iFiber, 4) = "<>"
                lbCounts.List(iFiber, 5) = "<>"
                lbCounts.List(iFiber, 6) = "<>"
                lbCounts.List(iFiber, 7) = "<>"
                iFiber = iFiber + 1
            Next j
        End If
    Next i
    
Cable_Filled:
    If iFiber < CInt(cbCableSize.Value) + 1 Then
        For i = iFiber To CInt(cbCableSize.Value) + 1
            lbCounts.List(i, 1) = vLine(0)
            lbCounts.List(i, 2) = i
            lbCounts.List(i, 3) = "<>"
            lbCounts.List(i, 4) = "<>"
            lbCounts.List(i, 5) = "<>"
            lbCounts.List(i, 6) = "<>"
            lbCounts.List(i, 7) = "<>"
            Call CreateCallout
        Next i
        
        MsgBox "Number of fibers in Counts < the cable size"
    End If
    
    Call EnableAll
    
    vLine = Split(strNames, ";")
    For i = 0 To UBound(vLine)
        GetSpliced CStr(vLine(i))
    Next i
    
    'Call CreateCallout
    
    Call AutoFiber
    
    iAtt = iAtt + 1
    
    If Not vAttList(iAtt).TextString = "" Then
        Dim vClosures As Variant
        Dim strPosition, strClosure As String
        
        strPosition = "[" & tbPosition.Value & "]"
        
        strClosure = Replace(vAttList(iAtt).TextString, vbLf, "")
        vClosures = Split(strClosure, vbCr)
        
        For i = 0 To UBound(vClosures)
            If InStr(vClosures(i), strPosition) > 0 Then
                vItem = Split(vClosures(i), "] ")
                vLine = Split(vItem(1), " + ")
                
                strLine = vLine(0)
                If UBound(vLine) > 0 Then
                    For j = 1 To UBound(vLine)
                        strLine = strLine & vbCr & vLine(j)
                    Next j
                End If
                
                tbCallout.Value = strLine
                
                GoTo Exit_Sub
            End If
        Next i
    End If
    
Exit_Sub:
    
    cbGetPole.Enabled = True
    cbAddToPole.Enabled = True
    cbNewCable.Enabled = False
    cbExistingCable.Enabled = False
    
    Me.show
End Sub

Private Sub cbGetPole_Click()
    Me.Hide
    Call CreateCallout
    
    Call UpdateTerminal
    
    Call UpdateTerminalCallout
    
    Dim strTest As String
    strTest = tbActivePole.Value
    
    Call GetActivePole
    
    If strTest = tbActivePole.Value Then
        Me.show
        Exit Sub
    End If
    
    Call UpdateCable
    
    Call UpdateCableCallout
    
    Dim vAttList, vList, vItem, vSplice As Variant
    Dim strLine, strPosition As String
    Dim iAtt As Integer
    
    vAttList = objBlock.GetAttributes
    
    Select Case objBlock.Name
        Case "sPole"
            If Not vAttList(8).TextString = "" Then
                Select Case UCase(vAttList(8).TextString)
                    Case "M"
                        vAttList(8).TextString = "MGNV"
                    Case "T"
                        vAttList(8).TextString = "TGB"
                    Case "B"
                        vAttList(8).TextString = "BROKEN"
                    Case "", "NA", "N/A"
                        vAttList(8).TextString = "NO GRD"
                End Select
                tbGround.Value = vAttList(8).TextString
            End If
            
            iAtt = 26
        Case Else
            iAtt = 6
    End Select
    
    If vAttList(iAtt).TextString = "" Then
        tbCallout.Value = ""
    Else
        strLine = Replace(vAttList(iAtt).TextString, vbLf, "")
        
        vList = Split(strLine, vbCr)
        
        For i = 0 To UBound(vList)
            vItem = Split(vList(i), "] ")
            strPosition = Replace(vItem(0), "[", "")
            
            If strPosition = tbPosition.Value Then
                If Not vItem(1) = "" Then
                    vSplice = Split(vItem(1), " + ")
                    
                    strLine = vSplice(0)
                
                    If UBound(vSplice) > 0 Then
                        For j = 1 To UBound(vSplice)
                            strLine = strLine & vbCr & vSplice(j)
                        Next j
                    
                        tbCallout.Value = strLine
                    
                        GoTo Found_Splices
                    End If
                End If
            End If
        Next i
        
        tbCallout.Value = ""
Found_Splices:
    End If
    
    iAtt = iAtt + 1
    
    tbUnits.Value = ""
    If Not vAttList(iAtt).TextString = "" Then
        vList = Split(vAttList(iAtt).TextString, ";;")
        
        strTest = vList(0)
        If UBound(vList) > 0 Then
            For i = 0 To UBound(vList)
                strTest = strTest & vbCr & vList(i)
            Next i
        End If
        
        tbUnits.Value = strTest
    End If
    
    Me.show
End Sub

Private Sub cbInOutTap_Click()
    If lbCounts.ListCount < 1 Then Exit Sub
    
    Dim strCable, strCounts, strSpliced, strCallout As String
    Dim vLine, vItem As Variant
    'Dim iExist As Integer
    
    'iExist = 0
    Me.Hide
    Load CountsTap
        CountsTap.tbStructure.Value = tbActivePole.Value
        
        For i = 1 To lbCounts.ListCount - 1
            CountsTap.lbMain.AddItem i
            
            If lbCounts.List(i, 3) = "<>" Then
                CountsTap.lbMain.List(i - 1, 1) = lbCounts.List(i, 1)
                CountsTap.lbMain.List(i - 1, 2) = lbCounts.List(i, 2)
            Else
                CountsTap.lbMain.List(i - 1, 1) = "XD"
                CountsTap.lbMain.List(i - 1, 2) = i
            End If
            CountsTap.lbMain.List(i - 1, 3) = ""
        Next i
        
        CountsTap.show
        
        'GoTo Exit_Sub
        
        If CountsTap.cbChanged.Value = False Then GoTo Exit_Sub
        'If CountsTap.cbExisting.Value = True Then iExist = 1
        
        strLine = CountsTap.tbPosition.Value & ": " & CountsTap.cbCblType.Value & "(" & CountsTap.cbCableSize.Value & ")"
        If Not CountsTap.cbSuffix.Value = "" Then strLine = strLine & CountsTap.cbSuffix.Value
        strLine = strLine & " / " & Replace(CountsTap.tbResult.Value, vbCr, " + ")
        strLine = Replace(strLine, vbLf, "")
        
        'strLine = cable callout
        
        strSpliced = Replace(CountsTap.tbResult.Value, vbLf, "")
        vLine = Split(strSpliced, vbCr)
        strSpliced = ""
        For i = 0 To UBound(vLine)
            vItem = Split(vLine(i), ": ")
            If Not vItem(0) = "XD" Then
                If strSpliced = "" Then
                    strSpliced = vLine(i)
                Else
                    strSpliced = strSpliced & " + " & vLine(i)
                End If
            End If
        Next i
        
        strCallout = Replace(strSpliced, " + ", vbCr)
    
    Unload CountsTap
    
    Dim objEntity As AcadEntity
    Dim objBlock As AcadBlockReference
    Dim vReturnPnt, vAttList As Variant
    Dim strReplace As String
    Dim iAtt As Integer
    
    On Error Resume Next
    
    Err = 0
    ThisDrawing.Utility.GetEntity objEntity, vReturnPnt, vbCr & "Select Block:"
    If Not Err = 0 Then GoTo Exit_Sub
    
    If Not TypeOf objEntity Is AcadBlockReference Then GoTo Exit_Sub
    Set objBlock = objEntity
    
    Select Case objBlock.Name
        Case "sPole"
            iAtt = 25
        Case "sPed", "sHH", "sPanel"
            iAtt = 5
        Case Else
            GoTo Exit_Sub
    End Select
    
    vAttList = objBlock.GetAttributes
    strReplace = vAttList(0).TextString
    
    strLine = Replace(strLine, "<<???>>", strReplace)
    strCallout = Replace(strCallout, "<<???>>", strReplace)
        
    If tbCallout.Value = "" Then
        tbCallout.Value = strCallout
    Else
        tbCallout.Value = tbCallout.Value & vbCr & strCallout
    End If
    
    vAttList(iAtt).TextString = strLine
    objBlock.Update
        
    bUpdatePole = True
    
    'MsgBox strLine
    'MsgBox strCallout
    
    'Call CreateCallout
    
Exit_Sub:
    
    Me.show
End Sub

Private Sub cbNewCable_Click()
    'If cbCblType.Value = "" Then
        'MsgBox "Need Cable Type"
        'Exit Sub
    'End If
    'If cbCableSize.Value = "" Then
        'MsgBox "Need Cable Size"
        'Exit Sub
    'End If
    If tbF1Name.Value = "" Then
        MsgBox "Need F1 Name:" & vbCr & "Enter ""NA"" if no F1 counts."
        Exit Sub
    End If
    'If tbPosition.Value = "" Then
        'MsgBox "Need Cable Position"
        'Exit Sub
    'End If
    
    Dim strFileName As String
    Dim vName, vLine, vItem As Variant
    Dim fName As String
    
    Me.Hide
    Load NewCableForm
        NewCableForm.show
        
        If Not UCase(tbF1Name.Value) = "NA" Then
            vName = Split(ThisDrawing.Name, " ")
            strFileName = strSplitterFilePath & "\" & vName(0) & " Counts -" & tbF1Name.Value & ".mcl"
    
            fName = Dir(strFileName)
            If fName = "" Then
                If NewCableForm.lbCounts.ListCount < 1 Then GoTo Unload_Form
                
                For i = 0 To NewCableForm.lbCounts.ListCount - 1
                    vLine = Split(NewCableForm.lbCounts.List(i, 1), ": ")
                    
                    If vLine(0) = tbF1Name.Value Then GoTo Found_F1
                Next i
                
                MsgBox "No F1 counts found in Callout."
                GoTo Unload_Form
                
Found_F1:
                    
                vItem = Split(vLine(1), "-")
                
                Open strFileName For Output As #1
        
                Print #1, tbF1Name.Value & " F1 COUNTS"
        
                For i = 1 To CInt(vItem(1))
                    Print #1, i & vbTab & "<>" & vbTab & "<>" & vbTab & "<>" & vbTab & "<>" & vbTab & "<>"
                Next i
        
                Close #1
            End If
        End If
Unload_Form:
    Unload NewCableForm
    
    Call GetActivePole
    
    Dim objEntity As AcadEntity
    Dim objTemp As AcadBlockReference
    Dim vReturnPnt, vList As Variant
    
    On Error Resume Next
    Err = 0
    ThisDrawing.Utility.GetEntity objEntity, vReturnPnt, vbCr & "Select Source Block: "
    If Not Err = 0 Then
        MsgBox "Data not added to block!"
        Me.show
        Exit Sub
    End If
    
    If TypeOf objEntity Is AcadBlockReference Then
        Set objTemp = objEntity
    Else
        MsgBox "Data not added to block!"
        Me.show
        Exit Sub
    End If
    
    vList = objTemp.GetAttributes
    strPreviousBlock = vList(0).TextString
    
    Call EnableAll
    
    Call AutoFiber
    
    Call CreateCallout
    
    Dim vText As Variant
    Dim strLine As String
    
    vText = Split(tbCblCallout.Value, vbCr)
    For i = 0 To UBound(vText)
        vLine = Split(vText(i), ": ")
        If InStr(vLine(0), "XD") > 0 Then
            vText(i) = vLine(0) & ": " & vLine(1) & ": END"
        End If
    Next i
    
    strLine = vText(0)
    If UBound(vText) > 0 Then
        For i = 1 To UBound(vText)
            strLine = strLine & vbCr & vText(i)
        Next i
    End If
    
    tbCblCallout.Value = strLine
    
    Call UpdateCable
    
    cbGetPole.Enabled = True
    cbAddToPole.Enabled = True
    cbNewCable.Enabled = False
    cbExistingCable.Enabled = False
    
    Me.show
    
End Sub

Private Sub cbQuit_Click()
    Me.Hide
    
    Dim result As Integer
    
    If bSave = True Then
        result = MsgBox("Save changes to Master List?", vbYesNo, "Save Changes")
        If result = vbYes Then
            Call UpdateTerminal
            Call SaveAll
            bSave = False
        End If
    End If
    
    
    If bUpdatePole = True Then
        result = MsgBox("Save changes to Current Pole?", vbYesNo, "Save Changes")
        If result = vbYes Then
            Call UpdateCableCallout
            Call UpdateTerminal
        End If
    End If
    
End Sub

Private Sub cbRefresh_Click()
    Me.Repaint
End Sub

Private Sub cbRemoveWL_Click()
    If lbCounts.ListIndex < 0 Then Exit Sub
    
    Dim iIndex As Integer
    
    iIndex = lbCounts.ListIndex
    
    lbCounts.List(iIndex, 3) = "<>"
    lbCounts.List(iIndex, 4) = "<>"
    lbCounts.List(iIndex, 5) = "<>"
    lbCounts.List(iIndex, 6) = "<>"
    lbCounts.List(iIndex, 7) = "<>"
    
    If Not iIndex = 0 Then lbCounts.ListIndex = iIndex - 1
End Sub

Private Sub cbSaveSplitter_Click()
    Call SaveAll
End Sub

Private Sub cbSplitter_Click()
    'GoTo Skip_This
    
    Dim vLine As Variant
    Dim iIndex, iCIndex As Integer
    Dim strF1 As String
    Dim vAttList As Variant
    Dim vItem, vCounts, vTemp As Variant
    'Dim strCount(2) As String
    Dim strPrevious, strCurrent As String
    Dim strLine, strItem, strCallout As String
    Dim strMessage As String
    Dim iAtt, iCount, iFiber As Integer
    Dim iStart, iEnd As Integer
    
    strF1 = ""
    For i = 0 To lbCounts.ListCount - 1
        If lbCounts.Selected(i) = True Then
            strF1 = lbCounts.List(i, 1) & ": " & lbCounts.List(i, 2)
            iCIndex = i
            GoTo Found_F1
        End If
    Next i
    
    MsgBox "No fiber selected."
    Exit Sub
    
Found_F1:
    
    Me.Hide
    
    Load CountsSplitter
        CountsSplitter.tbActivePole.Value = tbActivePole.Value
        CountsSplitter.tbSplice.Value = strF1
        CountsSplitter.tbF2Name.Value = Replace(strF1, ": ", "-")
        'If Not strF1 = "" Then CountsSplitter.tbF2Name.Value = Replace(strF1, ": ", "-")
        
        CountsSplitter.show
        
        If CountsSplitter.cbChanged.Value = False Then GoTo Exit_Sub
        
        tbSplitterName.Value = CountsSplitter.tbSplitterName.Value
        
        '<----------------------------------------Add Splices to callout
        If tbCallout.Value = "" Then
            tbCallout.Value = CountsSplitter.tbResult.Value
        Else
            tbCallout.Value = tbCallout.Value & vbCr & CountsSplitter.tbResult.Value
        End If
        
        '<----------------------------------------Add Spliced Fibers to cable
        'If CountsSplitter.iExisting = 0 Then
            For i = 0 To CountsSplitter.lbMain.ListCount - 1
                If Left(CountsSplitter.lbMain.List(i, 3), 2) = "A " Then
                    vLine = Split(CountsSplitter.lbMain.List(i, 3), "A ")
                    iIndex = CInt(vLine(1))
                    
                    lbCounts.List(iIndex, 1) = CountsSplitter.lbMain.List(i, 1)
                    lbCounts.List(iIndex, 2) = CountsSplitter.lbMain.List(i, 2)
                End If
            Next i
        'End If
        
        '<----------------------------------------Assign Splitter location to cable
        'vLine = Split(CountsSplitter.tbSplice.Value, ": ")
        'For i = 0 To CountsSplitter.lbMain.ListCount - 1
            'If lbCounts.List(i, 1) = vLine(0) Then
                'If lbCounts.List(i, 2) = vLine(1) Then
                    lbCounts.List(iCIndex, 3) = CountsSplitter.tbActivePole.Value
                    lbCounts.List(iCIndex, 6) = "SPLITTER"
                    lbCounts.List(iCIndex, 7) = CountsSplitter.tbSplitterName.Value
                    
                    'GoTo Exit_Sub2
                'End If
            'End If
        'Next i
        
'Exit_Sub2:
    
        '<----------------------------------------Add counts to Backspan
        
        Select Case objBlock.Name
            Case "sPole"
                iAtt = 25
            Case "sPed", "sHH", "sFP", "sPanel"
                iAtt = 5
            Case Else
                GoTo Exit_Sub
        End Select
        
        vAttList = objBlock.GetAttributes
        vTemp = Split(vAttList(iAtt).TextString, " / ")
        strCallout = vTemp(0) & " / "
        vLine = Split(vTemp(0), ")")
        vCount = Split(vLine(0), "(")
        iCount = CInt(vCount(1))
        
        strMessage = "iCount: " & iCount & vbCr
        
        ReDim strCount(iCount) As String  '<------------ Break counts out individually into a list
        vLine = Split(vTemp(1), " + ")
        iFiber = 1
        For i = 0 To UBound(vLine)
            vItem = Split(vLine(i), ": ")
            vCount = Split(vItem(1), "-")
            iStart = CInt(vCount(0))
            If UBound(vCount) > 0 Then
                iEnd = CInt(vCount(1))
            Else
                iEnd = iStart
            End If
            
            For j = iStart To iEnd
                strCount(iFiber) = vItem(0) & ": " & j & ": " & vItem(2)
                iFiber = iFiber + 1
            Next j
        Next i
        
        For i = 0 To CountsSplitter.lbMain.ListCount - 1  '<------------ add Backspan counts
            If InStr(CountsSplitter.lbMain.List(i, 3), "B ") > 0 Then
                vLine = Split(CountsSplitter.lbMain.List(i, 3), "B ")
                iIndex = CInt(vLine(1))
                
                strLine = CountsSplitter.lbMain.List(i, 1) & ": " & CountsSplitter.lbMain.List(i, 2)
                strLine = strLine & ": " & tbActivePole.Value
                strCount(iIndex) = strLine
            End If
        Next i
        
        '<---------------------------- Need to combine them back into an attribute and save current block
        
        strLine = ""
        
        vLine = Split(strCount(1), ": ")
        strPrevious = vLine(0)
        'strCurrent = strPrevious
        iStart = CInt(vLine(1))
        iEnd = iStart
    
        For i = 2 To iCount
            vLine = Split(strCount(i), ": ")
            strCurrent = vLine(0)
        
            If strCurrent = strPrevious Then
                iEnd = CInt(vLine(1))
            Else
                strItem = strPrevious & ": " & iStart
                If iEnd > iStart Then strItem = strItem & "-" & iEnd
                strItem = strItem & ": " & tbActivePole.Value
                
                If strLine = "" Then
                    strLine = strItem
                Else
                    strLine = strLine & " + " & strItem
                End If
                
                strPrevious = strCurrent
                iStart = CInt(vLine(1))
                iEnd = iStart
            End If
        Next i
             
        strItem = strPrevious & ": " & iStart
        If iEnd > iStart Then strItem = strItem & "-" & iEnd
        
        strCallout = strCallout & strLine & " + " & strItem & ": " & tbActivePole.Value
    'MsgBox vAttList(iAtt).TextString & vbCr & strCallout
        vAttList(iAtt).TextString = strCallout
        objBlock.Update
        'tbResult.Value = strLine
    
        bUpdatePole = True
        bSave = True
    
        Call CreateCallout
        Call AddSplitter
        
Exit_Sub:
    Unload CountsSplitter
    
    Me.show
    Exit Sub
    
    
    
    
    
Skip_This:
    
    'If tbF1Name.Value = "" Then
        'MsgBox "You need to add a F1 Name"
        'tbF1Name.SetFocus
        'Exit Sub
    'End If
    
    If tbF2Name.Value = "" Then
        MsgBox "You need to add a F2 Name"
        tbF2Name.SetFocus
        Exit Sub
    End If
    
    If tbSplitterName.Value = "" Then
        MsgBox "You need to add a Splitter Location"
        tbSplitterName.SetFocus
        Exit Sub
    End If
    
    If cbSplitterSize.Value = "" Then
        MsgBox "You need to add a Splitter size"
        cbSplitterSize.SetFocus
        Exit Sub
    End If
    
    If tbSplice.Value = "" Then
        MsgBox "You need to add a Splitter splice"
        tbSplice.SetFocus
        Exit Sub
    End If
    
    If tbFFiber.Value = "" Then
        MsgBox "You need to add the From Fiber"
        tbFFiber.SetFocus
        Exit Sub
    End If
    
    If tbTFiber.Value = "" Then
        MsgBox "You need to add the To Fiber"
        tbTFiber.SetFocus
        Exit Sub
    End If
    
    Dim iSelected As Integer
    'Dim i, j As Integer
    
    For i = 0 To lbCounts.ListCount - 1
        If lbCounts.Selected(i) = True Then
            iSelected = i
            GoTo Found_Selected
        End If
    Next i
    
    MsgBox "No Count Selected."
    Exit Sub
    
Found_Selected:
    
    lbCounts.List(i, 3) = tbActivePole.Value
    lbCounts.List(i, 6) = "SPLITTER"
    lbCounts.List(i, 7) = tbSplitterName.Value
    
    If tbCallout = "" Then
        tbCallout.Value = lbCounts.List(i, 1) & ": " & lbCounts.List(i, 2)
    Else
        tbCallout.Value = tbCallout.Value & vbCr & lbCounts.List(i, 1) & ": " & lbCounts.List(i, 2)
    End If
    
    tbCallout.Value = tbCallout.Value & vbCr & tbF2Name.Value & ": 1-" & cbSplitterSize.Value
    
    '<------------------------------------------------ Update F1.mcl
    
    j = 1
    
    For i = CInt(tbFFiber.Value) To CInt(tbTFiber.Value)
        lbCounts.List(i, 1) = tbF2Name.Value
        lbCounts.List(i, 2) = j
        lbCounts.List(i, 3) = "<>"
        lbCounts.List(i, 4) = "<>"
        lbCounts.List(i, 5) = "<>"
        lbCounts.List(i, 6) = "<>"
        lbCounts.List(i, 7) = "<>"
        
        j = j + 1
    Next i
    
    lbCounts.ListIndex = CInt(tbTFiber.Value)
    lbCounts.Selected(CInt(tbTFiber.Value)) = True
    
    Call CreateCallout
    
    Call AddSplitter
    
    Call SaveAll
    'Call SaveF1
    
    bUpdatePole = True
    bSave = True
End Sub

Private Sub cbSplitterSize_Change()
    Call AutoFiber
End Sub

Private Sub cbTerminal_Click()
    If objBlock Is Nothing Then
        MsgBox "No Pole Selected"
        Exit Sub
    End If
    
    Dim iSelected As Integer
    
    For i = 0 To lbCounts.ListCount - 1
        If lbCounts.Selected(i) = True Then
            iSelected = i
            GoTo Found_Selected
        End If
    Next i
    
    MsgBox "No Count Selected."
    Exit Sub
    
Found_Selected:
    Dim result As Integer
    
    If Not lbCounts.List(i, 3) = "<>" Then
        
        result = MsgBox("Overwrite previous assignment?", vbYesNo, "Fiber Assigned!")
        If result = vbNo Then Exit Sub
    End If
    
    Dim objEntity As AcadEntity
    Dim objRES As AcadBlockReference
    Dim vAttList, vBasePnt As Variant
    Dim strLine As String
    Dim strName As String
    Dim iBCount, iECount As Integer
    
    iBCount = 0: iECount = 0
    
    Me.Hide
    On Error Resume Next
    
Next_One:
    
    Err = 0
    ThisDrawing.Utility.GetEntity objEntity, vBasePnt, "Select Building: "
    If Not Err = 0 Then GoTo Exit_Sub
    
    If Not lbCounts.List(iSelected, 3) = "<>" Then
        
        result = MsgBox("Overwrite previous assignment?", vbYesNo, "Fiber Assigned!")
        If result = vbNo Then Exit Sub
    End If
    
    If TypeOf objEntity Is AcadBlockReference Then
        Set objRES = objEntity
        vAttList = objRES.GetAttributes
            
        Select Case objRES.Name
            'Case "RES", "BUSINESS", "MDU", "TRLR", "SCHOOL", "CHURCH", "LOT"
            Case "SG"
                lbCounts.List(iSelected, 3) = tbActivePole.Value
                lbCounts.List(iSelected, 4) = "SG"
                lbCounts.List(iSelected, 5) = vAttList(1).TextString
                lbCounts.List(iSelected, 6) = "SMARTGRID"
                lbCounts.List(iSelected, 7) = vAttList(0).TextString
                
                strLine = lbCounts.List(iSelected, 1) & ": " & lbCounts.List(iSelected, 2)
                'If cbDrop.Value = False Then strline = "(" & strline & ")"
                vAttList(2).TextString = tbActivePole.Value & " - " & strLine
                objRES.Update
                
                strName = lbCounts.List(iSelected, 1)
                If iECount = 0 Then
                    iECount = CInt(lbCounts.List(iSelected, 2))
                Else
                    iBCount = CInt(lbCounts.List(iSelected, 2))
                End If
                
                
            Case "Customer"
                lbCounts.List(iSelected, 3) = tbActivePole.Value
                lbCounts.List(iSelected, 4) = vAttList(1).TextString
                lbCounts.List(iSelected, 5) = vAttList(2).TextString
                lbCounts.List(iSelected, 6) = vAttList(0).TextString
                If vAttList(3).TextString = "" Then
                    lbCounts.List(iSelected, 7) = "<>"
                Else
                    lbCounts.List(iSelected, 7) = vAttList(3).TextString
                End If
                
                strLine = lbCounts.List(iSelected, 1) & ": " & lbCounts.List(iSelected, 2)
                If cbDrop.Value = False Then strLine = "(" & strLine & ")"
                vAttList(4).TextString = tbActivePole.Value & " - " & strLine
                objRES.Update
                
                strName = lbCounts.List(iSelected, 1)
                If iECount = 0 Then
                    iECount = CInt(lbCounts.List(iSelected, 2))
                Else
                    iBCount = CInt(lbCounts.List(iSelected, 2))
                End If
        End Select
    End If
    
    iSelected = iSelected - 1
    
    GoTo Next_One
    
Exit_Sub:
    lbCounts.ListIndex = iSelected
    
    If iECount > 0 Then
        If iBCount = 0 Then
            strName = strName & ": " & iECount
        Else
            strName = strName & ": " & iBCount & "-" & iECount
        End If
        
        strName = strName & ": " & strPreviousBlock
        
        If tbCallout.Value = "" Then
            tbCallout.Value = strName
        Else
            tbCallout.Value = tbCallout.Value & vbCr & strName
        End If
    End If
    
    bUpdatePole = True
    bSave = True
    
    Call CreateCallout
    
    Call UpdateTerminalCallout
    
    Me.show
End Sub

Private Sub cbUpdateCblCO_Click()
    Dim vAttList As Variant
    
    vAttList = objBlock.GetAttributes
    
End Sub

Private Sub cbUpdateCO_Click()
    Call CreateCallout
End Sub

Private Sub cbUpdateHO1_Click()
    Call UpdateTerminalCallout
End Sub

Private Sub Label24_Click()
    If lbCounts.ListIndex < 0 Then Exit Sub
    
    tbF2Name.Value = tbF2Name.Value & "-" & lbCounts.List(lbCounts.ListIndex, 2)
End Sub

Private Sub Label26_Click()
    Dim objEntity As AcadEntity
    Dim objRES As AcadBlockReference
    Dim vAttList, vBasePnt As Variant
    Dim strName As String
    
    Me.Hide
    On Error Resume Next
    
    Err = 0
    ThisDrawing.Utility.GetEntity objEntity, vBasePnt, "Select Building: "
    If Not Err = 0 Then GoTo Exit_Sub
    
    If TypeOf objEntity Is AcadBlockReference Then
        Set objRES = objEntity
        vAttList = objRES.GetAttributes
            
        Select Case objRES.Name
            'Case "RES", "BUSINESS", "MDU", "TRLR", "SCHOOL", "CHURCH", "LOT"
                'tbSplitterName.Value = vAttList(0).TextString & " " & vAttList(1).TextString
            Case "Customer"
                strName = vAttList(1).TextString & " " & vAttList(2).TextString
                tbSplitterName.Value = Replace(strName, "  ", " ")
        End Select
        'Set objRES = Nothing
    End If
    
Exit_Sub:
    Me.show
End Sub

Private Sub LabelPan_Click()
    Dim entPole As AcadObject
    Dim basePnt As Variant
    
    Me.Hide
  On Error Resume Next
    
    ThisDrawing.Utility.GetEntity entPole, basePnt, "Left Click to Exit: "
    
    Me.show
End Sub

Private Sub lbCounts_Click()
    tbSplice.Value = lbCounts.List(lbCounts.ListIndex, 1) & ": " & lbCounts.List(lbCounts.ListIndex, 2)
End Sub

Private Sub lbCounts_DblClick(ByVal Cancel As MSForms.ReturnBoolean)
    Dim strLine As String
    Dim iIndex As Integer
    
    iIndex = lbCounts.ListIndex
    
    strLine = "Fiber: " & vbTab & lbCounts.List(iIndex, 0) & vbCr
    strLine = strLine & lbCounts.List(iIndex, 1) & ": " & lbCounts.List(iIndex, 2) & vbCr & vbCr
    strLine = strLine & "Pole: " & vbTab & lbCounts.List(iIndex, 3) & vbCr & vbCr
    strLine = strLine & "Address:  " & lbCounts.List(iIndex, 4) & " " & lbCounts.List(iIndex, 5) & vbCr
    strLine = strLine & "Type: " & vbTab & lbCounts.List(iIndex, 6) & vbCr & vbCr
    strLine = strLine & "Note: " & vbTab & lbCounts.List(iIndex, 7)
    
    MsgBox strLine
End Sub

Private Sub lbCounts_KeyDown(ByVal KeyCode As MSForms.ReturnInteger, ByVal Shift As Integer)
    Select Case KeyCode
        Case vbKeyF1
            tbF1Name.Value = lbCounts.List(lbCounts.ListIndex, 1)
        Case vbKeyF2
            tbF2Name.Value = lbCounts.List(lbCounts.ListIndex, 1) & "-" & lbCounts.List(lbCounts.ListIndex, 2)
        Case vbKeyDelete
            lbCounts.List(lbCounts.ListIndex, 3) = "<>"
            lbCounts.List(lbCounts.ListIndex, 4) = "<>"
            lbCounts.List(lbCounts.ListIndex, 5) = "<>"
            lbCounts.List(lbCounts.ListIndex, 6) = "<>"
            lbCounts.List(lbCounts.ListIndex, 7) = "<>"
    End Select
End Sub

Private Sub tbActivePole_Change()
    tbPoleNumber.Value = tbActivePole.Value
End Sub

Private Sub tbF1Name_Change()
    'tbF2Name.Value = tbF1Name.Value & "-"
End Sub

Private Sub tbSplice_Exit(ByVal Cancel As MSForms.ReturnBoolean)
    tbF2Name.Value = Replace(tbSplice.Value, ": ", "-")
End Sub

Private Sub UserForm_Initialize()
    cbCblType.AddItem "CO"
    cbCblType.AddItem "BFO"
    cbCblType.AddItem "UO"
    cbCblType.Value = "CO"
    
    cbSuffix.AddItem ""
    cbSuffix.AddItem "E"
    cbSuffix.AddItem "6M-EHS"
    cbSuffix.AddItem "6M"
    cbSuffix.AddItem "10M"
    'cbSuffix.Value = "6M"
    
    cbScale.AddItem "50"
    cbScale.AddItem "75"
    cbScale.AddItem "100"
    cbScale.Value = "100"
    
    cbCableSize.AddItem "12"
    cbCableSize.AddItem "24"
    cbCableSize.AddItem "36"
    cbCableSize.AddItem "48"
    cbCableSize.AddItem "72"
    cbCableSize.AddItem "96"
    cbCableSize.AddItem "144"
    cbCableSize.AddItem "216"
    cbCableSize.AddItem "288"
    cbCableSize.AddItem "360"
    cbCableSize.AddItem "432"
    
    cbPlacement.AddItem "Leader"
    cbPlacement.AddItem "Away"
    cbPlacement.Value = "Leader"
    
    cbSplitterSize.AddItem "2"
    cbSplitterSize.AddItem "4"
    cbSplitterSize.AddItem "8"
    cbSplitterSize.AddItem "16"
    cbSplitterSize.AddItem "32"
    cbSplitterSize.AddItem "64"
    
    lbCounts.Clear
    lbCounts.ColumnCount = 8
    lbCounts.ColumnWidths = "24;72;30;66;36;136;48;96"
    
    bSave = 0
    bUpdatePole = 0
    
    strSplitterFilePath = LCase(ThisDrawing.Path)
End Sub

Private Sub EnableAll()
    cbCutCounts.Enabled = True
    cbTerminal.Enabled = True
    cbDrop.Enabled = True
    cbAddClosure.Enabled = True
    cbCallout.Enabled = True
    cbSplitter.Enabled = True
    cbUpdateHO1.Enabled = True
End Sub

Private Sub DisableAll()
    cbCutCounts.Enabled = False
    cbTerminal.Enabled = False
    cbDrop.Enabled = False
    cbAddClosure.Enabled = False
    cbCallout.Enabled = False
    cbSplitter.Enabled = False
    cbUpdateHO1.Enabled = False
End Sub

Private Sub CreateCallout()
    If lbCounts.ListCount < 1 Then Exit Sub
    
    Dim vList As Variant
    Dim strCurrent, strPrevious As String
    Dim strList, strLine As String
    Dim iFiber, iStart, iEnd As Integer
    
    tbCblCallout.Value = ""
    strLine = ""
    'strPrevious = ""
    
    strPrevious = lbCounts.List(1, 1)
    If Not lbCounts.List(1, 3) = "<>" Then
        strPrevious = tbXD.Value
        iStart = CInt(lbCounts.List(1, 0))
    Else
        iStart = CInt(lbCounts.List(1, 2))
    End If
    
    For i = 2 To lbCounts.ListCount - 1
        strCurrent = lbCounts.List(i, 1)
        
        If Not lbCounts.List(i, 3) = "<>" Then strCurrent = tbXD.Value
        
        If strCurrent = strPrevious Then
            If Not CInt(lbCounts.List(i, 2)) = CInt(lbCounts.List(i - 1, 2)) + 1 Then
                If Not lbCounts.List(i - 1, 3) = "<>" Then
                    iEnd = CInt(lbCounts.List(i - 1, 0))
                Else
                    iEnd = CInt(lbCounts.List(i - 1, 2))
                End If
        
                If iStart = iEnd Then
                    strPrevious = strPrevious & ": " & iEnd & ": " & tbActivePole.Value
                Else
                    strPrevious = strPrevious & ": " & iStart & "-" & iEnd & ": " & tbActivePole.Value
                End If
            
                If strLine = "" Then
                    strLine = strPrevious
                Else
                    strLine = strLine & vbCr & strPrevious
                End If
            
                If strCurrent = tbXD.Value Then
                    iStart = CInt(lbCounts.List(i, 0))
                Else
                    iStart = CInt(lbCounts.List(i, 2))
                End If
            
                strPrevious = strCurrent
            End If
        Else
            'MsgBox strCurrent & vbCr & strPrevious
            
            'iEnd = CInt(lbCounts.List(i - 1, 2))
        
            If Not lbCounts.List(i - 1, 3) = "<>" Then
                iEnd = CInt(lbCounts.List(i - 1, 0))
            Else
                iEnd = CInt(lbCounts.List(i - 1, 2))
            End If
        
            If iStart = iEnd Then
                strPrevious = strPrevious & ": " & iEnd & ": " & tbActivePole.Value
            Else
                strPrevious = strPrevious & ": " & iStart & "-" & iEnd & ": " & tbActivePole.Value
            End If
            
            If strLine = "" Then
                strLine = strPrevious
            Else
                strLine = strLine & vbCr & strPrevious
            End If
            
            If strCurrent = tbXD.Value Then
                iStart = CInt(lbCounts.List(i, 0))
            Else
                iStart = CInt(lbCounts.List(i, 2))
            End If
            
            strPrevious = strCurrent
        End If
    Next i
    
    iEnd = CInt(lbCounts.List(lbCounts.ListCount - 1, 2))
    strLine = strLine & vbCr & strCurrent & ": " & iStart & "-" & iEnd & ": " & tbActivePole.Value
    
    tbCblCallout = strLine
    'Me.Repaint
End Sub

Private Sub SaveAll()
    Dim strFileName, strText As String
    Dim vName, vLine, vItem, vList As Variant
    Dim vText As Variant
    Dim strLine, strList As String
    Dim fName As String
    Dim iIndex As Integer
    
    strList = ""
    For i = 0 To lbCounts.ListCount - 1
        If Not lbCounts.List(i, 1) = "XD" Then
            If lbCounts.List(i, 6) = "" Then GoTo Next_I
            If lbCounts.List(i, 6) = "TAP" Then GoTo Next_I
            
            If strList = "" Then
                strList = lbCounts.List(i, 1)
            Else
                vLine = Split(strList, ";;")
                For j = 0 To UBound(vLine)
                    If vLine(j) = lbCounts.List(i, 1) Then GoTo Found_Name
                Next j
                
                strList = strList & ";;" & lbCounts.List(i, 1)
Found_Name:
            End If
        End If
Next_I:
    Next i
    
    If strList = "" Then Exit Sub
    
    vList = Split(strList, ";;")
    For n = 0 To UBound(vList)
        vName = Split(ThisDrawing.Name, " ")
        strFileName = strSplitterFilePath & "\" & vName(0) & " Counts -" & vList(n) & ".mcl"
    
        fName = Dir(strFileName)
        If fName = "" Then
            MsgBox "No MCL file for  " & vList(n) & "."
            GoTo Next_N
        End If
        
        Open strFileName For Input As #1
        strText = Input(LOF(1), 1)
        Close #1
        
        strText = Replace(strText, vbLf, "")
        vText = Split(strText, vbCr)
        
        For i = 0 To lbCounts.ListCount - 1
            If lbCounts.List(i, 1) = vList(n) Then
                strLine = lbCounts.List(i, 2)
                If lbCounts.List(i, 6) = "TAP" Then
                    strLine = strLine & vbTab & "<>" & vbTab & "<>" & vbTab & "<>" & vbTab & "<>" & vbTab & "<>" & vbTab & "<>"
                Else
                    If lbCounts.List(i, 3) = "" Or lbCounts.List(i, 3) = "<>" Then
                        strLine = strLine & vbTab & tbActivePole.Value
                    Else
                        strLine = strLine & vbTab & lbCounts.List(i, 3)
                    End If
                    If lbCounts.List(i, 4) = "" Then
                        strLine = strLine & vbTab & "<>"
                    Else
                        strLine = strLine & vbTab & lbCounts.List(i, 4)
                    End If
                    If lbCounts.List(i, 5) = "" Then
                        strLine = strLine & vbTab & "<>"
                    Else
                        strLine = strLine & vbTab & lbCounts.List(i, 5)
                    End If
                    If lbCounts.List(i, 6) = "" Then
                        strLine = strLine & vbTab & "<>"
                    Else
                        strLine = strLine & vbTab & lbCounts.List(i, 6)
                    End If
                    If lbCounts.List(i, 7) = "" Then
                        strLine = strLine & vbTab & "<>"
                    Else
                        strLine = strLine & vbTab & lbCounts.List(i, 7)
                    End If
                End If
                
                For j = 0 To UBound(vText)
                    vItem = Split(vText(j), vbTab)
                    If vItem(0) = lbCounts.List(i, 2) Then
                        vText(j) = strLine
                        GoTo Found_Line
                    End If
                Next j
Found_Line:
                
            End If
        Next i
        
        strText = vText(0)
        If UBound(vText) > 0 Then
            For j = 1 To UBound(vText)
                If Not vText(j) = "" Then strText = strText & vbCr & vText(j)
            Next j
        End If
        
    
        Open strFileName For Output As #2
    
        'Print #2, vList(n) '& " " & tbSplitterName.Value
        Print #2, strText
    
        Close #2
Next_N:
    Next n
    
    bSave = False
End Sub

Private Sub SaveF1()
    Dim strFileName As String
    Dim vName, vLine, vItem As Variant
    Dim strLine As String
    Dim fName As String
    Dim iIndex As Integer
    
    vName = Split(ThisDrawing.Name, " ")
    strFileName = strSplitterFilePath & "\" & vName(0) & " Counts -" & tbF1Name.Value & ".mcl"
    
    fName = Dir(strFileName)
    If fName = "" Then
        MsgBox "No F1 File found."
        Exit Sub
    End If
    
    Load CountFileView
    
    Open strFileName For Input As #2
    
    Line Input #2, strLine
    
    While Not EOF(2)
        Line Input #2, strLine
        vLine = Split(strLine, vbTab)
        
        CountFileView.lbCounts.AddItem vLine(0)
        iIndex = CountFileView.lbCounts.ListCount - 1
        
        CountFileView.lbCounts.List(iIndex, 1) = vLine(1)
        CountFileView.lbCounts.List(iIndex, 2) = vLine(2)
        CountFileView.lbCounts.List(iIndex, 3) = vLine(3)
        CountFileView.lbCounts.List(iIndex, 4) = vLine(4)
        CountFileView.lbCounts.List(iIndex, 5) = vLine(5)
    Wend
    
    Close #2
    
    For i = 0 To lbCounts.ListCount - 1
        If lbCounts.List(i, 1) = tbF1Name.Value Then
            iIndex = CInt(lbCounts.List(i, 2)) - 1
            
            CountFileView.lbCounts.List(iIndex, 1) = lbCounts.List(i, 3)
            'CountFileView.show
            CountFileView.lbCounts.List(iIndex, 2) = lbCounts.List(i, 4)
            CountFileView.lbCounts.List(iIndex, 3) = lbCounts.List(i, 5)
            CountFileView.lbCounts.List(iIndex, 4) = lbCounts.List(i, 6)
            CountFileView.lbCounts.List(iIndex, 5) = lbCounts.List(i, 7)
        End If
    Next i
    
    'Me.hide
    CountFileView.show
    'Me.show
    
    Open strFileName For Output As #3
    
    Print #3, tbF1Name.Value & " F1 COUNTS"
    
    For i = 0 To CountFileView.lbCounts.ListCount - 1
        strLine = ""
        
        strLine = CountFileView.lbCounts.List(i, 0)
        If CountFileView.lbCounts.List(i, 1) = " " Then
            strLine = strLine & vbTab & vbTab & vbTab & vbTab & vbTab
            GoTo Next_I
        End If
        
        strLine = strLine & vbTab & CountFileView.lbCounts.List(i, 1)
        strLine = strLine & vbTab & CountFileView.lbCounts.List(i, 2)
        strLine = strLine & vbTab & CountFileView.lbCounts.List(i, 3)
        strLine = strLine & vbTab & CountFileView.lbCounts.List(i, 4)
        strLine = strLine & vbTab & CountFileView.lbCounts.List(i, 5)
        
Next_I:
        Print #3, strLine
    Next i
    
    Close #3
    
    Unload CountFileView
    
    'bSave = False
End Sub

Private Sub GetSpliced(strName As String)
    Dim vName, vFile As Variant
    Dim vLine As Variant
    Dim iIndex As Integer
    
    vName = Split(ThisDrawing.Name, " ")
    strFileName = strSplitterFilePath & "\" & vName(0) & " Counts -" & strName & ".mcl"

    fName = Dir(strFileName)
    If fName = "" Then
        MsgBox strFileName & vbCr & "not found."
        Exit Sub
    End If

    Open strFileName For Input As #1

    vFile = Split(Input$(LOF(1), 1), vbCrLf)
    Close #1
    
    For i = 1 To lbCounts.ListCount - 1
        If lbCounts.List(i, 1) = strName Then
            iIndex = CInt(lbCounts.List(i, 2))
            
            vLine = Split(vFile(iIndex), vbTab)
            lbCounts.List(i, 3) = vLine(1)
            If vLine(4) = "<>" Then lbCounts.List(i, 3) = "<>"
            lbCounts.List(i, 4) = vLine(2)
            lbCounts.List(i, 5) = vLine(3)
            lbCounts.List(i, 6) = vLine(4)
            lbCounts.List(i, 7) = vLine(5)
        End If
    Next i
End Sub

Private Sub GetActivePole()
    Dim objEntity As AcadEntity
    Dim vBasePnt As Variant
    Dim vAttList As Variant
    
  On Error Resume Next
    
    ThisDrawing.Utility.GetEntity objEntity, vBasePnt, "Select Pole: "
    If TypeOf objEntity Is AcadBlockReference Then
        Set objBlock = objEntity
    Else
        MsgBox "Not a valid object."
        Exit Sub
    End If
    
    Select Case objBlock.Name
        Case "sPed", "sHH", "sPole", "sPanel", "sMH"
        Case Else
            MsgBox "Not a valid block."
            Exit Sub
    End Select
    
    vAttList = objBlock.GetAttributes
    
    If Not tbActivePole.Value = vAttList(0).TextString Then
        strPreviousBlock = tbActivePole.Value
        tbActivePole.Value = vAttList(0).TextString
    End If
End Sub

Private Sub AutoFiber()
    If cbSplitterSize.Value = "" Then Exit Sub
    If cbCableSize.Value = "" Then Exit Sub
    If lbCounts.ListCount < 1 Then Exit Sub
    
    Dim iSize, iSPL, iDiff As Integer
    
    iSize = CInt(cbCableSize.Value)
    iSPL = CInt(cbSplitterSize.Value)
    iDiff = iSPL
    
    While iDiff > 12
        iDiff = iDiff - 12
    Wend
    
    iDiff = 12 - iDiff
    
    tbFFiber.Value = iSize - iSPL - iDiff + 1
    tbTFiber.Value = iSize - iDiff
End Sub

Private Sub UpdateCable()
    If tbActivePole.Value = "" Then
        MsgBox "Need to select Active Pole."
        Call GetActivePole
    End If
    
    Dim vAttList As Variant
    Dim vLine, vCable, vItem As Variant
    Dim strAttList As String
    Dim strLine, strFind As String
    Dim strCallout, strTemp As String
    Dim strReplace As String
    Dim result, iPosition As Integer
    Dim iAtt As Integer
    
    Select Case objBlock.Name
        Case "sPole"
            iAtt = 25
        Case Else
            iAtt = 5
    End Select
    
    iPosition = -1
    'strReplace = ": " & strPreviousBlock & " + "
    
    'strCallout = Replace(tbCblCallout.Value, vbLf, strReplace)
    strCallout = Replace(tbCblCallout.Value, vbLf, " + ")
    strCallout = Replace(strCallout, vbCr, "")
    
    strLine = tbPosition.Value & ": " & cbCblType.Value & "(" & cbCableSize.Value & ")"
    If Not cbSuffix.Value = "" Then strLine = strLine & cbSuffix.Value
    strLine = strLine & " / " & strCallout
    
    strCableCallout = strLine
    
    strFind = ""
    vAttList = objBlock.GetAttributes
    
    
    If vAttList(iAtt).TextString = "" Then
        vAttList(iAtt).TextString = strLine
    Else
        strTemp = Replace(vAttList(iAtt).TextString, vbLf, "")
        vLine = Split(strTemp, vbCr)
        For i = 0 To UBound(vLine)
            vCable = Split(vLine(0), ": ")
            If vCable(0) = tbPosition.Value Then
                iPosition = i
            End If
        Next i
        
        Select Case iPosition
            Case Is < 0
                vAttList(iAtt).TextString = vAttList(iAtt).TextString & vbCr & strLine
            Case Else
                strFind = vLine(iPosition)
                vAttList(iAtt).TextString = Replace(vAttList(iAtt).TextString, strFind, strLine)
        End Select
        
    End If
    
    objBlock.Update
    
    bUpdatePole = False
End Sub

Private Sub UpdateTerminal()
    If tbCallout.Value = "" Then Exit Sub
    
    Dim strLine As String
    
    strLine = Replace(tbCallout.Value, vbTab, "")
    strLine = Replace(strLine, vbCr, "")
    strLine = Replace(strLine, vbLf, "")
    strLine = Replace(strLine, vbCrLf, "")
    strLine = Replace(strLine, " ", "")
    
    If Len(strLine) < 3 Then Exit Sub
    
    strLine = tbCallout.Value
    
    If tbActivePole.Value = "" Then
        MsgBox "Need to select Active Pole."
        Call GetActivePole
    End If
    
    Dim vAttList, vLine, vItem As Variant
    Dim strPosition, strSpliced As String
    Dim iAtt As Integer
    
    Select Case objBlock.Name
        Case "sPole"
            iAtt = 26
        Case Else
            iAtt = 6
    End Select
    
    vAttList = objBlock.GetAttributes
    strSpliced = Replace(vAttList(iAtt).TextString, vbLf, "")
    
    strPosition = "[" & tbPosition.Value & "]"
    
    strLine = Replace(tbCallout.Value, vbCr, "")
    vLine = Split(strLine, vbLf)
    
    Dim strText As String
    Dim iTest As Integer
    iTest = 0
    For i = 0 To UBound(vLine)
        If Not vLine(i) = "" Then
            iTest = 1
            If strText = "" Then
                strText = vLine(i)
            Else
                strText = strText & " + " & vLine(i)
            End If
        End If
    Next i
    If iTest = 0 Then Exit Sub
    
    strLine = strPosition & " " & strText
    
    'If UBound(vLine) > 0 Then
        'For i = 1 To UBound(vLine)
            'strLine = strLine & " + " & vLine(i)
        'Next i
    'End If
    
    If strSpliced = "" Then
        vAttList(iAtt).TextString = strLine
    Else
        vLine = Split(strSpliced, vbCr)
        
        For i = 0 To UBound(vLine)
            If InStr(vLine(i), strPosition) > 0 Then
                vLine(i) = strLine
                GoTo Replaced_Position
            End If
        Next i
        
        vLine(UBound(vLine)) = vLine(UBound(vLine)) & vbCr & strLine
        
Replaced_Position:
        
        strSpliced = vLine(0)
        
        If UBound(vLine) > 0 Then
            For i = 1 To UBound(vLine)
                strSpliced = strSpliced & vbCr & vLine(i)
            Next i
        End If
        
        vAttList(iAtt).TextString = strSpliced
    End If
    
    objBlock.Update
    
    bUpdatePole = False
End Sub

Private Sub UpdateTerminalCallout()
    Dim objSSTemp4 As AcadSelectionSet
    Dim entItem As AcadEntity
    Dim objTemp As AcadBlockReference
    Dim vAttList As Variant
    Dim filterType, filterValue As Variant
    Dim grpCode(0) As Integer
    Dim grpValue(0) As Variant
    
    Dim strSearch As String
    Dim strAtt0, strAtt1, strAtt2 As String
    Dim strLayer, strCounts, strTemp As String
    Dim iHO1 As Integer
    
    strSearch = tbActivePole.Value & ": " & tbPosition.Value

    grpCode(0) = 2
    grpValue(0) = "Callout"
    filterType = grpCode
    filterValue = grpValue
    
  On Error Resume Next
    
    Set objSSTemp4 = ThisDrawing.SelectionSets.Add("objSSTemp4")
    If Not Err = 0 Then
        Set objSSTemp4 = ThisDrawing.SelectionSets.Item("objSSTemp4")
        Err = 0
    End If
    
    objSSTemp4.Select acSelectionSetAll, , , filterType, filterValue
    
    For Each objTemp In objSSTemp4
        vAttList = objTemp.GetAttributes
        
        If vAttList(0).TextString = strSearch Then
            If InStr(vAttList(1).TextString, "+HO1") > 0 Then
                
                'strAtt0 = tbActivePole.Value & ": " & tbPosition.Value
    
                iHO1 = 0
                strCounts = Replace(tbCallout.Value, vbLf, "")
                vCounts = Split(strCounts, vbCr)
                strCounts = ""
    
                For i = 0 To UBound(vCounts)
                    vLine = Split(vCounts(i), ": ")
                    vItem = Split(vLine(1), "-")
                    
                    strTemp = vLine(0) & ": " & vLine(1)
                    If strCounts = "" Then
                        strCounts = strTemp
                    Else
                        strCounts = strCounts & "\P" & strTemp
                    End If
        
                    If UBound(vItem) = 0 Then
                        iHO1 = iHO1 + 1
                    Else
                        iHO1 = iHO1 + CInt(vItem(1)) - CInt(vItem(0)) + 1
                    End If
                Next i
    
                If cbCblType.Value = "CO" Then
                    strAtt1 = "+HO1A=" & iHO1
                    strLayer = "Integrity Proposed-Aerial"
                Else
                    strAtt1 = "+HO1B=" & iHO1
                    strLayer = "Integrity Proposed-Buried"
                End If
    
                'strAtt2 = Replace(tbCallout.Value, vbCr, "\P")
                'strAtt2 = Replace(strAtt2, vbLf, "")
                
                
                'vAttList(0).TextString = strAtt0
                vAttList(1).TextString = strAtt1
                vAttList(2).TextString = strCounts
                vAttList(2).TextString = strAtt2
            
                objTemp.Update
                
                Call UpdateTerminal
                
                GoTo Exit_Sub
            End If
        End If
    Next objTemp
    
    'MsgBox "Callout not found."
    
Exit_Sub:
    objSSTemp4.Clear
    objSSTemp4.Delete
End Sub

Private Sub UpdateCableCallout()
    Dim objSSTemp4 As AcadSelectionSet
    Dim entItem As AcadEntity
    Dim objTemp As AcadBlockReference
    Dim vAttList, vPoleAtt As Variant
    Dim filterType, filterValue As Variant
    Dim grpCode(0) As Integer
    Dim grpValue(0) As Variant
    
    Dim vCounts, vLine As Variant
    
    Dim strSearch As String
    Dim strAtt0, strAtt1, strAtt2 As String
    Dim strLayer, strCounts, strTemp As String
    Dim iHO1 As Integer
    
    strSearch = tbActivePole.Value & ": " & tbPosition.Value

    grpCode(0) = 2
    grpValue(0) = "Callout"
    filterType = grpCode
    filterValue = grpValue
    
  On Error Resume Next
    
    Set objSSTemp4 = ThisDrawing.SelectionSets.Add("objSSTemp4")
    If Not Err = 0 Then
        Set objSSTemp4 = ThisDrawing.SelectionSets.Item("objSSTemp4")
        Err = 0
    End If
    
    objSSTemp4.Select acSelectionSetAll, , , filterType, filterValue
    
    For Each objTemp In objSSTemp4
        vAttList = objTemp.GetAttributes
        
        If vAttList(0).TextString = strSearch Then
            If InStr(vAttList(1).TextString, "+HO1") < 1 Then
                'strAtt1 = cbCblType.Value & "(" & cbCableSize.Value & ")"
                'If Not cbSuffix.Value = "" Then strAtt1 = strAtt1 & cbSuffix.Value
                'strAtt2 = Replace(tbCblCallout.Value, vbCr, "\P")
                'strAtt2 = Replace(strAtt2, vbLf, "")
                
                'MsgBox strCableCallout
                'GoTo Exit_Sub
                
                vPoleAtt = Split(strCableCallout, " / ")
                
                vCounts = Split(vPoleAtt(0), ": ")
                strAtt1 = vCounts(1)
                
    
                strCounts = ""
                vCounts = Split(vPoleAtt(1), " + ")
                For i = 0 To UBound(vCounts)
                    If vCounts(i) = "" Then GoTo Next_line
                    
                    vLine = Split(vCounts(i), ": ")
                    strTemp = vLine(0) & ": " & vLine(1)
                    If strCounts = "" Then
                        strCounts = strTemp
                    Else
                        strCounts = strCounts & "\P" & strTemp
                    End If
Next_line:
                Next i
                
                vAttList(1).TextString = strAtt1
                vAttList(2).TextString = strCounts
            
                objTemp.Update
                
                'GoTo Exit_Sub
            End If
        End If
    Next objTemp
    
    'MsgBox "Callout not found."
    
Exit_Sub:
    objSSTemp4.Clear
    objSSTemp4.Delete
End Sub

Private Sub AddSplitter()
    Dim objSplitter, objTemp As AcadBlockReference
    Dim objEntity As AcadEntity
    Dim vAttList, vReturnPnt As Variant
    
    Dim lwpCoords(0 To 3) As Double
    Dim vBlockCoords(0 To 2) As Double
    Dim dPrevious(0 To 2) As Double
    Dim lineObj As AcadLWPolyline
    Dim strLayer As String
    Dim dScale As Double
    
    Me.Hide
    
    ThisDrawing.Utility.GetEntity objEntity, vReturnPnt, "Select Closure: "
    
    If TypeOf objEntity Is AcadBlockReference Then
        Set objTemp = objEntity
        
        lwpCoords(0) = objTemp.InsertionPoint(0)
        lwpCoords(1) = objTemp.InsertionPoint(1)
    Else
        lwpCoords(0) = vReturnPnt(0)
        lwpCoords(1) = vReturnPnt(1)
    End If
    
    dPrevious(0) = lwpCoords(0)
    dPrevious(1) = lwpCoords(1)
    dPrevious(2) = 0#
    
    vReturnPnt = ThisDrawing.Utility.GetPoint(dPrevious, "Select Point: ")
    vBlockCoords(0) = vReturnPnt(0)
    vBlockCoords(1) = vReturnPnt(1)
    vBlockCoords(2) = vReturnPnt(2)
    lwpCoords(2) = vBlockCoords(0)
    lwpCoords(3) = vBlockCoords(1)
    
    Set lineObj = ThisDrawing.ModelSpace.AddLightWeightPolyline(lwpCoords)
    
    If cbCblType.Value = "CO" Then
        strLayer = "Integrity Proposed-Aerial"
    Else
        strLayer = "Integrity Proposed-Buried"
    End If
    lineObj.Layer = strLayer
    lineObj.Update
    
    dScale = CDbl(cbScale.Value) / 100
    If dScale = 0 Then dScale = 0.75
        
    Set objSplitter = ThisDrawing.ModelSpace.InsertBlock(vBlockCoords, "iSplitter", dScale, dScale, dScale, 0)
    vAttItem = objSplitter.GetAttributes
    
    vAttItem(0).TextString = CountsSplitter.cbSplitterSize.Value
    vAttItem(1).TextString = CountsSplitter.tbF2Name.Value & " " & CountsSplitter.tbSplitterName.Value
    
    objSplitter.Layer = strLayer
    
    'If lwpCoords(2) < lwpCoords(0) Then
        'vBlockCoords(0) = vBlockCoords(0) - (75 * dScale)
        'objSplitter.InsertionPoint = vBlockCoords
    'End If
    objSplitter.Update
    
    Me.show
End Sub

Private Sub AddTapToPole(strLine As String)
    Dim iBF, iEF, iBC, iEC, iTemp, iCable, iLine As Integer
    Dim dTemp As Double
    Dim vLine, vCount As Variant
    Dim strCounts, strFibers, strXD As String
    
    Me.Hide
    
    vLine = Split(strLine, ": ")
    vCount = Split(vLine(1), "-")
    
    iBC = CInt(vCount(0))
    If UBound(vCount) = 0 Then
        iEC = iBC
    Else
        iEC = CInt(vCount(1))
    End If
    
    iBF = iBC
    iEF = iEC
    
    While iBF > 12
        iBF = iBF - 12
        iEF = iEF - 12
    Wend
    
    'iEF = iEC - (iBF - iBC)
    
    strFibers = iBF & "-" & iEF
    strCounts = vLine(0) & ": " & iBC & "-" & iEC
    
    Load NewCableForm
        NewCableForm.Caption = "Tap Cable"
        NewCableForm.cbCblType.Value = "CO"
        NewCableForm.cbSuffix.Value = "6M-EHS"
        NewCableForm.tbPosition.Value = "A1"
        
        Select Case iEF
            Case Is < 13
                iCable = 12
            Case Is < 25
                iCable = 24
            Case Is < 49
                iCable = 48
            Case Is < 73
                iCable = 72
            Case Is < 97
                iCable = 96
            Case Is < 145
                iCable = 144
            Case Else
                iCable = 0
        End Select
        
        NewCableForm.cbCableSize.Value = iCable
        'NewCableForm.cbCblName.AddItem vLine(0)
            
        iLine = 0
        
        If iBF > 1 Then
            NewCableForm.lbCounts.AddItem "1-" & (iBF - 1)
            strXD = "XD: 1-" & (iBF - 1)
            NewCableForm.lbCounts.List(iLine, 1) = strXD
            iLine = iLine + 1
        End If
        
        NewCableForm.lbCounts.AddItem strFibers
        NewCableForm.lbCounts.List(iLine, 1) = strCounts
        iLine = iLine + 1
        
        If iEF < iCable Then
            NewCableForm.lbCounts.AddItem (iEF + 1) & "-" & iCable
            strXD = "XD: " & (iEF + 1) & "-" & iCable
            NewCableForm.lbCounts.List(iLine, 1) = strXD
            iLine = iLine + 1
        End If
        
        NewCableForm.show
        
    Unload NewCableForm
    
    Me.show
End Sub

Attribute VB_Name = "CountsSplitter"
Attribute VB_Base = "0{DCF59E6D-0DA9-4465-AADB-AA15AE8D774C}{17B1B75D-5A6A-4F54-AB93-20458D32133C}"
Attribute VB_GlobalNameSpace = False
Attribute VB_Creatable = False
Attribute VB_PredeclaredId = True
Attribute VB_Exposed = False
Attribute VB_TemplateDerived = False
Attribute VB_Customizable = False
Public iExisting As Integer
Dim strPreviousSplitter As String
Dim strPreviousSplices As String
Dim strPreviousF1 As String

Private Sub cbCancel_Click()
    cbChanged.Value = False
    Me.Hide
End Sub

Private Sub cbCreateMCL_Click()
    Call SaveMCL
End Sub

Private Sub cbDone_Click()
    Call SaveMCL
    cbChanged.Value = True
    
    Me.Hide
    
    'Dim strTemp As String
    
    'tbSplice.Value = strPreviousF1
    'strPreviousF1 = ""
    
    'tbF2Name.Value = strPreviousSplitter
    'strPreviousSplitter = ""
    
    'strPreviousSplices = strPreviousSplices & vbCr & tbresults.Value
    'tbResult.Value = ""
    
    'Call OpenMCL
End Sub

Private Sub cbDrop_Click()
    If lbMain.ListCount < 1 Then Exit Sub
    
    Dim strCable, strCounts, strSpliced, strCallout As String
    Dim vLine, vItem As Variant
    
    Load CountsTap
        CountsTap.tbStructure.Value = tbActivePole.Value
        
        For i = 0 To lbMain.ListCount - 1
            CountsTap.lbMain.AddItem i + 1
            
            If lbMain.List(i, 3) = "" Then
                CountsTap.lbMain.List(i, 1) = lbMain.List(i, 1)
                CountsTap.lbMain.List(i, 2) = lbMain.List(i, 2)
            Else
                CountsTap.lbMain.List(i, 1) = "XD"
                CountsTap.lbMain.List(i, 2) = i + 1
            End If
            CountsTap.lbMain.List(i, 3) = ""
        Next i
        
        CountsTap.show
        
        If CountsTap.cbChanged.Value = False Then GoTo Exit_Sub
        
        strLine = CountsTap.tbPosition.Value & ": " & CountsTap.cbCblType.Value & "(" & CountsTap.cbCableSize.Value & ")"
        If Not CountsTap.cbSuffix.Value = "" Then strLine = strLine & CountsTap.cbSuffix.Value
        strLine = strLine & " / " & Replace(CountsTap.tbResult.Value, vbCr, " + ")
        strLine = Replace(strLine, vbLf, "")
        
        For i = 0 To CountsTap.lbMain.ListCount - 1
            If Left(CountsTap.lbMain.List(i, 3), 2) = "Y " Then
                lbMain.List(i, 3) = "T"
            End If
        Next i
        
Exit_Sub:
    Unload CountsTap
    
    Dim objEntity As AcadEntity
    Dim objBlock As AcadBlockReference
    Dim vReturnPnt, vAttList As Variant
    Dim strTap As String
    Dim iAtt As Integer
    
    Me.Hide
    
    On Error Resume Next
    
    Err = 0
    ThisDrawing.Utility.GetEntity objEntity, vReturnPnt, vbCr & "Select Block:"
    If Not Err = 0 Then Exit Sub
    
    If Not TypeOf objEntity Is AcadBlockReference Then Exit Sub
    Set objBlock = objEntity
    
    Select Case objBlock.Name
        Case "sPole"
            iAtt = 25
        Case "sPed", "sHH", "sPanel"
            iAtt = 5
        Case Else
            Exit Sub
    End Select
        
    vAttList = objBlock.GetAttributes
    vAttList(iAtt).TextString = strLine
    strTap = "T " & vAttList(0).TextString
        
    objBlock.Update
    
    For i = 0 To lbMain.ListCount - 1
        If lbMain.List(i, 3) = "T" Then lbMain.List(i, 3) = strTap
    Next i

    bUpdatePole = True
    
    Call GetTapCallout
    
    Me.show
End Sub

Private Sub cbSendAhead_Click()
    If lbMain.ListCount < 1 Then Exit Sub
    
    Dim strCable, strCounts, strSpliced, strCallout As String
    Dim vLine, vItem As Variant
    
    Load CountsTap
        CountsTap.tbStructure.Value = tbActivePole.Value
        
        For i = 0 To lbMain.ListCount - 1
            CountsTap.lbMain.AddItem i + 1
            
            If lbMain.List(i, 3) = "" Then
                CountsTap.lbMain.List(i, 1) = lbMain.List(i, 1)
                CountsTap.lbMain.List(i, 2) = lbMain.List(i, 2)
            Else
                CountsTap.lbMain.List(i, 1) = "XD"
                CountsTap.lbMain.List(i, 2) = i + 1
            End If
            CountsTap.lbMain.List(i, 3) = ""
        Next i
        
        For i = 1 To CountsForm.lbCounts.ListCount - 1
            CountsTap.lbTap.AddItem i
            
            If CountsForm.lbCounts.List(i, 3) = "<>" Then
                CountsTap.lbTap.List(i - 1, 1) = CountsForm.lbCounts.List(i, 1)
                CountsTap.lbTap.List(i - 1, 2) = CountsForm.lbCounts.List(i, 2)
            Else
                CountsTap.lbTap.List(i - 1, 1) = "XD"
                CountsTap.lbTap.List(i - 1, 2) = i
            End If
        Next i
        
        CountsForm.tbPosition.Enabled = False
        CountsForm.cbCblType.Enabled = False
        CountsForm.cbCableSize.Enabled = False
        CountsForm.cbSuffix.Enabled = False
        
        CountsTap.show
        
        If CountsTap.cbChanged.Value = False Then GoTo Exit_Sub
        
        For i = 0 To CountsTap.lbMain.ListCount - 1
            If Left(CountsTap.lbMain.List(i, 3), 2) = "Y " Then
                lbMain.List(i, 3) = Replace(CountsTap.lbMain.List(i, 3), "Y ", "A ")
            End If
        Next i
        
Exit_Sub:
    Unload CountsTap

    bUpdatePole = True
    
    Call GetTapCallout
End Sub

Private Sub cbSendToBack_Click()
    If lbMain.ListCount < 1 Then Exit Sub
    
    Dim strCable, strCounts, strSpliced, strCallout As String
    Dim vLine, vItem As Variant
    
    Load CountsTap
        CountsTap.tbStructure.Value = tbActivePole.Value
        
        For i = 0 To lbMain.ListCount - 1
            CountsTap.lbMain.AddItem i + 1
            
            If lbMain.List(i, 3) = "" Then
                CountsTap.lbMain.List(i, 1) = lbMain.List(i, 1)
                CountsTap.lbMain.List(i, 2) = lbMain.List(i, 2)
            Else
                CountsTap.lbMain.List(i, 1) = "XD"
                CountsTap.lbMain.List(i, 2) = i + 1
            End If
            CountsTap.lbMain.List(i, 3) = ""
        Next i
        
        For i = 1 To CountsForm.lbCounts.ListCount - 1
            CountsTap.lbTap.AddItem i
            
            If CountsForm.lbCounts.List(i, 3) = "<>" Then
                CountsTap.lbTap.List(i - 1, 1) = CountsForm.lbCounts.List(i, 1)
                CountsTap.lbTap.List(i - 1, 2) = CountsForm.lbCounts.List(i, 2)
            Else
                CountsTap.lbTap.List(i - 1, 1) = "XD"
                CountsTap.lbTap.List(i - 1, 2) = i
            End If
        Next i
        
        CountsTap.tbPosition.Enabled = False
        CountsTap.cbCblType.Enabled = False
        CountsTap.cbCableSize.Enabled = False
        CountsTap.cbSuffix.Enabled = False
        
        CountsTap.show
        
        If CountsTap.cbChanged.Value = False Then GoTo Exit_Sub
        
        For i = 0 To CountsTap.lbMain.ListCount - 1
            If Left(CountsTap.lbMain.List(i, 3), 2) = "Y " Then
                lbMain.List(i, 3) = Replace(CountsTap.lbMain.List(i, 3), "Y ", "B ")
            End If
        Next i
        
Exit_Sub:
    Unload CountsTap

    bUpdatePole = True
    
    Call GetTapCallout
End Sub

Private Sub cbSplitterSize_Change()
    If cbSplitterSize.Value = "" Then Exit Sub
    If iExisting = 1 Then Exit Sub
    
    lbMain.Clear
    
    Dim iCounter As Integer
    
    iCounter = CInt(tbStartCount.Value)
    
    For i = 0 To CInt(cbSplitterSize.Value) - 1
        lbMain.AddItem iCounter
        lbMain.List(i, 1) = tbF2Name.Value
        lbMain.List(i, 2) = iCounter
        lbMain.List(i, 3) = ""
        
        iCounter = iCounter + 1
    Next i
    
    Call GetTapCallout
End Sub

Private Sub cbSplitterSplice_Click()
    Dim iSelected As Integer
    Dim strLine As String
    
    For i = 0 To lbMain.ListCount - 1
        If lbMain.Selected(i) = True Then
            iSelected = i
            GoTo Found_Selected
        End If
    Next i
    
    MsgBox "No Count Selected."
    Exit Sub
    
Found_Selected:
    
    'strPreviousSplitter = tbF2Name.Value
    'strPreviousSplices = tbResult.Value
    'strPreviousF1 = tbSplice.Value
    Call SaveMCL
    
    strLine = lbMain.List(iSelected, 1) & Asc(93 + CInt(lbMain.List(iSelected, 2)))
    tbSplice.Value = lbMain.List(iSelected, 1) & ": " & lbMain.List(iSelected, 2)
    tbF2Name.Value = strLine
    tbResult.Value = ""
    'iExisting = 0
    
    lbMain.Clear
    
End Sub

Private Sub cbTerminal_Click()
    Dim iSelected As Integer
    
    For i = 0 To lbMain.ListCount - 1
        If lbMain.Selected(i) = True Then
            iSelected = i
            GoTo Found_Selected
        End If
    Next i
    
    MsgBox "No Count Selected."
    Exit Sub
    
Found_Selected:
    
    Dim result As Integer
    Dim objEntity As AcadEntity
    Dim objRES As AcadBlockReference
    Dim vAttList, vBasePnt As Variant
    Dim strLine, strResult As String
    Dim strName As String
    
    Me.Hide
    On Error Resume Next
    
Next_One:
    
    If Not lbMain.List(iSelected, 3) = "" Then
        result = MsgBox("Overwrite previous assignment?", vbYesNo, "Fiber Assigned!")
        If result = vbNo Then Exit Sub
    End If
    
    Err = 0
    ThisDrawing.Utility.GetEntity objEntity, vBasePnt, "Select Building: "
    If Not Err = 0 Then GoTo Exit_Sub
    
    If TypeOf objEntity Is AcadBlockReference Then
        Set objRES = objEntity
        vAttList = objRES.GetAttributes
            
        Select Case objRES.Name
            Case "SG"
                strResult = "C " & tbActivePole.Value & ";;SG;;" & vAttList(1).TextString & ";;SMARTGRID;;" & vAttList(0).TextString
                
                strLine = lbMain.List(iSelected, 1) & ": " & lbMain.List(iSelected, 2)
                
                vAttList(2).TextString = tbActivePole.Value & " - " & strLine
                objRES.Update
                
            Case "Customer"
                strResult = "C " & tbActivePole.Value & ";;" & vAttList(1).TextString & ";;" & vAttList(2).TextString & ";;" & vAttList(0).TextString
                If vAttList(3).TextString = "" Then
                    strResult = strResult & ";;<>"
                Else
                    strResult = strResult & ";;" & vAttList(3).TextString
                End If
                
                strLine = lbMain.List(iSelected, 1) & ": " & lbMain.List(iSelected, 2)
                If cbDrop.Value = False Then strLine = "(" & strLine & ")"
                vAttList(4).TextString = tbActivePole.Value & " - " & strLine
                objRES.Update
            Case Else
                GoTo Exit_Sub
        End Select
        
        lbMain.List(iSelected, 3) = strResult
    End If
    
    iSelected = iSelected - 1
    
    GoTo Next_One
    
Exit_Sub:
    lbMain.ListIndex = iSelected
    
    Call GetTapCallout
    
    Me.show
End Sub

Private Sub Label26_Click()
    Dim objEntity As AcadEntity
    Dim objRES As AcadBlockReference
    Dim vAttList, vBasePnt As Variant
    Dim strName As String
    
    Me.Hide
    On Error Resume Next
    
    Err = 0
    ThisDrawing.Utility.GetEntity objEntity, vBasePnt, "Select Building: "
    If Not Err = 0 Then GoTo Exit_Sub
    
    If TypeOf objEntity Is AcadBlockReference Then
        Set objRES = objEntity
        vAttList = objRES.GetAttributes
            
        Select Case objRES.Name
            'Case "RES", "BUSINESS", "MDU", "TRLR", "SCHOOL", "CHURCH", "LOT"
                'tbSplitterName.Value = vAttList(0).TextString & " " & vAttList(1).TextString
            Case "Customer"
                strName = vAttList(1).TextString & " " & vAttList(2).TextString
                tbSplitterName.Value = Replace(strName, "  ", " ")
        End Select
        'Set objRES = Nothing
    End If
    
Exit_Sub:
    Me.show
End Sub

Private Sub tbF2Name_Exit(ByVal Cancel As MSForms.ReturnBoolean)
    If tbF2Name.Value = "" Then Exit Sub
    
    lbMain.Clear
    tbResult.Value = ""
    
    Dim vLine, vItem, vTemp As Variant
    Dim strFileName, strName As String
    
    strName = tbF2Name.Value
    vLine = Split(ThisDrawing.Name, " ")
    strFileName = ThisDrawing.Path & "\" & vLine(0) & " Counts -" & strName & ".mcl"
    
    For i = 0 To tbF2Name.ListCount - 1
        If tbF2Name.List(i) = strName Then GoTo Found_Name
    Next i
    
    iExisting = 0
    Exit Sub
    
Found_Name:
    
    iExisting = 1
    cbSplitterSize.Enabled = False
    
    Call OpenMCL
    
    cbSplitterSize.Value = lbMain.ListCount
End Sub

Private Sub UserForm_Initialize()
    lbMain.ColumnCount = 4
    lbMain.ColumnWidths = "24;72;36;30"
    
    cbSplitterSize.AddItem "2"
    cbSplitterSize.AddItem "4"
    cbSplitterSize.AddItem "8"
    cbSplitterSize.AddItem "16"
    cbSplitterSize.AddItem "32"
    cbSplitterSize.AddItem "64"
    
    iExisting = 0
    'strPreviousSplitter = ""
    'strPreviousSplices = ""
    'strPreviousF1 = ""
    
    Dim strFile, strFolder, strTemp As String
    Dim strFileName As String
    Dim vName, vLine, vItem As Variant
    Dim strLine, strTab, strCable As String
    Dim fName As String
    Dim iIndex, iCount As Integer
    
    strFolder = ThisDrawing.Path & "\*.*"
    
    strFile = Dir$(strFolder)
    
    Do While strFile <> ""
        If InStr(LCase(strFile), ".mcl") Then
            strTab = Replace(UCase(strFile), ".MCL", "")
            vLine = Split(strTab, " -")
            
            tbF2Name.AddItem vLine(1)
        End If
        strFile = Dir$
    Loop
End Sub

Private Sub GetTapCallout()
    Dim strLine, strItem As String
    Dim strCurrent, strPrevious As String
    Dim iStart, iEnd As Integer
    
    tbResult.Value = ""
    
    If strPreviousSplices = "" Then
        strLine = ""
    Else
        strLine = strPreviousSplices
    End If
    
    If iExisting = 0 Then
        If strLine = "" Then
            strLine = tbSplice.Value & ": " & tbActivePole.Value
        Else
            strLine = strLine & vbCr & tbSplice.Value & ": " & tbActivePole.Value
        End If
    End If
    
    strPrevious = lbMain.List(0, 3)
    If Left(strPrevious, 2) = "A " Then strPrevious = "A"
    If Left(strPrevious, 2) = "B " Then strPrevious = "B"
    If Left(strPrevious, 2) = "C " Then strPrevious = "C"
    If strPrevious = "X" Then strPrevious = ""
    
    strCurrent = strPrevious
    iStart = CInt(lbMain.List(0, 2))
    iEnd = iStart
    
    For i = 1 To lbMain.ListCount - 1
        strCurrent = lbMain.List(i, 3)
        If Left(strCurrent, 2) = "A " Then strCurrent = "A"
        If Left(strCurrent, 2) = "B " Then strCurrent = "B"
        If Left(strCurrent, 2) = "C " Then strCurrent = "C"
        If strCurrent = "X" Then strCurrent = ""
        
        If strCurrent = strPrevious Then
            iEnd = CInt(lbMain.List(i, 2))
        Else
            If Not strPrevious = "" Then
                strItem = lbMain.List(i - 1, 1) & ": " & iStart
                If iEnd > iStart Then strItem = strItem & "-" & iEnd
                
                strItem = strItem & ": " & tbActivePole.Value
                
                If strLine = "" Then
                    strLine = strItem
                Else
                    strLine = strLine & vbCr & strItem
                End If
            End If
             
            strPrevious = strCurrent
            iStart = CInt(lbMain.List(i, 2))
            iEnd = iStart
        End If
        
    Next i
             
    If Not strPrevious = "" Then
        strItem = lbMain.List(i - 1, 1) & ": " & iStart
        If iEnd > iStart Then strItem = strItem & "-" & iEnd
        
        strItem = strItem & ": " & tbActivePole.Value
             
        If strLine = "" Then
            strLine = strItem
        Else
            strLine = strLine & vbCr & strItem
        End If
    End If
    
    tbResult.Value = strLine
End Sub

Private Sub SaveMCL()
    Dim strFileName As String
    Dim vName, vLine, vItem As Variant
    Dim strLine, strTemp As String
    'Dim fName As String
    Dim iIndex As Integer
    
    vName = Split(ThisDrawing.Name, " ")
    strFileName = ThisDrawing.Path & "\" & vName(0) & " Counts -" & tbF2Name.Value & ".mcl"
    
    'fName = Dir(strFilename)
    'If Not fName = "" Then
        'MsgBox "File already exist."
        'Exit Sub
    'End If
    
    Open strFileName For Output As #1
    
    Print #1, tbF2Name.Value & " " & tbSplitterName.Value
    
    For i = 0 To lbMain.ListCount - 1
        If Left(lbMain.List(i, 3), 2) = "C " Then
            'vItem = Split(lbMain.List(i, 3), "C ")
            'vLine = Split(vItem(1), ";;")
            strTemp = Right(lbMain.List(i, 3), Len(lbMain.List(i, 3)) - 2)
            vLine = Split(strTemp, ";;")
                
            strLine = lbMain.List(i, 2) & vbTab & vLine(0) & vbTab & vLine(1) & vbTab & vLine(2) & vbTab & vLine(3) & vbTab & vLine(4)
        Else
            strLine = lbMain.List(i, 2) & vbTab & "<>" & vbTab & "<>" & vbTab & "<>" & vbTab & "<>" & vbTab & "<>"
        End If
        
        Print #1, strLine
    Next i
    
    Close #1
End Sub

Private Sub OpenMCL()
    Dim vLine As Variant
    Dim strFileName, strName As String
    Dim strLine As String
    Dim iIndex As Integer
    
    strName = tbF2Name.Value
    vLine = Split(ThisDrawing.Name, " ")
    strFileName = ThisDrawing.Path & "\" & vLine(0) & " Counts -" & strName & ".mcl"
    
    Open strFileName For Input As #1
    
    Line Input #1, strLine
    While Not EOF(1)
        Line Input #1, strLine
        If strLine = "" Then GoTo Next_line
        
        vLine = Split(strLine, vbTab)
        
        iIndex = lbMain.ListCount + 1
        lbMain.AddItem iIndex
        iIndex = iIndex - 1
        
        lbMain.List(iIndex, 1) = strName
        lbMain.List(iIndex, 2) = vLine(0)
        lbMain.List(iIndex, 3) = ""
        If Not vLine(4) = "<>" Then lbMain.List(iIndex, 3) = "X"
        
Next_line:
    Wend
    
    Close #1
End Sub

Attribute VB_Name = "CountsTap"
Attribute VB_Base = "0{96EFC051-6FE4-40BA-954A-21A356D1513D}{081C3A36-EFD1-48B3-AC5C-54E4DCC8C421}"
Attribute VB_GlobalNameSpace = False
Attribute VB_Creatable = False
Attribute VB_PredeclaredId = True
Attribute VB_Exposed = False
Attribute VB_TemplateDerived = False
Attribute VB_Customizable = False
Dim iChanged As Integer

Private Sub cbAddToBottom_Click()
    If lbTap.ListCount < 1 Then Exit Sub
    If lbMain.ListCount < 1 Then Exit Sub
    
    Dim iMainIndex, iTapIndex As Integer
    Dim iCounter, iIndex As Integer
    
    iCounter = 0
    iIndex = 0
    
    For i = 0 To lbMain.ListCount - 1
        If lbMain.Selected(i) = True Then
            iCounter = iCounter + 1
            iIndex = i
        Else
            If iCounter > 0 Then GoTo Exit_Next
        End If
    Next i
Exit_Next:
    
    iTapIndex = iIndex - iCounter + 1
    While iTapIndex > lbTap.ListCount - 1
        iTapIndex = iTapIndex - 12
    Wend
    While iTapIndex < lbTap.ListCount - 13
        iTapIndex = iTapIndex + 12
    Wend
    iCounter = 0
    
    For i = 0 To lbMain.ListCount - 1
        If lbMain.Selected(i) = True Then
            lbTap.List(iTapIndex, 1) = lbMain.List(i, 1)
            lbTap.List(iTapIndex, 2) = lbMain.List(i, 2)
            iTapIndex = iTapIndex + 1
            lbMain.List(i, 3) = "Y " & iTapIndex
            iCounter = iCounter + 1
        Else
            If iCounter > 0 Then GoTo Exit_Sub
        End If
    Next i
    
Exit_Sub:
    
    Call GetTapCallout
End Sub

Private Sub cbAddToTop_Click()
    If lbTap.ListCount < 1 Then Exit Sub
    If lbMain.ListCount < 1 Then Exit Sub
    
    Dim iMainIndex, iTapIndex As Integer
    Dim iCounter, iIndex As Integer
    
    iCounter = 0
    'iIndex = 0
    
    For i = 0 To lbMain.ListCount - 1
        If lbMain.Selected(i) = True Then
            If iCounter = 0 Then
                iTapIndex = CInt(lbMain.List(i, 2)) - 1
                While iTapIndex > 11
                    iTapIndex = iTapIndex - 12
                Wend
            End If
            
            lbTap.List(iTapIndex, 1) = lbMain.List(i, 1)
            lbTap.List(iTapIndex, 2) = lbMain.List(i, 2)
            iTapIndex = iTapIndex + 1
            lbMain.List(i, 3) = "Y " & iTapIndex
            iCounter = iCounter + 1
        Else
            If iCounter > 0 Then GoTo Exit_Next
        End If
    Next i
    
Exit_Next:
    
    Call GetTapCallout
End Sub

Private Sub cbCableSize_Change()
    If cbCableSize.Value = "" Then Exit Sub
    
    Dim iCount As Integer
    
    lbTap.Clear
    iCount = CInt(cbCableSize.Value)
    
    For i = 0 To iCount - 1
        lbTap.AddItem i + 1
        lbTap.List(i, 1) = "XD"
        lbTap.List(i, 2) = i + 1
    Next i
    
    tbResult.Value = "XD: 1-" & cbCableSize.Value & ": END"
End Sub

Private Sub cbCblType_Change()
    Select Case cbCblType.Value
        Case "BFO", "UO"
            cbSuffix.Value = ""
        Case "CO"
            cbSuffix.Value = "6M-EHS"
    End Select
End Sub

Private Sub cbDone_Click()
    cbChanged.Value = True
    Me.Hide
End Sub

Private Sub cbIn_Click()
    If lbTap.ListCount < 1 Then Exit Sub
    If lbMain.ListCount < 1 Then Exit Sub
    
    Dim iMainIndex, iTapIndex As Integer
    Dim iTapTemp, iMainTemp As Integer
    Dim iCounter As Integer
    Dim result As Integer
    
    For i = 0 To lbTap.ListCount - 1
        If lbTap.Selected(i) = True Then
            iTapIndex = i
            GoTo Found_TapSelected
        End If
    Next i
    
    Exit Sub
Found_TapSelected:
    iTapTemp = iTapIndex
    While iTapTemp > 11
        iTapTemp = iTapTemp - 12
    Wend
    iCounter = 0
    
    For i = 0 To lbMain.ListCount - 1
        If lbMain.Selected(i) = True Then
            If iCounter = 0 Then
                iMainTemp = i
                While iMainTemp > 11
                    iMainTemp = iMainTemp - 12
                Wend
                
                If Not iTapTemp = iMainTemp Then
                    result = MsgBox("Continue off-color?", vbYesNo, "Off - Color")
                    If result = vbNo Then Exit Sub
                End If
            End If
            
            iCounter = iCounter + 1
            lbTap.List(iTapIndex, 1) = lbMain.List(i, 1) & "(IN)"
            lbTap.List(iTapIndex, 2) = lbMain.List(i, 2)
            iTapIndex = iTapIndex + 1
            lbMain.List(i, 3) = "Y " & iTapIndex
        Else
            If iCounter > 0 Then GoTo Exit_Next
        End If
    Next i
    
Exit_Next:
    
    Call GetTapCallout
End Sub

Private Sub cbOut_Click()
    If lbTap.ListCount < 1 Then Exit Sub
    If lbMain.ListCount < 1 Then Exit Sub
    
    Dim iMainIndex, iTapIndex As Integer
    Dim iTapTemp, iMainTemp As Integer
    Dim iCounter As Integer
    Dim result As Integer
    
    For i = 0 To lbTap.ListCount - 1
        If lbTap.Selected(i) = True Then
            iTapIndex = i
            GoTo Found_TapSelected
        End If
    Next i
    
    Exit Sub
Found_TapSelected:
    iTapTemp = iTapIndex
    While iTapTemp > 11
        iTapTemp = iTapTemp - 12
    Wend
    iCounter = 0
    
    For i = 0 To lbMain.ListCount - 1
        If lbMain.Selected(i) = True Then
            If iCounter = 0 Then
                iMainTemp = i
                While iMainTemp > 11
                    iMainTemp = iMainTemp - 12
                Wend
                
                If Not iTapTemp = iMainTemp Then
                    result = MsgBox("Continue off-color?", vbYesNo, "Off - Color")
                    If result = vbNo Then Exit Sub
                End If
            End If
            
            iCounter = iCounter + 1
            lbTap.List(iTapIndex, 1) = lbMain.List(i, 1) & "(OUT)"
            lbTap.List(iTapIndex, 2) = lbMain.List(i, 2)
            iTapIndex = iTapIndex + 1
            lbMain.List(i, 3) = "Y " & iTapIndex
        Else
            If iCounter > 0 Then GoTo Exit_Next
        End If
    Next i
    
Exit_Next:
    
    Call GetTapCallout
End Sub

Private Sub cbQuit_Click()
    cbChanged.Value = False
    Me.Hide
End Sub

Private Sub cbSpliceSelected_Click()
    If lbTap.ListCount < 1 Then Exit Sub
    If lbMain.ListCount < 1 Then Exit Sub
    
    Dim iMainIndex, iTapIndex As Integer
    Dim iTapTemp, iMainTemp As Integer
    Dim iCounter As Integer
    Dim result As Integer
    
    For i = 0 To lbTap.ListCount - 1
        If lbTap.Selected(i) = True Then
            iTapIndex = i
            GoTo Found_TapSelected
        End If
    Next i
    
    Exit Sub
Found_TapSelected:
    iTapTemp = iTapIndex
    While iTapTemp > 11
        iTapTemp = iTapTemp - 12
    Wend
    iCounter = 0
    
    For i = 0 To lbMain.ListCount - 1
        If lbMain.Selected(i) = True Then
            If iCounter = 0 Then
                iMainTemp = i
                While iMainTemp > 11
                    iMainTemp = iMainTemp - 12
                Wend
                
                If Not iTapTemp = iMainTemp Then
                    result = MsgBox("Continue off-color?", vbYesNo, "Off - Color")
                    If result = vbNo Then Exit Sub
                End If
            End If
            
            iCounter = iCounter + 1
            lbTap.List(iTapIndex, 1) = lbMain.List(i, 1)
            lbTap.List(iTapIndex, 2) = lbMain.List(i, 2)
            iTapIndex = iTapIndex + 1
            lbMain.List(i, 3) = "Y " & iTapIndex
        Else
            If iCounter > 0 Then GoTo Exit_Next
        End If
    Next i
    
Exit_Next:
    
    Call GetTapCallout
End Sub

Private Sub lbTap_KeyDown(ByVal KeyCode As MSForms.ReturnInteger, ByVal Shift As Integer)
    If lbTap.ListCount < 1 Then Exit Sub
    
    Dim strCable, strCount As String
    Dim iIndex As Integer
    
    Select Case KeyCode
        Case vbKeyDelete
            iIndex = lbTap.ListIndex
            
            strCable = lbTap.List(iIndex, 1)
            strCount = lbTap.List(iIndex, 2)
            
            lbTap.List(iIndex, 1) = "XD"
            lbTap.List(iIndex, 2) = lbTap.List(iIndex, 0)
            
            For i = 0 To lbMain.ListCount - 1
                If lbMain.List(i, 1) = strCable Then
                    If lbMain.List(i, 2) = strCount Then
                        lbMain.List(i, 3) = ""
                        lbMain.Selected(i) = False
                        GoTo Exit_Next
                    End If
                End If
            Next i
Exit_Next:
            If Not iIndex > lbTap.ListCount - 1 Then
                lbTap.Selected(iIndex) = False
                lbTap.ListIndex = iIndex + 1
                lbTap.Selected(iIndex + 1) = True
            End If
            
            Call GetTapCallout
    End Select
End Sub

Private Sub UserForm_Initialize()
    lbMain.ColumnCount = 4
    lbMain.ColumnWidths = "24;72;36;30"
    
    lbTap.ColumnCount = 3
    lbTap.ColumnWidths = "24;72;30"
    
    cbCblType.AddItem "CO"
    cbCblType.AddItem "BFO"
    cbCblType.AddItem "UO"
    cbCblType.Value = "CO"
    
    cbSuffix.AddItem ""
    cbSuffix.AddItem "E"
    cbSuffix.AddItem "6M-EHS"
    cbSuffix.AddItem "6M"
    cbSuffix.AddItem "10M"
    cbSuffix.Value = "6M-EHS"
    
    cbCableSize.AddItem "12"
    cbCableSize.AddItem "24"
    cbCableSize.AddItem "36"
    cbCableSize.AddItem "48"
    cbCableSize.AddItem "72"
    cbCableSize.AddItem "96"
    cbCableSize.AddItem "144"
    cbCableSize.AddItem "216"
    cbCableSize.AddItem "288"
    cbCableSize.AddItem "360"
    cbCableSize.AddItem "432"
    
    cbChanged.Value = False
    
'    For i = 0 To 5
'        lbMain.AddItem i + 1
'        lbMain.List(i, 1) = "XD"
'        lbMain.List(i, 2) = i + 1
'        lbMain.List(i, 3) = ""
'    Next i
'
'    For i = 6 To 20
'        lbMain.AddItem i + 1
'        lbMain.List(i, 1) = "F100"
'        lbMain.List(i, 2) = i + 25
'        lbMain.List(i, 3) = ""
'    Next i
'
'    For i = 21 To 23
'        lbMain.AddItem i + 1
'        lbMain.List(i, 1) = "XD"
'        lbMain.List(i, 2) = i + 1
'        lbMain.List(i, 3) = ""
'    Next i
'
'    For i = 24 To 65
'        lbMain.AddItem i + 1
'        lbMain.List(i, 1) = "F100-32"
'        lbMain.List(i, 2) = i - 23
'        lbMain.List(i, 3) = ""
'    Next i
'
'    For i = 66 To 71
'        lbMain.AddItem i + 1
'        lbMain.List(i, 1) = "XD"
'        lbMain.List(i, 2) = i + 1
'        lbMain.List(i, 3) = ""
'    Next i
    
End Sub

Private Sub GetTapCallout()
    Dim strLine, strItem As String
    Dim strCurrent, strPrevious As String
    Dim iStart, iEnd As Integer
    Dim iHO1 As Integer
    
    tbResult.Value = ""
    iHO1 = 0
    
    strPrevious = lbTap.List(0, 1)
    strCurrent = strPrevious
    iStart = CInt(lbTap.List(0, 2))
    iEnd = iStart
    
    If Not strCurrent = "XD" Then iHO1 = iHO1 + 1
    
    For i = 1 To lbTap.ListCount - 1
        strCurrent = lbTap.List(i, 1)
        
        If strCurrent = strPrevious Then
            iEnd = CInt(lbTap.List(i, 2))
        Else
            strItem = strPrevious & ": " & iStart
            If iEnd > iStart Then strItem = strItem & "-" & iEnd
            If strPrevious = "XD" Then
                strItem = strItem & ": END"
            Else
                If InStr(strPrevious, " OUT") = 0 Then
                    strItem = strItem & ": " & tbStructure.Value
                Else
                    strItem = strItem & ": <<???>>"
                End If
            End If
            
            If strLine = "" Then
                strLine = strItem
            Else
                strLine = strLine & vbCr & strItem
            End If
             
            strPrevious = strCurrent
            iStart = CInt(lbTap.List(i, 2))
            iEnd = iStart
        End If
    
        If Not strCurrent = "XD" Then iHO1 = iHO1 + 1
    Next i
             
    strItem = strPrevious & ": " & iStart
    If iEnd > iStart Then strItem = strItem & "-" & iEnd
    If strPrevious = "XD" Then
        strItem = strItem & ": END"
    Else
        If InStr(strPrevious, " OUT") = 0 Then
            strItem = strItem & ": " & tbStructure.Value
        Else
            strItem = strItem & ": <<???>>"
        End If
    End If
             
    If strLine = "" Then
        strLine = strItem
    Else
        strLine = strLine & vbCr & strItem
    End If
    
    tbResult.Value = strLine
    tbHO1.Value = iHO1
End Sub

Attribute VB_Name = "CreateKML"
Attribute VB_Base = "0{3F6DF50D-D68C-4BD9-9CFC-F0E949714430}{15696B9A-1A40-43BB-8E8F-D62DA5011AE5}"
Attribute VB_GlobalNameSpace = False
Attribute VB_Creatable = False
Attribute VB_PredeclaredId = True
Attribute VB_Exposed = False
Attribute VB_TemplateDerived = False
Attribute VB_Customizable = False
Private Sub cbAddDescription_Click()
    If lbFrom.ListIndex < 0 Then Exit Sub
    
    tbDescription.Value = tbDescription.Value & "{" & lbFrom.ListIndex & "}"
End Sub

Private Sub cbAddName_Click()
    If lbFrom.ListIndex < 0 Then Exit Sub
    
    tbName.Value = tbName.Value & "{" & lbFrom.ListIndex & "}"
End Sub

Private Sub cbConvert_Click()
    If tbFolder.Value = "" Then Exit Sub
    If tbFile.Value = "" Then Exit Sub
    
    Dim filterType, filterValue As Variant
    Dim grpCode(0) As Integer
    Dim grpValue(0) As Variant
    Dim objSS As AcadSelectionSet
    
    Dim objEntity As AcadEntity
    Dim objPoint As AcadPoint
    Dim objBlock As AcadBlockReference
    Dim vAttList As Variant
    
    Dim amap As AcadMap
    Dim ODRcs As ODRecords
    Dim ODRc As ODRecord
    Dim tbl As ODTable
    Dim tbls As ODTables
    
    Dim strName, strDescription, strCoords As String
    Dim dNort, dEast As Double
    Dim vLL As Variant
    Dim vLine, vItem, vTemp As Variant
    Dim iIndex As Integer
    Dim strFind, strReplace As String
    Dim strFile, strItem As String
    Dim strFileName As String
    Dim strStyle As String
    
    strFileName = tbFolder.Value & tbFile.Value & ".kml"
    
    strFile = "<?xml version=""1.0"" encoding=""UTF-8""?>" & vbCr
    strFile = strFile & "<kml xmlns=""http://www.opengis.net/kml/2.2"">" & vbCr
    strFile = strFile & "<Document>" & vbCr & vbCr
    
    If Not tbName.Value = "" Then
        strFile = strFile & "<Style id=""size_label"">" & vbCr
        strFile = strFile & "<LabelStyle>" & vbCr
        strFile = strFile & "<scale>" & tbNameScale.Value & "</scale>" & vbCr
        strFile = strFile & "</LabelStyle>" & vbCr
        strFile = strFile & "</Style>" & vbCr & vbCr
    End If
    
    If Not cbIconFolder.Value = "" Then
        If Not cbIcon.Value = "" Then
            strStyle = "<Style>" & vbCr & "<IconStyle>" & vbCr & "<Scale>" & tbScale.Value & "</Scale>" & vbCr
            strStyle = strStyle & "<Icon>" & vbCr & "<href>"
            strStyle = strStyle & "http://maps.google.com/mapfiles/kml/" & cbIconFolder.Value & "/" & cbIcon.Value & ".png</href>"
            strStyle = strStyle & vbCr & "</Icon>" & vbCr & "</IconStyle>" & vbCr & "</Style>" & vbCr
        End If
    End If
    
    On Error Resume Next
    
    If cbFromType.Value = "Block" Then
        grpCode(0) = 2
    Else
        grpCode(0) = 8
    
        Set amap = ThisDrawing.Application.GetInterfaceObject("AutoCADMap.Application")
    
        Set tbls = amap.Projects(ThisDrawing).ODTables
        If tbls.count > 0 Then
            For Each tbl In tbls
                If tbl.Name = cbFromList.Value Then GoTo Exit_For
            Next
        End If
Exit_For:

        Set ODRcs = tbl.GetODRecords
    End If
    
    grpValue(0) = cbFromList.Value
    filterType = grpCode
    filterValue = grpValue
    
    Err = 0
    Set objSS = ThisDrawing.SelectionSets.Add("objSS")
    If Not Err = 0 Then
        Set objSS = ThisDrawing.SelectionSets.Item("objSS")
        objSS.Clear
    End If
    
    objSS.Select acSelectionSetAll, , , filterType, filterValue
    MsgBox cbFromType.Value & " found:  " & objSS.count
    
    For Each objEntity In objSS
        strName = tbName.Value
        strDescription = Replace(tbDescription.Value, vbLf, "")
        strDescription = Replace(strDescription, vbCr, "<br/>")
        
        If TypeOf objEntity Is AcadPoint Then
            Set objPoint = objEntity
            dEast = objPoint.Coordinates(0)
            dNorth = objPoint.Coordinates(1)
            vLL = TN83FtoLL(CDbl(dNorth), CDbl(dEast))
            
            If InStr(strName, "{") > 0 Or InStr(strDescription, "{") > 0 Then
                boolVal = ODRcs.Init(objEntity, True, False)
                Set ODRc = ODRcs.Record
                
                If InStr(strName, "}") > 0 Then
                    vLine = Split(strName, "}")
                    For i = 0 To UBound(vLine)
                        vItem = Split(vLine(i), "{")
                        iIndex = CInt(vItem(1))
                        
                        strFind = "{" & iIndex & "}"
                        strReplace = ODRc.Item(iIndex).Value
                        strName = Replace(strName, strFind, strReplace)
                    Next i
                End If
                
                If InStr(strDescription, "}") > 0 Then
                    vLine = Split(strDescription, "}")
                    For i = 0 To UBound(vLine)
                        vItem = Split(vLine(i), "{")
                        iIndex = CInt(vItem(1))
                        
                        strFind = "{" & iIndex & "}"
                        strReplace = ODRc.Item(iIndex).Value
                        strDescription = Replace(strDescription, strFind, strReplace)
                    Next i
                End If
            End If
            
            GoTo Add_Point
        End If
        
        If TypeOf objEntity Is AcadBlockReference Then
            Set objBlock = objEntity
            vAttList = objBlock.GetAttributes
            If vAttList(0).TextString = "POLE" Then GoTo Next_Entity
            
            dEast = objBlock.InsertionPoint(0)
            dNorth = objBlock.InsertionPoint(1)
            vLL = TN83FtoLL(CDbl(dNorth), CDbl(dEast))
            
            If InStr(strName, "}") > 0 Then
                vLine = Split(strName, "}")
                For i = 0 To UBound(vLine)
                    vItem = Split(vLine(i), "{")
                    iIndex = CInt(vItem(1))
                    
                    strFind = "{" & iIndex & "}"
                    strReplace = vAttList(iIndex).TextString
                    strName = Replace(strName, strFind, strReplace)
                Next i
            End If
            
            If InStr(strDescription, "}") > 0 Then
                vLine = Split(strDescription, "}")
                For i = 0 To UBound(vLine)
                    vItem = Split(vLine(i), "{")
                    iIndex = CInt(vItem(1))
                    
                    strFind = "{" & iIndex & "}"
                    strReplace = vAttList(iIndex).TextString
                    strDescription = Replace(strDescription, strFind, strReplace)
                Next i
            End If
            
            GoTo Add_Point
        End If
        
        GoTo Next_Entity
        
Add_Point:
            
        strItem = "<Placemark>" & vbCr
            
        If Not strName = "" Then strItem = strItem & "<name>" & strName & "</name>" & vbCr & "<styleUrl>#size_label</styleUrl>" & vbCr
        If Not strDescription = "" Then strItem = strItem & "<description>" & strDescription & "</description>" & vbCr
        strItem = strItem & strStyle
        
        strItem = strItem & "<Point>" & vbCr & "<coordinates>" & vLL(1) & "," & vLL(0) & "</coordinates>" & vbCr
        strItem = strItem & "</Point>" & vbCr & "</Placemark>" & vbCr
        
        strFile = strFile & strItem & vbCr
Next_Entity:
    Next objEntity
    
    strFile = strFile & "</Document>" & vbCr & "</kml>"
    
    'tbOutput.Value = strFile
    Open strFileName For Output As #1
    
    Print #1, strFile
    Close #1
    
Exit_Sub:
    objSS.Clear
    objSS.Delete
End Sub

Private Sub cbFromList_Change()
    Dim filterType, filterValue As Variant
    Dim grpCode(0) As Integer
    Dim grpValue(0) As Variant
    Dim objSS2 As AcadSelectionSet
    
    On Error Resume Next
    
    If cbFromType.Value = "Block" Then
        Dim objBlock As AcadBlockReference
        Dim vAttList As Variant
    
        grpCode(0) = 2
        grpValue(0) = cbFromList.Value
        filterType = grpCode
        filterValue = grpValue
    
        Err = 0
        Set objSS2 = ThisDrawing.SelectionSets.Add("objSS2")
        If Not Err = 0 Then
            Set objSS2 = ThisDrawing.SelectionSets.Item("objSS2")
            objSS2.Clear
        End If
    
        objSS2.Select acSelectionSetAll, , , filterType, filterValue
        
        For Each objBlock In objSS2
            vAttList = objBlock.GetAttributes
            lbFrom.Clear
            For i = 0 To UBound(vAttList)
                lbFrom.AddItem
                lbFrom.List(i, 0) = i
                lbFrom.List(i, 1) = vAttList(i).TagString
            Next i
            GoTo Exit_Next
        Next objBlock
Exit_Next:
    Else
        Dim amap As AcadMap
        Dim ODRcs As ODRecords
        Dim ODRc As ODRecord
        Dim tbl As ODTable
        Dim tbls As ODTables
        Dim refColumn As ODFieldDef
        Dim objEntity As AcadEntity
        Dim boolVal As Boolean
        Dim iCount As Integer
        Dim strTest As String
    
        Set amap = ThisDrawing.Application.GetInterfaceObject("AutoCADMap.Application")
    
        Set tbls = amap.Projects(ThisDrawing).ODTables
        If tbls.count > 0 Then
            For Each tbl In tbls
                If tbl.Name = cbFromList.Value Then GoTo Exit_For
            Next
        End If
Exit_For:

        Set ODRcs = tbl.GetODRecords
        
        iCount = 0
        Err = 0
        
        While Err = 0
            Set refColumn = tbl.ODFieldDefs(iCount)
            strTest = refColumn.Name
            If Not Err = 0 Then GoTo Exit_objEntity
            
            lbFrom.AddItem
            lbFrom.List(iCount, 0) = iCount
            lbFrom.List(iCount, 1) = strTest
            iCount = iCount + 1
        Wend
        
Exit_objEntity:
    End If
    
    objSS2.Clear
    objSS2.Delete
End Sub

Private Sub cbFromType_Change()
    Select Case cbFromType.Value
        Case "Block"
            Dim objBlocks As AcadBlocks
            Dim strLine As String
            
            Set objBlocks = ThisDrawing.Blocks
            For i = 0 To objBlocks.count - 1
                strLine = objBlocks(i).Name
                If Not Left(strLine, 1) = "*" Then cbFromList.AddItem objBlocks(i).Name
            Next i
        Case "Point w/OD"
            Dim amap As AcadMap
            Dim tbl As ODTable
            Dim tbls As ODTables
    
            Set amap = ThisDrawing.Application.GetInterfaceObject("AutoCADMap.Application")
    
            Set tbls = amap.Projects(ThisDrawing).ODTables
            If tbls.count > 0 Then
                cbFromList.Clear
                For Each tbl In tbls
                    cbFromList.AddItem tbl.Name
                Next
            End If
    End Select
End Sub

Private Sub CommandButton1_Click()

End Sub

Private Sub cbIconFolder_Change()
    cbIcon.Clear
    
    Select Case cbIconFolder.Value
        Case "shapes"
            cbIcon.AddItem "placemark_circle"
            cbIcon.AddItem "placemark_square"
            cbIcon.AddItem "square"
            cbIcon.AddItem "star"
            cbIcon.AddItem "polygon"
            cbIcon.AddItem "open-diamond"
            cbIcon.AddItem "shaded_dot"
            cbIcon.AddItem "target"
            cbIcon.AddItem "triangle"
            cbIcon.AddItem "donut"
            cbIcon.AddItem "cross-hairs"
            
            cbIcon.AddItem "phone"
            cbIcon.AddItem "homegardenbusiness"
            cbIcon.AddItem "schools"
            cbIcon.AddItem "church"
            cbIcon.AddItem "arrow"
            cbIcon.AddItem "flag"
            cbIcon.AddItem "caution"
            cbIcon.AddItem "marina"
            cbIcon.AddItem "mechanic"
        Case "pushpin"
            cbIcon.AddItem "blue-pushpin"
            cbIcon.AddItem "grn-pushpin"
            cbIcon.AddItem "ltblu-pushpin"
            cbIcon.AddItem "pink-pushpin"
            cbIcon.AddItem "purple-pushpin"
            cbIcon.AddItem "red-pushpin"
            cbIcon.AddItem "wht-pushpin"
            cbIcon.AddItem "ylw-pushpin"
        Case "paddle"
            cbIcon.AddItem "1"
            cbIcon.AddItem "2"
            cbIcon.AddItem "3"
            cbIcon.AddItem "4"
            cbIcon.AddItem "5"
            cbIcon.AddItem "6"
            cbIcon.AddItem "7"
            cbIcon.AddItem "8"
            cbIcon.AddItem "9"
            cbIcon.AddItem "10"
            cbIcon.AddItem "A"
            cbIcon.AddItem "B"
            cbIcon.AddItem "C"
            cbIcon.AddItem "D"
            cbIcon.AddItem "E"
            cbIcon.AddItem "F"
            cbIcon.AddItem "G"
            cbIcon.AddItem "H"
            cbIcon.AddItem "red-blank"
            cbIcon.AddItem "red-circle"
            cbIcon.AddItem "red-diamond"
            cbIcon.AddItem "red-square"
            cbIcon.AddItem "red-stars"
            cbIcon.AddItem "orange-blank"
            cbIcon.AddItem "orange-circle"
            cbIcon.AddItem "orange-diamond"
            cbIcon.AddItem "orange-square"
            cbIcon.AddItem "orange-stars"
            cbIcon.AddItem "ylw-blank"
            cbIcon.AddItem "ylw-circle"
            cbIcon.AddItem "ylw-diamond"
            cbIcon.AddItem "ylw-square"
            cbIcon.AddItem "ylw-stars"
            cbIcon.AddItem "grn-circle"
            cbIcon.AddItem "grn-diamond"
            cbIcon.AddItem "grn-square"
            cbIcon.AddItem "grn-stars"
            cbIcon.AddItem "blu-blank"
            cbIcon.AddItem "blu-circle"
            cbIcon.AddItem "blu-diamond"
            cbIcon.AddItem "blu-square"
            cbIcon.AddItem "blu-stars"
            cbIcon.AddItem "grn-blank"
            cbIcon.AddItem "purple-blank"
            cbIcon.AddItem "purple-circle"
            cbIcon.AddItem "purple-diamond"
            cbIcon.AddItem "purple-square"
            cbIcon.AddItem "purple-stars"
    End Select
End Sub

Private Sub UserForm_Initialize()
    cbFromType.AddItem "Block"
    cbFromType.AddItem "Point w/OD"
    cbFromType.Value = "Point w/OD"
    
    lbFrom.Clear
    lbFrom.ColumnCount = 2
    lbFrom.ColumnWidths = "20;90"
    
    cbIconFolder.AddItem "shapes"
    cbIconFolder.AddItem "pushpin"
    cbIconFolder.AddItem "paddle"
    'cbIconFolder.AddItem ""
    
    tbFolder.Value = ThisDrawing.Path & "\"
    
    'Dim strLine As String
    
    'strLine = "<?xml version=""1.0"" encoding=""UTF-8""?>" & vbCr
    'strLine = strLine & "<kml xmlns=""http://www.opengis.net/kml/2.2"">" & vbCr
    'strLine = strLine & "<Document>" & vbCr & "Placemark>" & vbCr
    'strLine = strLine & "<name>Test</name>" & vbCr
    'strLine = strLine & "<description> This is a test point</description>" & vbCr
    'strLine = strLine & "<Point>" & vbCr & "<coordinates>-86.36249947,36.22776216</coordinates>" & vbCr
    'strLine = strLine & "</Point>" & vbCr & "</Placemark>" & vbCr & "</Document>" & vbCr & "</kml>"
    
    'tbOutput.Value = strLine
End Sub

Private Function TN83FtoLL(dNorth As Double, dEast As Double)
    Dim dLat, dLong, dDLat As Double
    Dim dDiffE, dEast0 As Double
    Dim dDiffN, dNorth0 As Double
    Dim dR, dCAR, dCA, dU, dK As Double
    Dim LL(2) As Double
    
    dEast = dEast * 0.3048006096
    dNorth = dNorth * 0.3048006096
    
    dDiffE = dEast - 600000
    dDiffN = dNorth - 166504.1691
    
    dR = 8842127.1422 - dDiffN
    dCAR = Atn(dDiffE / dR)
    dCA = dCAR * 180 / 3.14159265359
    dLong = -86 + dCA / 0.585439726459
    
    dU = dDiffN - dDiffE * Tan(dCAR / 2)
    dDLat = dU * (0.00000901305249 + dU * (-6.77268E-15 + dU * (-3.72351E-20 + dU * -9.2828E-28)))
    dLat = 35.8340607459 + dDLat
    
    dK = 0.999948401424 + (1.23188E-14 * dU * dU) + (4.54E-22 * dU * dU * dU)
    
    LL(0) = dLat
    LL(1) = dLong
    LL(2) = dK
    
    TN83FtoLL = LL
End Function

Attribute VB_Name = "CreateMCL"
Attribute VB_Base = "0{EB2D4DC3-FB97-4A69-998F-39108E9A64A2}{156E2E07-DEF4-4894-B588-6CAE287F1110}"
Attribute VB_GlobalNameSpace = False
Attribute VB_Creatable = False
Attribute VB_PredeclaredId = True
Attribute VB_Exposed = False
Attribute VB_TemplateDerived = False
Attribute VB_Customizable = False
Private Sub cbClearPanel_Click()
    lbCounts.Clear
End Sub

Private Sub cbClearSelected_Click()
    If lbCounts.ListCount < 1 Then Exit Sub
    
    For i = 0 To lbCounts.ListCount - 1
        If lbCounts.Selected(i) = True Then
            lbCounts.List(i, 1) = "<>"
            lbCounts.List(i, 2) = "<>"
            lbCounts.List(i, 3) = "<>"
            lbCounts.List(i, 4) = "<>"
            lbCounts.List(i, 5) = "<>"
        End If
    Next i
End Sub

Private Sub cbCreatePanel_Click()
    If tbF1Name.Value = "" Then Exit Sub
    
    'Label42.Enabled = False
    'Label43.Enabled = False
    'tbStartFiber.Enabled = False
    'tbEndFiber.Enabled = False
    'cbCreatePanel.Enabled = False
    'lbCounts.Clear
    
    Dim iStart, iEnd As Integer
    
    iStart = CInt(tbStartFiber.Value)
    iEnd = CInt(tbEndFiber.Value)
    
    For i = iStart To iEnd
        lbCounts.AddItem i
        lbCounts.List(lbCounts.ListCount - 1, 1) = "<>"
        lbCounts.List(lbCounts.ListCount - 1, 2) = "<>"
        lbCounts.List(lbCounts.ListCount - 1, 3) = "<>"
        lbCounts.List(lbCounts.ListCount - 1, 4) = "<>"
        lbCounts.List(lbCounts.ListCount - 1, 5) = "<>"
    Next i
End Sub

Private Sub cbMarkSelected_Click()
    If lbCounts.ListCount < 1 Then Exit Sub
    If tbMark.Value = "" Then Exit Sub
    
    For i = 0 To lbCounts.ListCount - 1
        If lbCounts.Selected(i) = True Then
            lbCounts.List(i, 1) = tbMark.Value
            lbCounts.List(i, 2) = tbMark.Value
            lbCounts.List(i, 3) = tbMark.Value
            lbCounts.List(i, 4) = tbMark.Value
            lbCounts.List(i, 5) = tbMark.Value
        End If
    Next i
End Sub

Private Sub cbMoveSelected_Click()
    If lbCounts.ListCount < 1 Then Exit Sub
    
    Dim iCount As Integer
    Dim strList(5) As String
    
    iCount = lbCounts.ListCount - 1
    For i = iCount To 0 Step -1
        If lbCounts.Selected(i) = True Then
            strList(0) = lbCounts.List(i, 0)
            strList(1) = lbCounts.List(i, 1)
            strList(2) = lbCounts.List(i, 2)
            strList(3) = lbCounts.List(i, 3)
            strList(4) = lbCounts.List(i, 4)
            strList(5) = lbCounts.List(i, 5)
            
            lbCounts.Selected(i) = False
            lbCounts.RemoveItem i
            lbCounts.AddItem strList(0), 0
            lbCounts.List(0, 1) = strList(1)
            lbCounts.List(0, 2) = strList(2)
            lbCounts.List(0, 3) = strList(3)
            lbCounts.List(0, 4) = strList(4)
            lbCounts.List(0, 5) = strList(5)
            
            i = i + 1
        End If
    Next i
End Sub

Private Sub cbOpenMCL_Click()
    If tbF1Name.Value = "" Then Exit Sub
    lbCounts.Clear
    
    Dim strFileName As String
    Dim vName, vLine, vItem As Variant
    Dim vFile As Variant
    Dim fName As String
    
    vName = Split(ThisDrawing.Name, " ")
    strFileName = ThisDrawing.Path & "\" & vName(0) & " Counts -" & tbF1Name.Value & ".mcl"
    
    fName = Dir(strFileName)
    If fName = "" Then
        'Label42.Enabled = True
        'Label43.Enabled = True
        'tbStartFiber.Enabled = True
        'tbEndFiber.Enabled = True
        'cbCreatePanel.Enabled = True
        
        tbStartFiber.SetFocus
        Exit Sub
    End If
    
    Open strFileName For Input As #1
    vFile = Split(Input$(LOF(1), 1), vbCrLf)
    Close #1
    
    For i = 1 To UBound(vFile)
        If vFile(i) = "" Then GoTo Next_I
        vLine = Split(vFile(i), vbTab)
        
        lbCounts.AddItem vLine(0)
        lbCounts.List(lbCounts.ListCount - 1, 1) = vLine(1)
        lbCounts.List(lbCounts.ListCount - 1, 2) = vLine(2)
        lbCounts.List(lbCounts.ListCount - 1, 3) = vLine(3)
        lbCounts.List(lbCounts.ListCount - 1, 4) = vLine(4)
        lbCounts.List(lbCounts.ListCount - 1, 5) = vLine(5)
Next_I:
    Next i
End Sub

Private Sub cbRemoveSelected_Click()
    If lbCounts.ListCount < 1 Then Exit Sub
    
    For i = lbCounts.ListCount - 1 To 0 Step -1
        If lbCounts.Selected(i) = True Then lbCounts.RemoveItem i
    Next i
End Sub

Private Sub cbSavePanel_Click()
    If tbF1Name.Value = "" Then Exit Sub
    
    Dim strFileName As String
    Dim vName As Variant
    Dim fName, strLine As String
    
    vName = Split(ThisDrawing.Name, " ")
    strFileName = ThisDrawing.Path & "\" & vName(0) & " Counts -" & tbF1Name.Value & ".mcl"
    
    Open strFileName For Output As #1
    
    Print #1, tbF1Name.Value & " FIBER COUNTS"
    For i = 0 To lbCounts.ListCount - 1
        strLine = lbCounts.List(i, 0) & vbTab & lbCounts.List(i, 1) & vbTab & lbCounts.List(i, 2) & vbTab & lbCounts.List(i, 3)
        strLine = strLine & vbTab & lbCounts.List(i, 4) & vbTab & lbCounts.List(i, 5)
        Print #1, strLine
    Next i
    
    Close #1
End Sub

Private Sub tbF1Name_Exit(ByVal Cancel As MSForms.ReturnBoolean)
    tbF1Name.Value = UCase(tbF1Name.Value)
End Sub

Private Sub UserForm_Initialize()
    lbCounts.Clear
    lbCounts.ColumnCount = 6
    lbCounts.ColumnWidths = "30;72;36;144;48;108"
    
End Sub

Attribute VB_Name = "CreateNESPoles"
Attribute VB_Base = "0{BE699A24-CE32-4760-93ED-E930ECFBBA50}{7F46BD10-37BD-4164-9D44-011005265B53}"
Attribute VB_GlobalNameSpace = False
Attribute VB_Creatable = False
Attribute VB_PredeclaredId = True
Attribute VB_Exposed = False
Attribute VB_TemplateDerived = False
Attribute VB_Customizable = False

Private Sub cbCompany_Change()
    If tbPaste.Value = "" Then Exit Sub
    
    If cbCompany.Value = "NES" Then
        Call GetNESData
    Else
        Call GetMTEData
    End If
End Sub

Private Sub cbPlace_Click()
    If tbCoords.Value = "" Then Exit Sub
    
    Dim obrNES As AcadBlockReference
    Dim vAttList, vTemp As Variant
    Dim dCoords(0 To 2) As Double
    Dim dPoint(2) As Double
    Dim vNE As Variant
    Dim iCount As Integer
    
    vTemp = Split(tbCoords.Value, ", ")
    vNE = LLtoTN83F(CDbl(vTemp(0)), CDbl(vTemp(1)))
    dCoords(0) = vNE(1)
    dCoords(1) = vNE(0)
    dCoords(2) = 0#
    
    iCount = 16
    
    Set obrNES = ThisDrawing.ModelSpace.InsertBlock(dCoords, "sPole", 1#, 1#, 1#, 0#)
    vAttList = obrNES.GetAttributes
    
    vAttList(0).TextString = tbOwner.Value & " POLE"
    If Not tbType.Value = "" Then vAttList(1).TextString = tbType.Value
    vAttList(2).TextString = tbOwner.Value
    vAttList(3).TextString = tbNumber.Value
    'vAttList(25).TextString = tbID.Value
    vAttList(5).TextString = tbHC.Value
    vAttList(7).TextString = tbCoords.Value
    
    Select Case cbCompany.Value
        Case "NES"
            If tbOwner.Value = "NES" Then
                obrNES.Layer = "Integrity Poles-Power"
            Else
                obrNES.Layer = "Integrity Poles-Other"
            End If
        Case Else
            If InStr(tbOwner.Value, "MTE") > 0 Then
                obrNES.Layer = "Integrity Poles-Power"
            Else
                obrNES.Layer = "Integrity Poles-Other"
            End If
    End Select
    
    If lbCOMMs.ListCount > 0 Then
        For i = 0 To lbCOMMs.ListCount - 1
            vAttList(iCount).TextString = lbCOMMs.List(i) & "="
            iCount = iCount + 1
        Next i
    End If
    
    'vAttList(16).TextString = "CLIENT="
    
    'If lbCOMMs.ListCount > 0 Then
        
    'End If
    
    obrNES.Update
End Sub

Private Sub cbQuit_Click()
    ThisDrawing.SendCommand "_QSAVE" & vbCr
    
    Me.Hide
End Sub

Private Sub LabelPan_Click()
    Dim entPole As AcadObject
    Dim basePnt As Variant
    
    Me.Hide
  On Error Resume Next
    
    ThisDrawing.Utility.GetEntity entPole, basePnt, "Left Click to Exit: "
    
    Me.show
End Sub

Private Sub tbPaste_Change()
    If tbPaste.Value = "" Then Exit Sub
    
    If cbCompany.Value = "NES" Then
        Call GetNESData
    Else
        Call GetMTEData
    End If
    
    Exit Sub
    
    Dim strAll, strTemp As String
    Dim vList As Variant
    Dim iCOMMs As Integer
    
    strAll = Replace(tbPaste.Value, vbLf, "")
    vList = Split(strAll, vbCr)
    iCOMMs = 0
    
    For i = 0 To UBound(vList)
        Select Case vList(i)
            Case "Location"
                tbCoords.Value = vList(i + 1)
            Case "Pole Number"
                tbNumber.Value = vList(i + 1)
            Case "Class"
                strTemp = vList(i + 3) & "-" & vList(i + 1)
                tbHC.Value = strTemp
            Case "Owner"
                tbOwner.Value = vList(i + 1)
            Case "Pole Oid"
                tbID.Value = vList(i + 1)
            Case "Type"
                If iCOMMs = 0 Then tbType.Value = vList(i + 1)
            Case "Asset Attachments"
                iCOMMs = 1
                i = i + 1
                lbCOMMs.AddItem vList(i)
                i = i + 4
            Case Else
                If iCOMMs = 1 Then
                    For j = 0 To lbCOMMs.ListCount - 1
                        If lbCOMMs.List(j) = vList(i) Then GoTo Found_COMM
                    Next j
                    
                    lbCOMMs.AddItem vList(i)
Found_COMM:
                    i = i + 4
                End If
        End Select
    Next i
End Sub

Private Sub tbPaste_Enter()
   tbPaste.Value = ""
    lbCOMMs.Clear
End Sub

Private Sub tbPaste_Error(ByVal Number As Integer, ByVal Description As MSForms.ReturnString, ByVal SCode As Long, ByVal Source As String, ByVal HelpFile As String, ByVal HelpContext As Long, ByVal CancelDisplay As MSForms.ReturnBoolean)
    tbPaste.Value = ""
    lbCOMMs.Clear
End Sub

Private Sub UserForm_Initialize()
    cbCompany.AddItem "NES"
    cbCompany.AddItem "MTE"
    cbCompany.Value = "NES"
End Sub

Private Function LLtoTN83F(dLat As Double, dLong As Double)
    Dim dDLat As Double
    Dim dEast, dDiffE, dEast0 As Double
    Dim dNorth, dDiffN, dNorth0 As Double
    Dim dU, dR, dCA, dK As Double
    Dim NE(2) As Double
    
    dDLat = dLat - 35.8340607459
    dU = dDLat * (110950.2019 + dDLat * (9.25072 + dDLat * (5.64572 + dDLat * 0.017374)))
    dR = 8842127.1422 - dU
    dCA = ((86 + dLong) * 0.585439726459) * 3.14159265359 / 180
    
    dDiffE = dR * Sin(dCA)
    dDiffN = dU + dDiffE * Tan(dCA / 2)
    
    dEast = (dDiffE + 600000) / 0.3048006096
    dNorth = (dDiffN + 166504.1691) / 0.3048006096
    
    dK = 0.999948401424 + (1.23188E-14 * dU * dU) + (4.54E-22 * dU * dU * dU)
    
    NE(0) = dNorth
    NE(1) = dEast
    NE(2) = dK
    
    LLtoTN83F = NE
End Function

Private Sub GetNESData()
    If tbPaste.Value = "" Then Exit Sub
    
    Dim strAll, strTemp As String
    Dim vList As Variant
    Dim iCOMMs As Integer
    
    strAll = Replace(tbPaste.Value, vbLf, "")
    vList = Split(strAll, vbCr)
    iCOMMs = 0
    
    For i = 0 To UBound(vList)
        Select Case vList(i)
            Case "Location"
                tbCoords.Value = vList(i + 1)
            Case "Pole Number"
                tbNumber.Value = vList(i + 1)
            Case "Class"
                strTemp = vList(i + 3) & "-" & vList(i + 1)
                tbHC.Value = strTemp
            Case "Owner"
                tbOwner.Value = vList(i + 1)
            Case "Pole Oid"
                tbID.Value = vList(i + 1)
            Case "Type"
                If iCOMMs = 0 Then tbType.Value = vList(i + 1)
            Case "Asset Attachments"
                iCOMMs = 1
                i = i + 1
                lbCOMMs.AddItem vList(i)
                i = i + 4
            Case Else
                If iCOMMs = 1 Then
                    For j = 0 To lbCOMMs.ListCount - 1
                        If lbCOMMs.List(j) = vList(i) Then GoTo Found_COMM
                    Next j
                    
                    lbCOMMs.AddItem vList(i)
Found_COMM:
                    i = i + 4
                End If
        End Select
    Next i
End Sub

Private Sub GetMTEData()
    If tbPaste.Value = "" Then Exit Sub
    
    Dim strAll, strTemp As String
    Dim vList As Variant
    Dim iCOMMs As Integer
    
    strAll = Replace(tbPaste.Value, vbLf, "")
    vList = Split(strAll, vbCr)
    iCOMMs = 0
    
    For i = 0 To UBound(vList)
        Select Case vList(i)
            Case "Location"
                tbCoords.Value = vList(i + 1)
            Case "Pole Number"
                tbNumber.Value = vList(i + 1)
            Case "Class"
                strTemp = vList(i + 3) & "-" & vList(i + 1)
                tbHC.Value = strTemp
            Case "Ownership Code"
                tbOwner.Value = vList(i + 1)
            Case "Fid Number"
                tbID.Value = vList(i + 1)
        End Select
    Next i
    
    tbType.Value = "INCOMPLETE"
End Sub

Attribute VB_Name = "CreateTDOT"
Attribute VB_Base = "0{ACABAF96-8E7A-4B87-80CC-23988D6027CB}{DDD25C23-CDD5-43B5-9334-C6025B440BE4}"
Attribute VB_GlobalNameSpace = False
Attribute VB_Creatable = False
Attribute VB_PredeclaredId = True
Attribute VB_Exposed = False
Attribute VB_TemplateDerived = False
Attribute VB_Customizable = False
Private Sub cbCopyLayers_Click()
    Call CopyLayers
    
    Dim entPole As AcadObject
    Dim basePnt As Variant
    
    Me.Hide
  On Error Resume Next
    
    ThisDrawing.Utility.GetEntity entPole, basePnt, "Left Click to Exit: "
    
    Call CurrentLayers
    
    Me.show
End Sub

Private Sub cbCurrent_Click()
    'Call CurrentLayers
End Sub

Private Sub cbExport_Click()
    If tbFile.Value = "" Then Exit Sub
    
    Dim strText, strFileName As String
    
    strFileName = "C:\Integrity\VBA\References\"
    strFileName = strFileName & tbFile.Value & ".plt"
    
    strText = "<<LAYERS>>" & vbCr
    
    If lbLayers.ListCount > 0 Then
        For i = 0 To lbLayers.ListCount - 1
            If lbLayers.List(i, 2) = "YES" Then
                strText = strText & lbLayers.List(i, 0) & vbCr
            End If
        Next i
    End If
    
    strText = strText & vbCr & "<<BLOCKS>>" & vbCr
    
    If lbBlocks.ListCount > 0 Then
        For i = 0 To lbBlocks.ListCount - 1
            If lbBlocks.List(i, 1) = "YES" Then
                strText = strText & lbBlocks.List(i, 0) & vbCr
            End If
        Next i
    End If
    
    Open strFileName For Output As #1
    
    Print #1, strText
    
    Close #1
End Sub

Private Sub cbImport_Click()
    If lbFiles.ListCount < 1 Then Exit Sub
    If lbFiles.ListIndex < 0 Then Exit Sub
    
    tbFile.Value = lbFiles.List(lbFiles.ListIndex)
    
    Dim strLine, strFileName As String
    Dim strLayers, strBlocks As String
    Dim vLayers, vBlocks As Variant
    Dim fName As String
    Dim iStatus As Integer
    
    strFileName = "C:\Integrity\VBA\References\"
    strFileName = strFileName & lbFiles.List(lbFiles.ListIndex) & ".plt"
    
    iStatus = 0
    strLayers = ""
    strBlocks = ""
    
    fName = Dir(strFileName)
    If fName = "" Then
        Exit Sub
    End If
    
    Open strFileName For Input As #2
    
    While Not EOF(2)
        Input #2, strLine
        
        Select Case strLine
            Case "<<LAYERS>>"
                iStatus = 1
            Case "<<BLOCKS>>"
                iStatus = 2
            Case Else
                If iStatus = 1 Then
                    If strLayers = "" Then
                        strLayers = strLine
                    Else
                        strLayers = strLayers & vbTab & strLine
                    End If
                Else
                    If strBlocks = "" Then
                        strBlocks = strLine
                    Else
                        strBlocks = strBlocks & vbTab & strLine
                    End If
                End If
        End Select
Next_line:
    Wend
    
    Close #2
    
    If Not strLayers = "" Then
        vLayers = Split(strLayers, vbTab)
        
        If lbLayers.ListCount > 0 Then
            For i = 0 To lbLayers.ListCount - 1
                For j = 0 To UBound(vLayers)
                    If lbLayers.List(i, 0) = vLayers(j) Then
                        lbLayers.List(i, 2) = "YES"
                        GoTo Next_Layer
                    End If
                Next j
Next_Layer:
            Next i
        End If
    End If
    
    If Not strBlocks = "" Then
        vBlocks = Split(strBlocks, vbTab)
        
        If lbBlocks.ListCount > 0 Then
            For i = 0 To lbBlocks.ListCount - 1
                For j = 0 To UBound(vBlocks)
                    If lbBlocks.List(i, 0) = vBlocks(j) Then
                        lbBlocks.List(i, 1) = "YES"
                        GoTo Next_Block
                    End If
                Next j
Next_Block:
            Next i
        End If
    End If
End Sub

Private Sub cbMaptrim_Click()
    Dim objSSM1 As AcadSelectionSet
    Dim objEntity As AcadEntity
    Dim objEntTemp As AcadEntity
    Dim objRemove(0) As AcadEntity
    Dim objLWP As AcadLWPolyline
    Dim objLWPBorder As AcadLWPolyline
    Dim objSSBlock As AcadBlockReference
    Dim objBlock As AcadBlockReference
    Dim objLayer As AcadLayer
    Dim strCommand As String
    Dim strHandle As String
    Dim strRemove As String
    Dim strBlocks As String
    Dim vBlocks As Variant
    Dim vReturnPnt As Variant
    Dim vCoords As Variant
    Dim dLL(0 To 2) As Double
    Dim dUR(0 To 2) As Double
    Dim dLL1(0 To 2) As Double
    Dim dUR1(0 To 2) As Double
    Dim dFrom(0 To 2) As Double
    Dim dTo(0 To 2) As Double
    Dim dDiff(0 To 1) As Double
    Dim dScale As Double
    
  On Error Resume Next
    'Select boundary & find drawing number
    
    strBlocks = ""
    For i = 0 To lbBlocks.ListCount - 1
        If lbBlocks.List(i, 1) = "YES" Then
            If strBlocks = "" Then
                strBlocks = lbBlocks.List(i, 0)
            Else
                strBlocks = strBlocks & vbTab & lbBlocks.List(i, 0)
            End If
        End If
    Next i
    
    If Not strBlocks = "" Then vBlocks = Split(strBlocks, vbTab)
    
    Me.Hide
    
    Err = 0
    Set objSSM1 = ThisDrawing.SelectionSets.Add("objSSM1")
    If Not Err = 0 Then
        Set objSSM1 = ThisDrawing.SelectionSets.Item("objSSM1")
        Err = 0
    End If
    
    Call CopyLayers
    
  While Err = 0
    
    ThisDrawing.Utility.GetEntity objEntity, vReturnPnt, "Select Trim Border: "
    If Not objEntity.ObjectName = "AcDbPolyline" Then GoTo Exit_Sub
    
    Set objLWP = objEntity
    vCoords = objLWP.Coordinates
    
    dLL(0) = vCoords(0)
    dLL(1) = vCoords(1)
    dUR(0) = vCoords(0)
    dUR(1) = vCoords(1)
    
    For i = 2 To UBound(vCoords)
        If vCoords(i) < dLL(0) Then
            dLL(0) = vCoords(i)
        Else
            If vCoords(i) > dUR(0) Then
                dUR(0) = vCoords(i)
            End If
        End If
        
        i = i + 1
        
        If vCoords(i) < dLL(1) Then
            dLL(1) = vCoords(i)
        Else
            If vCoords(i) > dUR(1) Then
                dUR(1) = vCoords(i)
            End If
        End If
    Next i
    
    dFrom(0) = (dLL(0) + dUR(0)) / 2
    dFrom(1) = (dLL(1) + dUR(1)) / 2
    
    'Get coordinates to DWG Sheet and draw LWP (Save strHandle)
    
    ThisDrawing.Utility.GetEntity objEntity, vReturnPnt, "Select DWG Border: "
    If TypeOf objEntity Is AcadBlockReference Then
        Set objSSBlock = objEntity
    Else
        MsgBox "Not a valid entity."
        GoTo Exit_Sub
    End If
    
    dScale = objSSBlock.XScaleFactor
    strRemove = objSSBlock.Layer
    
    dTo(0) = objSSBlock.InsertionPoint(0) + (825 * dScale)
    dTo(1) = objSSBlock.InsertionPoint(1) + (525 * dScale)
    dTo(2) = 0#
    
    dDiff(0) = dTo(0) - dFrom(0)
    dDiff(1) = dTo(1) - dFrom(1)
    
    Set objLWPBorder = ThisDrawing.ModelSpace.AddLightWeightPolyline(vCoords)
    objLWPBorder.Closed = True
    objLWPBorder.Layer = objLWP.Layer
    objLWPBorder.Move dFrom, dTo
    objLWPBorder.Update
    strHandle = objLWPBorder.Handle
    
    'Get objects crossing within dimensions of DWG and copy to DWG
    
    objSSM1.Select acSelectionSetCrossing, dLL, dUR
    
    If objSSM1.count = 0 Then GoTo Exit_Sub
    
    If Not strBlocks = "" Then
        For Each objEntTemp In objSSM1
            If TypeOf objEntTemp Is AcadBlockReference Then
                Set objBlock = objEntTemp
                
                For i = 0 To UBound(vBlocks)
                    If objBlock.Name = vBlocks(i) Then GoTo Next_objEntTemp
                Next i
            
            'If objEntTemp.Layer = strRemove Then
                Set objRemove(0) = objEntTemp
                objSSM1.RemoveItems objRemove
            End If
Next_objEntTemp:
        Next objEntTemp
    End If
    
    strCommand = "COPY" & vbCr & "P" & vbCr & vbCr
    strCommand = strCommand & dFrom(0) & "," & dFrom(1) & ",0" & vbCr
    strCommand = strCommand & dTo(0) & "," & dTo(1) & ",0" & vbCr & vbCr
    
    ThisDrawing.SetVariable "CMDDIA", 0
    ThisDrawing.SendCommand strCommand
    
    objSSM1.Clear
    
    Set objLayer = ThisDrawing.Layers(strRemove)
    objLayer.Lock = True
    
    dLL1(0) = dLL(0) + dDiff(0)
    dLL1(1) = dLL(1) + dDiff(1)
    dUR1(0) = dUR(0) + dDiff(0)
    dUR1(1) = dUR(1) + dDiff(1)
    
    objSSM1.Select acSelectionSetCrossing, dLL1, dUR1
        
    For Each objEntTemp In objSSM1
        If objEntTemp.Layer = strRemove Then
            Set objRemove(0) = objEntTemp
            objSSM1.RemoveItems objRemove
        End If
    Next objEntTemp
    
    strCommand = "_MAPTRIM" & vbCr & "S" & vbCr & "(handent """ & strHandle & """)" & vbCr
    strCommand = strCommand & "N" & vbCr & "Y" & vbCr & "P" & vbCr & vbCr & "O" & vbCr
    strCommand = strCommand & "Y" & vbCr & "Y" & vbCr & "R" & vbCr & "Y" & vbCr

    ThisDrawing.SendCommand strCommand
    
    objSSM1.Clear
    
    objLayer.Lock = False
  Wend
    
Exit_Sub:
    Call CurrentLayers
    
    objSSM1.Delete
    
    ThisDrawing.SetVariable "CMDDIA", 1
    Me.show
End Sub

Private Sub cbQuit_Click()
    Me.Hide
End Sub

Private Sub cbSelectBlocks_Click()
    If lbBlocks.ListCount < 1 Then Exit Sub
    
    Dim objEntity As AcadEntity
    Dim objBlock As AcadBlockReference
    Dim vReturnPnt As Variant
    Dim strName As String
    
    On Error Resume Next
    
    Me.Hide
    
Get_Another:
    
    ThisDrawing.Utility.GetEntity objEntity, vReturnPnt, vbCr & "Select Block:"
    If Not Err = 0 Then GoTo Exit_Sub
    
    If Not TypeOf objEntity Is AcadBlockReference Then GoTo Exit_Sub
    Set objBlock = objEntity
    
    strName = objBlock.Name
    
    For i = 0 To lbBlocks.ListCount - 1
        If lbBlocks.List(i, 0) = strName Then
            lbBlocks.List(i, 1) = "YES"
            GoTo Get_Another
        End If
    Next i
    
Exit_Sub:
    Me.show
End Sub

Private Sub cbSelectLayer_Click()
    If lbLayers.ListCount < 1 Then Exit Sub
    
    Dim objEntity As AcadEntity
    Dim objBlock As AcadBlockReference
    Dim vReturnPnt As Variant
    Dim strLayer As String
    Dim strName As String
    
    On Error Resume Next
    
    Me.Hide
    
Get_Another:
    
    ThisDrawing.Utility.GetEntity objEntity, vReturnPnt, vbCr & "Select object on Layer:"
    If Not Err = 0 Then GoTo Exit_Sub
    
    strLayer = objEntity.Layer
    
    For i = 0 To lbLayers.ListCount - 1
        If lbLayers.List(i, 0) = strLayer Then
            lbLayers.List(i, 2) = "YES"
            GoTo Exit_Layers
        End If
    Next i
    
Exit_Layers:
    
    If TypeOf objEntity Is AcadBlockReference Then
        Set objBlock = objEntity
    
        strName = objBlock.Name
    
        For i = 0 To lbBlocks.ListCount - 1
            If lbBlocks.List(i, 0) = strName Then
                lbBlocks.List(i, 1) = "YES"
                GoTo Get_Another
            End If
        Next i
    End If
    
    GoTo Get_Another
    
Exit_Sub:
    Me.show
End Sub

Private Sub Label3_Click()
    If lbLayers.ListCount < 1 Then Exit Sub
    
    Dim strName, strStatus, strCopy As String
    Dim iIndex, iCount As Integer
    
    iIndex = 0
    
    For iCount = 0 To lbLayers.ListCount - 1
        If lbLayers.List(iCount, 2) = "YES" Then
            strName = lbLayers.List(iCount, 0)
            strStatus = lbLayers.List(iCount, 1)
            strCopy = lbLayers.List(iCount, 2)
            
            lbLayers.RemoveItem iCount
            lbLayers.AddItem strName, iIndex
            lbLayers.List(iIndex, 1) = strStatus
            lbLayers.List(iIndex, 2) = strCopy
            iIndex = iIndex + 1
        End If
    Next iCount
    
    lbLayers.ListIndex = 0
End Sub

Private Sub Label5_Click()
    If lbBlocks.ListCount < 1 Then Exit Sub
    
    Dim strName, strStatus As String
    Dim iIndex, iCount As Integer
    
    iIndex = 0
    
    For iCount = 0 To lbBlocks.ListCount - 1
        If lbBlocks.List(iCount, 1) = "YES" Then
            strName = lbBlocks.List(iCount, 0)
            strStatus = lbBlocks.List(iCount, 1)
            
            lbBlocks.RemoveItem iCount
            lbBlocks.AddItem strName, iIndex
            lbBlocks.List(iIndex, 1) = strStatus
            iIndex = iIndex + 1
        End If
    Next iCount
    
    lbBlocks.ListIndex = 0
End Sub

Private Sub LabelPan_Click()
    Dim entPole As AcadObject
    Dim basePnt As Variant
    
    Me.Hide
  On Error Resume Next
    
    ThisDrawing.Utility.GetEntity entPole, basePnt, "Left Click to Exit: "
    
    Me.show
End Sub

Private Sub lbBlocks_DblClick(ByVal Cancel As MSForms.ReturnBoolean)
    Select Case lbBlocks.List(lbBlocks.ListIndex, 1)
        Case "YES"
            lbBlocks.List(lbBlocks.ListIndex, 1) = ""
        Case Else
            lbBlocks.List(lbBlocks.ListIndex, 1) = "YES"
    End Select
End Sub

Private Sub lbLayers_DblClick(ByVal Cancel As MSForms.ReturnBoolean)
    Select Case lbLayers.List(lbLayers.ListIndex, 2)
        Case "YES"
            lbLayers.List(lbLayers.ListIndex, 2) = ""
        Case Else
            lbLayers.List(lbLayers.ListIndex, 2) = "YES"
    End Select
End Sub

Private Sub UserForm_Initialize()
    Dim strTFolder, strFile As String
    Dim vTemp As Variant
    strTFolder = "C:\Integrity\VBA\References\*.*"
    
    strFile = Dir$(strTFolder)
    
    Do While strFile <> ""
        If InStr(strFile, ".plt") Then
            lbFiles.AddItem Replace(strFile, ".plt", "")
        End If
        strFile = Dir$
    Loop

    lbLayers.ColumnCount = 3
    lbLayers.ColumnWidths = "180;60;48"
    
    lbBlocks.ColumnCount = 2
    lbBlocks.ColumnWidths = "126;48"
    
    Dim objLayers As AcadLayers
    Dim objLayer As AcadLayer
    
    Set objLayers = ThisDrawing.Layers
    For Each objLayer In objLayers
        lbLayers.AddItem objLayer.Name
        If objLayer.LayerOn = True Then
            lbLayers.List(lbLayers.ListCount - 1, 1) = "ON"
        Else
            lbLayers.List(lbLayers.ListCount - 1, 1) = "x"
        End If
        lbLayers.List(lbLayers.ListCount - 1, 2) = ""
    Next objLayer
    
    Call SortList
    
    Dim objBlocks As AcadBlocks
    Dim strLine As String
            
    Set objBlocks = ThisDrawing.Blocks
    For i = 0 To objBlocks.count - 1
        strLine = objBlocks(i).Name
        
        If Left(strLine, 1) = "*" Then GoTo Next_Block
        If Left(strLine, 2) = "A$" Then GoTo Next_Block
        
        lbBlocks.AddItem objBlocks(i).Name
        lbBlocks.List(lbBlocks.ListCount - 1, 1) = ""
        
Next_Block:
    Next i
    
    Call SortListBlocks
End Sub

Private Sub SortList()
    Dim a, b As Integer
    Dim iCount As Integer
    Dim strAtt(0 To 2) As String
    
    iCount = lbLayers.ListCount - 1
    If iCount < 1 Then Exit Sub
    
    On Error Resume Next
    
    For a = iCount To 0 Step -1
        For b = 0 To a - 1
            If lbLayers.List(b, 0) > lbLayers.List(b + 1, 0) Then
                If Not Err = 0 Then
                    MsgBox "Error sorting list"
                    lbLayers.Selected(b) = True
                    lbLayers.ListIndex = b
                    Exit Sub
                End If
                
                strAtt(0) = lbLayers.List(b + 1, 0)
                strAtt(1) = lbLayers.List(b + 1, 1)
                strAtt(2) = lbLayers.List(b + 1, 2)
                
                lbLayers.List(b + 1, 0) = lbLayers.List(b, 0)
                lbLayers.List(b + 1, 1) = lbLayers.List(b, 1)
                lbLayers.List(b + 1, 2) = lbLayers.List(b, 2)
                
                lbLayers.List(b, 0) = strAtt(0)
                lbLayers.List(b, 1) = strAtt(1)
                lbLayers.List(b, 2) = strAtt(2)
            End If
        Next b
    Next a
End Sub

Private Sub SortListBlocks()
    Dim a, b As Integer
    Dim iCount As Integer
    Dim strAtt(0 To 1) As String
    
    iCount = lbBlocks.ListCount - 1
    If iCount < 1 Then Exit Sub
    
    On Error Resume Next
    
    For a = iCount To 0 Step -1
        For b = 0 To a - 1
            If lbBlocks.List(b, 0) > lbBlocks.List(b + 1, 0) Then
                If Not Err = 0 Then
                    MsgBox "Error sorting list"
                    lbBlocks.Selected(b) = True
                    lbBlocks.ListIndex = b
                    Exit Sub
                End If
                
                strAtt(0) = lbBlocks.List(b + 1, 0)
                strAtt(1) = lbBlocks.List(b + 1, 1)
                
                lbBlocks.List(b + 1, 0) = lbBlocks.List(b, 0)
                lbBlocks.List(b + 1, 1) = lbBlocks.List(b, 1)
                
                lbBlocks.List(b, 0) = strAtt(0)
                lbBlocks.List(b, 1) = strAtt(1)
            End If
        Next b
    Next a
End Sub

Private Sub CopyLayers()
    If lbLayers.ListCount < 1 Then Exit Sub
    
    Dim objLayer As AcadLayer
    
    On Error Resume Next
    
    For i = 0 To lbLayers.ListCount - 1
        Set objLayer = ThisDrawing.Layers(lbLayers.List(i, 0))
        If objLayer Is Nothing Then
            Err = 0
            GoTo Next_I
        End If
        
        If InStr(lbLayers.List(i, 0), "Integrity Permits") > 0 Then
            objLayer.LayerOn = True
            objLayer.Lock = True
            GoTo Next_I
        End If
                
        Select Case lbLayers.List(i, 2)
            Case "YES"
                objLayer.LayerOn = True
            Case Else
                objLayer.LayerOn = False
        End Select
Next_I:
    Next i
    
    ThisDrawing.Regen acAllViewports
End Sub

Private Sub CurrentLayers()
    If lbLayers.ListCount < 1 Then Exit Sub
    
    Dim objLayer As AcadLayer
    
    On Error Resume Next
    
    For i = 0 To lbLayers.ListCount - 1
        Set objLayer = ThisDrawing.Layers(lbLayers.List(i, 0))
        If objLayer Is Nothing Then
            Err = 0
            MsgBox "Error"
            GoTo Next_I
        End If
                
        Select Case lbLayers.List(i, 1)
            Case "ON"
                objLayer.LayerOn = True
            Case Else
                objLayer.LayerOn = False
        End Select
        
        If InStr(lbLayers.List(i, 0), "Integrity Permits") > 0 Then objLayer.Lock = False
Next_I:
    Next i
    
    ThisDrawing.Regen acAllViewports
End Sub

Attribute VB_Name = "CreateVHLEForms"
Attribute VB_Base = "0{48407C6E-7CCB-4497-8F27-36D54E784A05}{B1A030FC-F44B-4C8B-AD4F-F43CDF0197FD}"
Attribute VB_GlobalNameSpace = False
Attribute VB_Creatable = False
Attribute VB_PredeclaredId = True
Attribute VB_Exposed = False
Attribute VB_TemplateDerived = False
Attribute VB_Customizable = False
Dim dProjectCost As Double

Private Sub cbPOR_Click()
    If cbPOR.Value = True Then cbVHLE.Value = True
End Sub

Private Sub cbRun_Click()
    If cbVHLE.Value = True Then
        Call FilloutVHLE
        If cbPOR.Value = True Then Call FilloutPORequest
    End If
    If cbMSAT.Value = True Then Call FilloutMSAT
End Sub

Private Sub cbVHLE_Click()
    If cbVHLE.Value = False Then cbPOR.Value = False
End Sub

Private Sub Label10_Click()
    Dim dTotal As Double
    
    Me.Hide
    Load GetCableLengths
        GetCableLengths.show
        
        dTotal = CDbl(GetCableLengths.tbTotalFeet.Value) * 1000
        tbBP.Value = dTotal
    Unload GetCableLengths
    Me.show
End Sub

Private Sub Label4_Click()
    Dim objSS As AcadSelectionSet
    Dim objEntity As AcadEntity
    Dim objLWP As AcadLWPolyline
    Dim objBlock As AcadBlockReference
    Dim vReturnPnt As Variant
    Dim vCoords, vArray As Variant
    Dim vAttList As Variant
    Dim dCoords() As Double
    Dim iRes, iBus, iSG, iTemp, iCounter As Integer
    
    iRes = 0: iBus = 0: iSG = 0
    
    On Error Resume Next
    
    Me.Hide
    
    ThisDrawing.Utility.GetEntity objEntity, vReturnPnt, "Select Polygon Border: "
    If Not objEntity.ObjectName = "AcDbPolyline" Then
        MsgBox "Error: Invalid Selection."
        Me.show
        Exit Sub
    End If
    
    Set objLWP = objEntity
    vCoords = objLWP.Coordinates
    
    iTemp = (UBound(vCoords) + 1) / 2 * 3 - 1
    ReDim dCoords(iTemp) As Double
    
    iCounter = 0
    For i = 0 To UBound(vCoords) Step 2
        dCoords(iCounter) = vCoords(i)
        iCounter = iCounter + 1
        dCoords(iCounter) = vCoords(i + 1)
        iCounter = iCounter + 1
        dCoords(iCounter) = 0#
        iCounter = iCounter + 1
    Next i
    
    Err = 0
    Set objSS = ThisDrawing.SelectionSets.Add("objSS")
    If Not Err = 0 Then Set objSS = ThisDrawing.SelectionSets.Item("objSS")
    
    objSS.SelectByPolygon acSelectionSetWindowPolygon, dCoords
    
    For Each objEntity In objSS
        If TypeOf objEntity Is AcadBlockReference Then
            Set objBlock = objEntity
            Select Case objBlock.Name
                Case "RES", "LOT", "TRLR", "MDU", "CHURCH", "SCHOOL"
                    iRes = iRes + 1
                Case "BUSINESS", "SCHOOL"
                    iBus = iBus + 1
                Case "SG"
                    iSG = iSG + 1
                Case "Customer"
                    vAttList = objBlock.GetAttributes
                    
                    Select Case vAttList(5).TextString
                        Case "", "T", "M", "C"
                            iRes = iRes + 1
                        Case "B", "S"
                            iBus = iBus + 1
                        Case "!"
                            iSG = iSG + 1
                    End Select
            End Select
        Set objBlock = Nothing
        End If
    Next objEntity
    
    objSS.Clear
    objSS.Delete
    
    tbRU.Value = iRes
    tbBU.Value = iBus
    tbSG.Value = iSG
    
    iRes = iRes + iBus + iSG
    tbCTotal.Value = iRes
    
    Me.show
End Sub

Private Sub Label7_Click()
    Dim dTotal As Double
    
    Me.Hide
    Load GetCableLengths
        GetCableLengths.show
        
        dTotal = CDbl(GetCableLengths.tbTotalFeet.Value) * 1000
        tbAS.Value = dTotal
    Unload GetCableLengths
    Me.show
End Sub

Private Sub Label8_Click()
    Dim dTotal As Double
    
    Me.Hide
    Load GetCableLengths
        GetCableLengths.show
        
        dTotal = CDbl(GetCableLengths.tbTotalFeet.Value) * 1000
        tbAL.Value = dTotal
    Unload GetCableLengths
    Me.show
End Sub

Private Sub Label9_Click()
    Dim dTotal As Double
    
    Me.Hide
    Load GetCableLengths
        GetCableLengths.show
        
        dTotal = CDbl(GetCableLengths.tbTotalFeet.Value) * 1000
        tbBC.Value = dTotal
    Unload GetCableLengths
    Me.show
End Sub

Private Sub UserForm_Initialize()
    cbType.AddItem "FEEDER"
    cbType.AddItem "DISTRIBUTION"
    cbType.AddItem "RURAL DISTRIBUTION"
    cbType.AddItem "DROP-AERIAL"
    cbType.AddItem "DROP-UG"
    
    cbLocation.AddItem "ILEC"
    cbLocation.AddItem "CLEC"
    
    cbProject.AddItem "FTTH"
    cbProject.AddItem "FTTB"
    cbProject.AddItem "FTTT"
    cbProject.AddItem "FFIB"
    
    cbField.AddItem ""
    cbField.AddItem "GF"
    cbField.AddItem "GF-SG"
    cbField.AddItem "OVERBUILD"
    cbField.AddItem "RURAL OVERBUILD"
    
    cbSG.AddItem "YES"
    cbSG.AddItem "NO"
    
    dProjectCost = 0#
    
    Dim strLine As String
    Dim vLine As Variant
    
    strLine = Replace(UCase(ThisDrawing.Name), ".DWG", "")
    vLine = Split(strLine, " ")
    tbNumber.Value = vLine(0)
    
    If UBound(vLine) > 0 Then
        strLine = vLine(1)
        If UBound(vLine) > 1 Then
            For i = 2 To UBound(vLine)
                strLine = strLine & " " & vLine(i)
            Next i
        End If
        
        tbDescription.Value = strLine
    End If
End Sub

Private Sub FilloutVHLE()
    Dim strExistingName, strFileName As String
    Dim strTemp, strFormName As String
    Dim vTemp, vTemp2, vLine As Variant
    Dim fName, strLocal As String
    Dim objExcel As Workbook
    Dim strResult As String
    
    'vTemp = Split(ThisDrawing.Name, " ")
    'strExistingName = ThisDrawing.Path & "\VHLE\" & vTemp(0) & " VHLE.xlsx"
    strExistingName = ThisDrawing.Path & "\" & tbNumber.Value & " " & tbDescription.Value & " VHLE.xlsx"
    strLocal = "C:\Integrity\VBA\Forms\"
    
    fName = Dir(strExistingName)
    If fName = "" Then
        strTemp = ThisDrawing.Path
        If InStr(LCase(strTemp), "dropbox") > 0 Then
            vTemp2 = Split(LCase(strTemp), "dropbox")
            strFormName = vTemp2(0) & "\Dropbox\UNITED COMMUNICATIONS JOB INFORMATION\VBA\Integrity\VBA\Forms\Blank VHLE.xlsx"
        Else
            strFormName = strLocal & "Blank VHLE.xlsx"
        End If
        
        Set objExcel = Workbooks.Open(strFormName)
        'MsgBox strExistingName
        objExcel.SaveAs (strExistingName)
        MsgBox "Created New VHLE."
    Else
        Set objExcel = Workbooks.Open(strExistingName)
        'MsgBox "Opened Existing File"
    End If
    
    objExcel.Sheets("VHLE").Cells(2, 4).Value = tbNumber.Value
    objExcel.Sheets("VHLE").Cells(2, 5).Value = tbDescription.Value
    
    If cbProject.Value = "FFIB" Then
        objExcel.Sheets("VHLE").Cells(2, 7).Value = "FEEDER"
    Else
        Select Case cbField.Value
            Case "RURAL OVERBUILD"
                objExcel.Sheets("VHLE").Cells(2, 7).Value = "RURAL DISTRIBUTION"
            Case Else
                objExcel.Sheets("VHLE").Cells(2, 7).Value = "DISTRIBUTION"
        End Select
    End If
    
    'objExcel.Sheets("VHLE").Cells(2, 7).Value = cbType.Value
    objExcel.Sheets("VHLE").Cells(2, 8).Value = tbRU.Value
    objExcel.Sheets("VHLE").Cells(2, 9).Value = tbBU.Value
    objExcel.Sheets("VHLE").Cells(2, 10).Value = tbSG.Value
    objExcel.Sheets("VHLE").Cells(2, 19).Value = tbAS.Value
    objExcel.Sheets("VHLE").Cells(2, 21).Value = tbAL.Value
    objExcel.Sheets("VHLE").Cells(2, 23).Value = tbBC.Value
    objExcel.Sheets("VHLE").Cells(2, 25).Value = tbBP.Value
    
    dProjectCost = CDbl(objExcel.Sheets("VHLE").Cells(2, 40))
        
    objExcel.Save
    objExcel.Close
    
    MsgBox "VHLE form has been updated."
End Sub

Private Sub FilloutPORequest()
    Dim strExistingName, strFileName As String
    Dim strTemp, strFormName As String
    Dim vTemp, vTemp2, vLine As Variant
    Dim fName, strLocal As String
    Dim objExcel As Workbook
    
    'vTemp = Split(ThisDrawing.Name, " ")
    'strExistingName = ThisDrawing.Path & "\VHLE\" & vTemp(0) & " VHLE.xlsx"
    strExistingName = ThisDrawing.Path & "\" & tbNumber.Value & " " & tbDescription.Value & " ICS PO Request.xlsx"
    strLocal = "C:\Integrity\VBA\Forms\"
    
    fName = Dir(strExistingName)
    If fName = "" Then
        strTemp = ThisDrawing.Path
        If InStr(LCase(strTemp), "dropbox") > 0 Then
            vTemp2 = Split(LCase(strTemp), "dropbox")
            strFormName = vTemp2(0) & "\Dropbox\UNITED COMMUNICATIONS JOB INFORMATION\VBA\Integrity\VBA\Forms\Blank PO Request.xlsx"
        Else
            strFormName = strLocal & "Blank PO Request.xlsx"
        End If
        
        Set objExcel = Workbooks.Open(strFormName)
        'MsgBox strExistingName
        objExcel.SaveAs (strExistingName)
        MsgBox "Created New P.O. Request."
    Else
        Set objExcel = Workbooks.Open(strExistingName)
        'MsgBox "Opened Existing File"
    End If
    
    objExcel.Sheets("ICS").Cells(4, 2).Value = Date
    objExcel.Sheets("ICS").Cells(7, 2).Value = tbNumber.Value
    objExcel.Sheets("ICS").Cells(8, 2).Value = tbCTotal.Value
    objExcel.Sheets("ICS").Cells(9, 2).Value = dProjectCost
    objExcel.Sheets("ICS").Cells(15, 2).Value = tbAS.Value
    objExcel.Sheets("ICS").Cells(16, 2).Value = tbAL.Value
    objExcel.Sheets("ICS").Cells(17, 2).Value = tbBC.Value
    objExcel.Sheets("ICS").Cells(18, 2).Value = tbBP.Value
        
    objExcel.Save
    objExcel.Close
    
    MsgBox "P.O. Request form has been updated."
End Sub

Private Sub FilloutMSAT()
    Dim strExistingName, strFileName As String
    Dim strTemp, strFormName, strLine As String
    Dim vTemp, vTemp2, vLine As Variant
    Dim fName As String
    Dim book1 As Word.Application
    Dim sheet1 As Word.Document
    
    strExistingName = ThisDrawing.Path & "\" & tbNumber.Value & " " & tbDescription.Value & " COVER SHEET.docx"
    
    fName = Dir(strExistingName)
    If fName = "" Then
        strTemp = ThisDrawing.Path
        If InStr(LCase(strTemp), "dropbox") > 0 Then
            vTemp2 = Split(LCase(strTemp), "dropbox")
            strFormName = vTemp2(0) & "\Dropbox\UNITED COMMUNICATIONS JOB INFORMATION\VBA\Integrity\VBA\Forms\Blank COVER SHEET.docx"
        Else
            strFormName = "C:\Integrity\VBA\Forms\Blank COVER SHEET.docx"
        End If
        
        FileCopy strFormName, strExistingName
        MsgBox "Created New COVER SHEET."
    End If
    
    Set book1 = CreateObject("word.application")
    book1.Visible = True
    Set sheet1 = book1.Documents.Open(strExistingName)

    With sheet1.Content.Paragraphs(1).Range.Find
        .Text = "<<blank date>>"
        .Replacement.Text = Date
        '.Forward = True
        .Wrap = wdFindContinue
        '.Format = False
        '.MatchCase = False
        .Execute Replace:=wdReplaceAll
        
        .Text = "<<blank project>>"
        .Replacement.Text = tbNumber.Value & " " & tbDescription.Value
        '.Forward = True
        .Wrap = wdFindContinue
        '.Format = False
        '.MatchCase = False
        .Execute Replace:=wdReplaceAll
        
        strLine = cbLocation.Value & " " & cbProject.Value & " " & cbField.Value
        .Text = "<<blank type>>"
        .Replacement.Text = strLine
        '.Forward = True
        .Wrap = wdFindContinue
        '.Format = False
        '.MatchCase = False
        .Execute Replace:=wdReplaceAll
        
        If Not tbSource.Value = "" Then
            .Text = "<<blank source>>"
            .Replacement.Text = tbSource.Value
            '.Forward = True
            .Wrap = wdFindContinue
            '.Format = False
            '.MatchCase = False
            .Execute Replace:=wdReplaceAll
        End If
        
        If Not tbFeeder.Value = "" Then
            .Text = "<<blank feeder>>"
            .Replacement.Text = tbFeeder.Value
            '.Forward = True
            .Wrap = wdFindContinue
            '.Format = False
            '.MatchCase = False
            .Execute Replace:=wdReplaceAll
        End If
        
        If Not tbScope.Value = "" Then
            .Text = "<<blank scope>>"
            .Replacement.Text = tbScope.Value
            '.Forward = True
            .Wrap = wdFindContinue
            '.Format = False
            '.MatchCase = False
            .Execute Replace:=wdReplaceAll
        End If
    End With
    
    sheet1.Save
    sheet1.Close
    book1.Quit
    
    MsgBox "MSAT Cover Sheet has been updated."
End Sub

Attribute VB_Name = "CustomerLocationReport"
Attribute VB_Base = "0{F0C63563-8935-4CBE-8D65-45F2FA7A3AA6}{805BAFB5-DA74-46C1-8387-792C3C9D5C3A}"
Attribute VB_GlobalNameSpace = False
Attribute VB_Creatable = False
Attribute VB_PredeclaredId = True
Attribute VB_Exposed = False
Attribute VB_TemplateDerived = False
Attribute VB_Customizable = False
Private Sub cbCreateReport_Click()
    If lbList.ListCount < 1 Then Exit Sub
    
    Dim strPath As String
    
    strPath = ThisDrawing.Path & "\Customer Location Report.csv"
    Open strPath For Output As #1
    
    Print #1, "Hse #,Street Name,Latitude,Longitude,Type"
    For i = 0 To lbList.ListCount - 1
        strLine = lbList.List(i, 0) & "," & lbList.List(i, 1) & "," & lbList.List(i, 2) & "," & lbList.List(i, 3) & "," & lbList.List(i, 4)
        Print #1, strLine
    Next i
    
    Close #1
End Sub

Private Sub cbGetCustomers_Click()
    Dim objSS As AcadSelectionSet
    Dim objLWP As AcadLWPolyline
    Dim objEntity As AcadEntity
    Dim objBlock As AcadBlockReference
    Dim vAttList, vReturnPnt As Variant
    
    Dim vCoords As Variant
    Dim vNE, vLL As Variant
    Dim iTemp, iCounter As Integer
    
    On Error Resume Next
    
    Me.Hide
    
    ThisDrawing.Utility.GetEntity objEntity, vReturnPnt, "Select Polygon Border: "
    If Not objEntity.ObjectName = "AcDbPolyline" Then
        MsgBox "Error: Invalid Selection."
        Me.show
        Exit Sub
    End If
    
    Set objLWP = objEntity
    vCoords = objLWP.Coordinates
    
    iTemp = (UBound(vCoords) + 1) / 2 * 3 - 1
    ReDim dCoords(iTemp) As Double
    
    iCounter = 0
    For i = 0 To UBound(vCoords) Step 2
        dCoords(iCounter) = vCoords(i)
        iCounter = iCounter + 1
        dCoords(iCounter) = vCoords(i + 1)
        iCounter = iCounter + 1
        dCoords(iCounter) = 0#
        iCounter = iCounter + 1
    Next i
    
    Err = 0
    Set objSS = ThisDrawing.SelectionSets.Add("objSS")
    If Not Err = 0 Then
        Set objSS = ThisDrawing.SelectionSets.Item("objSS")
        objSS.Clear
    End If
    
    objSS.SelectByPolygon acSelectionSetWindowPolygon, dCoords
    
    For Each objEntity In objSS
        If TypeOf objEntity Is AcadBlockReference Then
            Set objBlock = objEntity
            If objBlock.Name = "Customer" Then
                vAttList = objBlock.GetAttributes
                
                If Not vAttList(1).TextString = "" Then
                    lbList.AddItem vAttList(1).TextString
                    lbList.List(lbList.ListCount - 1, 1) = vAttList(2).TextString
                    
                    vLL = TN83FtoLL(CDbl(objBlock.InsertionPoint(1)), CDbl(objBlock.InsertionPoint(0)))
                    lbList.List(lbList.ListCount - 1, 2) = vLL(0)
                    lbList.List(lbList.ListCount - 1, 3) = vLL(1)
                    lbList.List(lbList.ListCount - 1, 4) = vAttList(0).TextString
                    
                End If
            End If
        End If
    Next objEntity
    
    tbListCount = lbList.ListCount
    
Exit_Sub:
    objSS.Clear
    objSS.Delete
    
    Me.show
End Sub

Private Sub cbSort_Click()
    If lbList.ListCount < 2 Then Exit Sub
    
    Call SortList
End Sub

Private Sub UserForm_Initialize()
    lbList.ColumnCount = 5
    lbList.ColumnWidths = "60;144;96;96;54"
End Sub

Private Function TN83FtoLL(dNorth As Double, dEast As Double)
    Dim dLat, dLong, dDLat As Double
    Dim dDiffE, dEast0 As Double
    Dim dDiffN, dNorth0 As Double
    Dim dR, dCAR, dCA, dU, dK As Double
    Dim LL(2) As Double
    
    dEast = dEast * 0.3048006096
    dNorth = dNorth * 0.3048006096
    
    dDiffE = dEast - 600000
    dDiffN = dNorth - 166504.1691
    
    dR = 8842127.1422 - dDiffN
    dCAR = Atn(dDiffE / dR)
    dCA = dCAR * 180 / 3.14159265359
    dLong = -86 + dCA / 0.585439726459
    
    dU = dDiffN - dDiffE * Tan(dCAR / 2)
    dDLat = dU * (0.00000901305249 + dU * (-6.77268E-15 + dU * (-3.72351E-20 + dU * -9.2828E-28)))
    dLat = 35.8340607459 + dDLat
    
    dK = 0.999948401424 + (1.23188E-14 * dU * dU) + (4.54E-22 * dU * dU * dU)
    
    LL(0) = dLat
    LL(1) = dLong
    LL(2) = dK
    
    TN83FtoLL = LL
End Function

Private Sub SortList()
    Dim strTemp, strTotal As String
    Dim iCount, iOffset As Integer
    Dim iIndex As Integer
    Dim strAtt(0 To 4) As String
    
    iCount = lbList.ListCount - 1
    If iCount < 1 Then Exit Sub
    
    On Error Resume Next
    
    For a = iCount To 0 Step -1
        For b = 0 To a - 1
            If lbList.List(b, 1) > lbList.List(b + 1, 1) Then
                If Not Err = 0 Then
                    MsgBox "Error sorting list"
                    lbList.Selected(b) = True
                    lbList.ListIndex = b
                    Exit Sub
                End If
                
                strAtt(0) = lbList.List(b + 1, 0)
                strAtt(1) = lbList.List(b + 1, 1)
                strAtt(2) = lbList.List(b + 1, 2)
                strAtt(3) = lbList.List(b + 1, 3)
                strAtt(4) = lbList.List(b + 1, 4)
                
                lbList.List(b + 1, 0) = lbList.List(b, 0)
                lbList.List(b + 1, 1) = lbList.List(b, 1)
                lbList.List(b + 1, 2) = lbList.List(b, 2)
                lbList.List(b + 1, 3) = lbList.List(b, 3)
                lbList.List(b + 1, 4) = lbList.List(b, 4)
                
                lbList.List(b, 0) = strAtt(0)
                lbList.List(b, 1) = strAtt(1)
                lbList.List(b, 2) = strAtt(2)
                lbList.List(b, 3) = strAtt(3)
                lbList.List(b, 4) = strAtt(4)
            End If
            
            If lbList.List(b, 1) = lbList.List(b + 1, 1) Then
                If lbList.List(b, 0) > lbList.List(b + 1, 0) Then
                    strAtt(0) = lbList.List(b + 1, 0)
                    strAtt(1) = lbList.List(b + 1, 1)
                    strAtt(2) = lbList.List(b + 1, 2)
                    strAtt(3) = lbList.List(b + 1, 3)
                    strAtt(4) = lbList.List(b + 1, 4)
                
                    lbList.List(b + 1, 0) = lbList.List(b, 0)
                    lbList.List(b + 1, 1) = lbList.List(b, 1)
                    lbList.List(b + 1, 2) = lbList.List(b, 2)
                    lbList.List(b + 1, 3) = lbList.List(b, 3)
                    lbList.List(b + 1, 4) = lbList.List(b, 4)
                
                    lbList.List(b, 0) = strAtt(0)
                    lbList.List(b, 1) = strAtt(1)
                    lbList.List(b, 2) = strAtt(2)
                    lbList.List(b, 3) = strAtt(3)
                    lbList.List(b, 4) = strAtt(4)
                End If
            End If
        Next b
    Next a
End Sub

Attribute VB_Name = "DesignTermForm"
Attribute VB_Base = "0{5525FFAE-9778-4D38-BDC0-98BCCC874889}{852771E8-681F-4B5C-872F-CC6D93854343}"
Attribute VB_GlobalNameSpace = False
Attribute VB_Creatable = False
Attribute VB_PredeclaredId = True
Attribute VB_Exposed = False
Attribute VB_TemplateDerived = False
Attribute VB_Customizable = False

'Dim iListIndex As Integer
Dim Pi As Double


Private Sub cbClosureType_Change()
    Select Case cbClosureType.Value
        Case "Aerial"
            tbCoil.Value = "100"
        Case "Buried"
            tbCoil.Value = "20"
    End Select
End Sub

Private Sub cbCoilType_Change()
    If InStr(UCase(ThisDrawing.Path), "LORETTO") > 0 Then
        Select Case Left(cbCoilType.Value, 3)
            Case "12F", "24F"
                cbClosure.Value = "G4"
            Case "36F", "48F", "72F", "96F", "144"
                cbClosure.Value = "G5"
            Case Else
                cbClosure.Value = "G6"
        End Select
    Else
        Select Case Left(cbCoilType.Value, 3)
            Case "12F", "24F", "36F", "48F"
                cbClosure.Value = "FOSC A"
            Case "72F", "96F"
                cbClosure.Value = "FOSC B"
            Case Else
                cbClosure.Value = "FOSC D"
        End Select
    End If
    'If lbWLimits.ListCount > 0 Then cbClosure.Value = "#1413"
End Sub

Private Sub cbConvert_Click()
    Dim obrMClosure As AcadBlockReference
    Dim obrMCoil As AcadBlockReference
    Dim objBlock, obrGP3 As AcadBlockReference
    Dim objEntity As AcadEntity
    Dim vReturnPnt, vEndPnt As Variant
    Dim vAttList As Variant
    Dim dDiff(0 To 3) As Double
    Dim dInsertPnt(0 To 2) As Double
    Dim dDist As Double
    Dim strBlockName, strTermType As String
    Dim layerObj As AcadLayer
    Dim returnPnt, vPoleCoords As Variant
    Dim str, strLayer As String
    Dim vBlockCoords(0 To 2) As Double
    Dim dScale As Double
    Dim i As Integer

    Me.Hide

    strTermType = ""

  On Error Resume Next

    dScale = CDbl(cbScale.Value) / 100

    str = ""
    'For i = 0 To lbWLimits.ListCount - 1
    '    str = str & lbWLimits.List(i) & "::"
    'Next i
    Err = 0

    vReturnPnt = ThisDrawing.Utility.GetPoint(, "Start Pole/Point:")
    vEndPnt = ThisDrawing.Utility.GetPoint(, "Direction of Placement:")
    
    If Not Err = 0 Then GoTo Exit_Sub

    dDiff(0) = vEndPnt(0) - vReturnPnt(0)
    dDiff(1) = vEndPnt(1) - vReturnPnt(1)
    dDiff(2) = Math.Sqr(dDiff(0) * dDiff(0) + (dDiff(1) * dDiff(1)))

    If cbClosureType.Value = "Buried" Then
        dInsertPnt(0) = vReturnPnt(0) + 7.25 * dScale * dDiff(0) / dDiff(2)
        dInsertPnt(1) = vReturnPnt(1) + 7.25 * dScale * dDiff(1) / dDiff(2)
        dInsertPnt(2) = 0#
    Else
        dInsertPnt(0) = vReturnPnt(0) + 15 * dScale * dDiff(0) / dDiff(2)
        dInsertPnt(1) = vReturnPnt(1) + 15 * dScale * dDiff(1) / dDiff(2)
        dInsertPnt(2) = 0#
    End If

    If dDiff(0) = 0 Then
        dRotate = Pi / 2
    ElseIf dDiff(1) = 0 Then
        dRotate = 0#
    Else
        dRotate = Math.Atn(dDiff(1) / dDiff(0))
        If dDiff(0) < 0 Then
            dRotate = Pi + dRotate
        ElseIf dDiff(1) < 0 Then
            dRotate = 2 * Pi + dRotate
        End If
    End If

    If dRotate > Pi Then dRotate = dRotate - Pi
    If dRotate > Pi / 2 Then dRotate = Pi + dRotate

    If Not cbPlaceClosure Then GoTo place_coil

    Select Case cbClosureType.Value
        Case "Aerial"
            strLayer = "Integrity Map Splices-Aerial"
        Case "Buried"
            strLayer = "Integrity Map Splices-Buried"
        Case "UG"
            strLayer = "Integrity Map Splices-UG"
    End Select
    'Set layerObj = ThisDrawing.Layers.Add("Integrity Map Splices-Aerial")
    'ThisDrawing.ActiveLayer = layerObj

    strBlockName = "Map splice"
    Set obrMClosure = ThisDrawing.ModelSpace.InsertBlock(dInsertPnt, strBlockName, dScale, dScale, dScale, dRotate)
    obrMClosure.Layer = strLayer
    vAttList = obrMClosure.GetAttributes

    If Not cbClosure.Value = "" Then vAttList(0).TextString = cbClosure.Value
    'vAttList(1).TextString = str
    obrMClosure.Update

place_coil:

    dInsertPnt(0) = dInsertPnt(0) + 15 * dScale * dDiff(0) / dDiff(2)
    dInsertPnt(1) = dInsertPnt(1) + 15 * dScale * dDiff(1) / dDiff(2)

    If obCTop Then
        If dDiff(0) > 0 Then
            dInsertPnt(0) = dInsertPnt(0) - 9 * dScale * dDiff(1) / dDiff(2)
            dInsertPnt(1) = dInsertPnt(1) + 9 * dScale * dDiff(0) / dDiff(2)
        Else
            dInsertPnt(0) = dInsertPnt(0) + 9 * dScale * dDiff(1) / dDiff(2)
            dInsertPnt(1) = dInsertPnt(1) - 9 * dScale * dDiff(0) / dDiff(2)
        End If
    Else
        If dDiff(0) > 0 Then
            dInsertPnt(0) = dInsertPnt(0) + 9 * dScale * dDiff(1) / dDiff(2)
            dInsertPnt(1) = dInsertPnt(1) - 9 * dScale * dDiff(0) / dDiff(2)
        Else
            dInsertPnt(0) = dInsertPnt(0) - 9 * dScale * dDiff(1) / dDiff(2)
            dInsertPnt(1) = dInsertPnt(1) + 9 * dScale * dDiff(0) / dDiff(2)
        End If
    End If

    If Not cbPlaceCoil Then GoTo Exit_Sub

    'Set layerObj = ThisDrawing.Layers.Add("Integrity Map Coils-Aerial")
    'ThisDrawing.ActiveLayer = layerObj
    
    strLayer = Replace(strLayer, "Splices", "Coils")

    Set obrMCoil = ThisDrawing.ModelSpace.InsertBlock(dInsertPnt, "Map coil", dScale, dScale, dScale, 0#)
    obrMCoil.Layer = strLayer
    vAttList = obrMCoil.GetAttributes
    If Not tbCoil.Value = "" Then vAttList(0).TextString = tbCoil.Value & "'"
    If Not cbCoilType.Value = "" Then vAttList(1).TextString = cbCoilType.Value
    obrMCoil.Update

Exit_Sub:

    Dim strLine, strTemp As String
    Dim iAtt As Integer
    
    strLine = ""
    
    If cbPlaceCoil.Value = True Then
        Select Case cbClosureType.Value
            Case "UG"
                strLine = "+UO(" & Replace(cbCoilType.Value, "F", "") & ")=" & tbCoil.Value & "'  LOOP"
            Case "Buried"
                strLine = "+BFO(" & Replace(cbCoilType.Value, "F", "") & ")=" & tbCoil.Value & "'  LOOP"
            Case Else
                strLine = "+CO(" & Replace(cbCoilType.Value, "F", "") & ")E=" & tbCoil.Value & "'  LOOP"
        End Select
    End If
    
    If cbPlaceClosure.Value = True Then
        Select Case cbClosureType.Value
            Case "UG"
                strTemp = "+HBFO(" & Replace(cbCoilType.Value, "F", "") & ")=1  " & cbClosure.Value
            Case "Buried"
                strTemp = "+HBFO(" & Replace(cbCoilType.Value, "F", "") & ")=1  " & cbClosure.Value
            Case Else
                strTemp = "+HACO(" & Replace(cbCoilType.Value, "F", "") & ")=1  " & cbClosure.Value
        End Select
        
        If strLine = "" Then
            strLine = strTemp
        Else
            If Not strTemp = "" Then strLine = strLine & ";;" & strTemp
        End If
    End If
    
    Err = 0
    ThisDrawing.Utility.GetEntity objEntity, vReturnPnt, vbCr & "Select Structure to add Units:"
    If Not Err = 0 Then GoTo Tidy_Up
    
    If Not TypeOf objEntity Is AcadBlockReference Then
        MsgBox "Not a Block"
        GoTo Tidy_Up
    End If
    
    Set objBlock = objEntity
    
    Select Case objBlock.Name
        Case "sPole"
            iAtt = 27
        Case "sPED", "sHH"
            iAtt = 7
        Case Else
            MsgBox "Not a valid Block"
            GoTo Tidy_Up
    End Select
    
    vAttList = objBlock.GetAttributes
    
    If vAttList(iAtt).TextString = "" Then
        vAttList(iAtt).TextString = strLine
    Else
        vAttList(iAtt).TextString = vAttList(iAtt).TextString & ";;" & strLine
    End If
    
    objBlock.Update
    
Tidy_Up:

    Me.show
End Sub

Private Sub cbQuit_Click()
    Me.Hide
End Sub

Private Sub Label25_Click()
    Dim entPole As AcadObject
    Dim basePnt As Variant
    
    Me.Hide
  On Error Resume Next
    
    ThisDrawing.Utility.GetEntity entPole, basePnt, "Left Click to Exit: "
    
    Me.show
End Sub

Private Sub UserForm_Initialize()
    cbClosure.AddItem ""
    cbClosure.AddItem "#1413"
    cbClosure.AddItem "FOSC A"
    cbClosure.AddItem "FOSC B"
    cbClosure.AddItem "FOSC D"
    cbClosure.AddItem "G4"
    cbClosure.AddItem "G5"
    cbClosure.AddItem "G6"
    cbClosure.AddItem "G6S"
    
    cbCoilType.AddItem ""
    cbCoilType.AddItem "FEED"
    cbCoilType.AddItem "12F"
    cbCoilType.AddItem "24F"
    cbCoilType.AddItem "36F"
    cbCoilType.AddItem "48F"
    cbCoilType.AddItem "72F"
    cbCoilType.AddItem "96F"
    cbCoilType.AddItem "144F"
    cbCoilType.AddItem "216F"
    cbCoilType.AddItem "288F"
    cbCoilType.AddItem "432F"
    
    cbClosureType.AddItem ""
    cbClosureType.AddItem "Aerial"
    cbClosureType.AddItem "Buried"
    cbClosureType.AddItem "UG"
    cbClosureType.Value = "Aerial"
    
    tbCoil.Value = "100"
    
    Pi = 3.14150265359
    
    'cbUP.Caption = Chr(225)
    'cbDOWN.Caption = Chr(226)
    
    cbScale.AddItem "50"
    cbScale.AddItem "75"
    cbScale.AddItem "100"
    cbScale.Value = "100"
    
    'cbScale.Value = MainForm.cbScale.Value
    'If cbScale.Value = "" Then cbScale.Value = "75"
End Sub

Attribute VB_Name = "ExtraHeightForm"
Attribute VB_Base = "0{3CC334A6-6FD6-485D-AA48-3423988DED96}{BCB71C6F-8603-493B-AD5C-6E9AE06A560F}"
Attribute VB_GlobalNameSpace = False
Attribute VB_Creatable = False
Attribute VB_PredeclaredId = True
Attribute VB_Exposed = False
Attribute VB_TemplateDerived = False
Attribute VB_Customizable = False
Dim iListIndex As Integer

Private Sub cbCompanies_Change()
    If cbCompanies.Value = "" Then Exit Sub
    If lbPoles.ListCount < 1 Then Exit Sub
    
    Dim vLine, vItem, vTemp As Variant
    Dim strCompany As String
    Dim iOwner, iMR As Integer
    Dim iTotal, iIndex As Integer
    Dim iCompany, iMRLoc, iMRTotal As Integer
    
    lbATT.Clear
    
    strCompany = cbCompanies.Value
    For i = 0 To lbPoles.ListCount - 1
        iOwner = 0
        iMR = 0
        
        If lbPoles.List(i, 1) = strCompany Then iOwner = 1
        
        vLine = Split(lbPoles.List(i, 5), " + ")
        For j = 0 To UBound(vLine)
            vItem = Split(vLine(j), "=")
            If vItem(0) = strCompany Then
                vTemp = Split(vItem(1), " ")
                For k = 0 To UBound(vTemp)
                    If InStr(vTemp(k), ")") > 0 Then
                        iMR = iMR + 1
                    End If
                Next k
            End If
        Next j
        
        iTotal = iOwner + iMR
        
        If iTotal > 0 Then
            lbATT.AddItem lbPoles.List(i, 0)
            iIndex = lbATT.ListCount - 1
            
            lbATT.List(iIndex, 1) = iOwner
            lbATT.List(iIndex, 2) = iMR
            lbATT.List(iIndex, 3) = i
        End If
    Next i
    
    iCompany = 0
    iMRLoc = 0
    iMRTotal = 0
    
    For i = 0 To lbATT.ListCount - 1
        iCompany = iCompany + CInt(lbATT.List(i, 1))
        If CInt(lbATT.List(i, 2)) > 0 Then
            iMRLoc = iMRLoc + 1
            iMRTotal = iMRTotal + CInt(lbATT.List(i, 2))
        End If
    Next i
    
    tbAttVisit.Value = lbATT.ListCount
    tbAtt.Value = iCompany
    tbATTMR.Value = iMRLoc
    tbATTMRTotal.Value = iMRTotal
End Sub

Private Sub cbGet_Click()
    Me.Hide
    Call GetPoles
    
    Call GetData
    Me.show
End Sub

Private Sub AddDataToTextBox(strCompany As String)
    Dim strAll, strTest As String
    Dim strOne, strTwo As String
    Dim vLine, vItem As Variant
    
    If lbMR.ListCount = 0 Then GoTo Add_To_List
    
    For i = 0 To lbMR.ListCount - 1
        If lbMR.List(i, 0) = "" Then GoTo Skip_This
        strTemp = lbMR.List(i, 0)
        
        If StrComp(strTemp, strCompany) = 0 Then
            lbMR.List(i, 1) = CInt(lbMR.List(i, 1)) + 1
            
            Exit Sub
        End If
Skip_This:
    Next i
    
Add_To_List:
    
    lbMR.AddItem strCompany
    lbMR.List(lbMR.ListCount - 1, 1) = 1
End Sub

Private Sub cbOwners_Change()
    If cbOwners.Value = "" Then Exit Sub
    If lbData.ListCount < 1 Then Exit Sub
    
    Dim vLine, vItem As Variant
    Dim strOwner, strHC As String
    Dim iTotal As Integer
    
    lbEHReport.Clear
    
    strOwner = cbOwners.Value
    For i = 0 To lbData.ListCount - 1
        If lbData.List(i, 0) = strOwner Then
            strHC = lbData.List(i, 2)
            If InStr(strHC, ")") > 0 Then
                vLine = Split(strHC, ")")
                strHC = vLine(1)
            End If
            
            If lbEHReport.ListCount > 0 Then
                For j = 0 To lbEHReport.ListCount - 1
                    If lbEHReport.List(j, 0) = strHC Then
                        lbEHReport.List(j, 1) = CInt(lbEHReport.List(j, 1)) + 1
                        GoTo Existing_Owner
                    End If
                Next j
            End If
            
            lbEHReport.AddItem strHC
            lbEHReport.List(lbEHReport.ListCount - 1, 1) = "1"
Existing_Owner:
            
        End If
    Next i
    
    iTotal = 0
    
    For i = 0 To lbEHReport.ListCount - 1
        iTotal = iTotal + CInt(lbEHReport.List(i, 1))
    Next i
    
    tbTotalEHCompany.Value = iTotal
    
    Call SortEH
End Sub

Private Sub cbQuit_Click()
    Me.Hide
End Sub

Private Sub cbRun_Click()
    Dim i406, i405, i404, i403, i402, i401 As Integer
    Dim i456, i455, i454, i453, i452, i451 As Integer
    Dim i505, i504, i503, i502, i501 As Integer
    Dim i555, i554, i553, i552, i551 As Integer
    Dim i604, i603, i602, i601 As Integer
    Dim i653, i652, i651 As Integer
    Dim i702, i701 As Integer
    Dim vLine, vHC As Variant
    Dim strHC, strLine As String
    
    i406 = 0: i405 = 0: i404 = 0: i403 = 0: i402 = 0: i401 = 0
    i456 = 0: i455 = 0: i454 = 0: i453 = 0: i452 = 0: i451 = 0
    i505 = 0: i504 = 0: i503 = 0: i502 = 0: i501 = 0
    i555 = 0: i554 = 0: i553 = 0: i552 = 0: i551 = 0
    i604 = 0: i603 = 0: i602 = 0: i601 = 0
    i653 = 0: i652 = 0: i651 = 0
    i702 = 0: i701 = 0
    
    On Error Resume Next
    
    For n = 0 To lbData.ListCount - 1
        vLine = Split(lbData.List(n), vbTab)
        
        If Len(vLine(2)) > 6 Then
            vHC = Split(vLine(2), ") ")
            vLine(2) = vHC(UBound(vHC))
        End If
        
        vHC = Split(vLine(2), "-")
        Select Case Left(vHC(0), 1)
            Case "S", "C"
                vHC(0) = Right(vHC(0), 2)
                vHC(1) = 1
            'Case "("
            'Case Else
        End Select
        
        'If UBound(vHC) < 1 Then MsgBox vLine(2)
        
        strHC = vHC(0) & vHC(1)
        Select Case strHC
            Case "406"
                i406 = i406 + 1
            Case "405"
                i405 = i405 + 1
            Case "404"
                i404 = i404 + 1
            Case "403"
                i403 = i403 + 1
            Case "402"
                i402 = i402 + 1
            Case "401"
                i401 = i401 + 1
                
            Case "456"
                i456 = i456 + 1
            Case "455"
                i455 = i455 + 1
            Case "454"
                i454 = i454 + 1
            Case "453"
                i453 = i453 + 1
            Case "452"
                i452 = i452 + 1
            Case "451"
                i451 = i451 + 1
                
            Case "505"
                i505 = i505 + 1
            Case "504"
                i504 = i504 + 1
            Case "503"
                i503 = i503 + 1
            Case "502"
                i502 = i502 + 1
            Case "501"
                i501 = i501 + 1
                
            Case "555"
                i555 = i555 + 1
            Case "554"
                i554 = i554 + 1
            Case "553"
                i553 = i553 + 1
            Case "552"
                i552 = i552 + 1
            Case "551"
                i551 = i551 + 1
                
            Case "604"
                i604 = i604 + 1
            Case "603"
                i603 = i603 + 1
            Case "602"
                i602 = i602 + 1
            Case "601"
                i601 = i601 + 1
                
            Case "653"
                i653 = i653 + 1
            Case "652"
                i652 = i652 + 1
            Case "651"
                i651 = i651 + 1
                
            Case "702"
                i702 = i702 + 1
            Case "701"
                i701 = i701 + 1
        End Select
    Next n
    
    strLine = ""
    
    If Not i406 = 0 Then strLine = strLine & "40-6" & vbTab & i406 & vbCr
    If Not i405 = 0 Then strLine = strLine & "40-5" & vbTab & i405 & vbCr
    If Not i404 = 0 Then strLine = strLine & "40-4" & vbTab & i404 & vbCr
    If Not i403 = 0 Then strLine = strLine & "40-3" & vbTab & i403 & vbCr
    If Not i402 = 0 Then strLine = strLine & "40-2" & vbTab & i402 & vbCr
    If Not i401 = 0 Then strLine = strLine & "40-1" & vbTab & i401 & vbCr
    
    If Not i456 = 0 Then strLine = strLine & "45-6" & vbTab & i456 & vbCr
    If Not i455 = 0 Then strLine = strLine & "45-5" & vbTab & i455 & vbCr
    If Not i454 = 0 Then strLine = strLine & "45-4" & vbTab & i454 & vbCr
    If Not i453 = 0 Then strLine = strLine & "45-3" & vbTab & i453 & vbCr
    If Not i452 = 0 Then strLine = strLine & "45-2" & vbTab & i452 & vbCr
    If Not i451 = 0 Then strLine = strLine & "45-1" & vbTab & i451 & vbCr
    
    If Not i505 = 0 Then strLine = strLine & "50-5" & vbTab & i505 & vbCr
    If Not i504 = 0 Then strLine = strLine & "50-4" & vbTab & i504 & vbCr
    If Not i503 = 0 Then strLine = strLine & "50-3" & vbTab & i503 & vbCr
    If Not i502 = 0 Then strLine = strLine & "50-2" & vbTab & i502 & vbCr
    If Not i501 = 0 Then strLine = strLine & "50-1" & vbTab & i501 & vbCr
    
    If Not i555 = 0 Then strLine = strLine & "55-5" & vbTab & i555 & vbCr
    If Not i554 = 0 Then strLine = strLine & "55-4" & vbTab & i554 & vbCr
    If Not i553 = 0 Then strLine = strLine & "55-3" & vbTab & i553 & vbCr
    If Not i552 = 0 Then strLine = strLine & "55-2" & vbTab & i552 & vbCr
    If Not i551 = 0 Then strLine = strLine & "55-1" & vbTab & i551 & vbCr
    
    If Not i604 = 0 Then strLine = strLine & "60-4" & vbTab & i604 & vbCr
    If Not i603 = 0 Then strLine = strLine & "60-3" & vbTab & i603 & vbCr
    If Not i602 = 0 Then strLine = strLine & "60-2" & vbTab & i602 & vbCr
    If Not i601 = 0 Then strLine = strLine & "60-1" & vbTab & i601 & vbCr
    
    If Not i653 = 0 Then strLine = strLine & "65-3" & vbTab & i653 & vbCr
    If Not i652 = 0 Then strLine = strLine & "65-2" & vbTab & i652 & vbCr
    If Not i651 = 0 Then strLine = strLine & "65-1" & vbTab & i651 & vbCr
    
    If Not i702 = 0 Then strLine = strLine & "70-2" & vbTab & i702 & vbCr
    If Not i701 = 0 Then strLine = strLine & "70-1" & vbTab & i701 & vbCr
    
    tbReport.Value = strLine
End Sub

Private Sub cbTotalSelected_Click()
    If lbEHReport.ListCount < 0 Then Exit Sub
    
    Dim iTotal As Integer
    
    iTotal = 0
    
    For i = 0 To lbEHReport.ListCount - 1
        If lbEHReport.Selected(i) = True Then iTotal = iTotal + CInt(lbEHReport.List(i, 1))
    Next i
    
    tbTotalEHCompany.Value = iTotal
End Sub

Private Sub cbUpdate_Click()
    Dim strLine As String
    
    strLine = tbAttach.Value & vbTab & tbPole.Value & vbTab & tbHC.Value
    lbData.AddItem strLine, iListIndex
    lbData.RemoveItem (iListIndex + 1)
    
    cbUpdate.Enabled = False
    cbGet.Enabled = True
    cbRun.Enabled = True
    tbPole.Value = ""
    tbAttach.Value = ""
    tbHC.Value = ""
End Sub

Private Sub Label2_Click()
    Dim obrPole As AcadBlockReference
    Dim obrAttach As AcadBlockReference
    Dim entBlock As AcadEntity
    Dim objSSFix As AcadSelectionSet
    Dim strPole As String
    Dim vAttList, basePnt As Variant
    
    Me.Hide
    
  On Error Resume Next
    Err = 0
    
    ThisDrawing.Utility.GetEntity entBlock, basePnt, "Select Pole: "
    If TypeOf entBlock Is AcadBlockReference Then
        Set obrPole = entBlock
    Else
        MsgBox "Not a valid pole."
        Me.show
        Exit Sub
    End If
    
    vAttList = obrPole.GetAttributes
    
    If Not Err = 0 Then
        Me.show
        Exit Sub
    End If
    
    strPole = vAttList(0).TextString
    
  
    Set objSSFix = ThisDrawing.SelectionSets.Add("objSSFix")
    objSSFix.SelectOnScreen
    For Each entBlock In objSSFix
        If TypeOf entBlock Is AcadBlockReference Then
            Set obrAttach = entBlock
            
            vAttList = obrAttach.GetAttributes
            vAttList(0).TextString = strPole
            obrAttach.Update
            'If obrPole.Name = "pole_attach" Then
            '    attList = obrBlock.GetAttributes
            '    str1 = attList(2).TextString & vbTab & attList(3).TextString & vbTab & attList(4).TextString
            '    lbAttachments.AddItem str1
            '    If CDbl(attList(1).TextString) < dTest Then
            '        vCoordsAttach = obrBlock.InsertionPoint
            '        dTest = CDbl(attList(1).TextString)
            '        dPosition = dTest
            '    End If
            '    tbUnitedPole = attList(0).TextString
            '    cbScale.Value = obrBlock.XScaleFactor * 100
            'End If
        End If
    Next entBlock
    
    objSSFix.Clear
    objSSFix.Delete
    
    Me.show
End Sub

Private Sub lbATT_DblClick(ByVal Cancel As MSForms.ReturnBoolean)
    Dim iIndex As Integer
    Dim strLine As String
    
    iIndex = CInt(lbATT.List(lbATT.ListIndex, 3))
    
    strLine = Replace(lbPoles.List(iIndex, 5), " + ", vbCr)
    
    MsgBox strLine
End Sub

Private Sub lbData_DblClick(ByVal Cancel As MSForms.ReturnBoolean)
    Dim vLine As Variant
    
    cbUpdate.Enabled = True
    cbGet.Enabled = False
    cbRun.Enabled = False
    iListIndex = lbData.ListIndex
    
    vLine = Split(lbData.List(iListIndex), vbTab)
    tbPole.Value = vLine(1)
    tbAttach.Value = vLine(0)
    tbHC.Value = vLine(2)
End Sub

Private Sub lbPoles_DblClick(ByVal Cancel As MSForms.ReturnBoolean)
    Dim vCoords, vAttList As Variant
    Dim viewCoordsB(0 To 2) As Double
    Dim viewCoordsE(0 To 2) As Double
    
    Me.Hide
    
    vCoords = Split(lbPoles.List(lbPoles.ListIndex, 6), ",")
    
    viewCoordsB(0) = vCoords(0) - 200
    viewCoordsB(1) = vCoords(1) - 200
    viewCoordsB(2) = 0#
    viewCoordsE(0) = vCoords(0) + 200
    viewCoordsE(1) = vCoords(1) + 200
    viewCoordsE(2) = 0#
    
    ThisDrawing.Application.ZoomWindow viewCoordsB, viewCoordsE
    
    Me.show
End Sub

Private Sub lbPoles_KeyDown(ByVal KeyCode As MSForms.ReturnInteger, ByVal Shift As Integer)
    Select Case KeyCode
        Case vbKeyReturn
            Dim iIndex As Integer
            Dim strLine As String
    
            iIndex = lbPoles.ListIndex
    
            strLine = Replace(lbPoles.List(iIndex, 5), " + ", vbCr)
    
            MsgBox strLine
            
            If Not iIndex = lbPoles.ListCount - 1 Then lbPoles.ListIndex = iIndex + 1
    End Select
End Sub

Private Sub UserForm_Initialize()
    lbMR.ColumnCount = 2
    lbMR.ColumnWidths = "70;25"
    
    lbATT.ColumnCount = 4
    lbATT.ColumnWidths = "100;48;38;10"
    
    lbOwners.ColumnCount = 4
    lbOwners.ColumnWidths = "72;48;48;36"
    
    lbData.ColumnCount = 5
    lbData.ColumnWidths = "48;120;48;36;10"
    
    lbPoles.ColumnCount = 7
    lbPoles.ColumnWidths = "120;48;48;48;24;170;10"
    
    lbEHReport.ColumnCount = 2
    lbEHReport.ColumnWidths = "48;36"
    
    cbClient.AddItem "UTC"
    cbClient.AddItem "LOR"
    cbClient.AddItem "LTC"
    cbClient.AddItem "TDS"
    cbClient.AddItem ""
    cbClient.Value = "UTC"
End Sub

Private Sub GetPoles()
    Dim vPnt1, vPnt2 As Variant
    Dim grpCode(0) As Integer
    Dim grpValue(0) As Variant
    Dim filterType, filterValue As Variant
    Dim objSS As AcadSelectionSet
    Dim objBlock As AcadBlockReference
    Dim vAttList As Variant
    Dim vItem, vTemp As Variant
    Dim iHeight As Integer
    Dim iIndex As Integer
    Dim strMR, strPWR, strLine As String
    
    On Error Resume Next
    
    cbCompanies.Clear
    
    Err = 0
    vPnt1 = ThisDrawing.Utility.GetPoint(, "Get BL Corner: ")
    vPnt2 = ThisDrawing.Utility.GetCorner(vPnt1, vbCr & "Get UR Corner: ")
    If Not Err = 0 Then
        Me.show
        Exit Sub
    End If
    
    grpCode(0) = 2
    grpValue(0) = "sPole"
    filterType = grpCode
    filterValue = grpValue
    
    Err = 0
    Set objSS = ThisDrawing.SelectionSets.Add("objSS")
    If Not Err = 0 Then
        Set objSS = ThisDrawing.SelectionSets.Item("objSS")
        objSS.Clear
    End If
    objSS.Select acSelectionSetWindow, vPnt1, vPnt2, filterType, filterValue
    
    'MsgBox objSS.count
    
    For Each objBlock In objSS
        vAttList = objBlock.GetAttributes
        
        If vAttList(0).TextString = "POLE" Then GoTo Next_objBlock
        If vAttList(0).TextString = "" Then GoTo Next_objBlock
        
        lbPoles.AddItem vAttList(0).TextString
        iIndex = lbPoles.ListCount - 1
        lbPoles.List(iIndex, 1) = vAttList(2).TextString
        lbPoles.List(iIndex, 2) = vAttList(5).TextString
        lbPoles.List(iIndex, 3) = vAttList(15).TextString
        lbPoles.List(iIndex, 4) = ""
        lbPoles.List(iIndex, 5) = ""
        lbPoles.List(iIndex, 6) = objBlock.InsertionPoint(0) & "," & objBlock.InsertionPoint(1)
        
        If cbCompanies.ListCount > 0 Then
            For j = 0 To cbCompanies.ListCount - 1
                If cbCompanies.List(j) = vAttList(2).TextString Then GoTo Found_Company
            Next j
        End If
        
        cbCompanies.AddItem vAttList(2).TextString
        
Found_Company:
        
        strPWR = ""
        For i = 9 To 14
            vItem = Split(vAttList(i).TextString, " ")
            For j = 0 To UBound(vItem)
                If InStr(vItem(j), ")") > 0 Then
                    If strPWR = "" Then
                        strPWR = "PWR=" & vItem(j)
                    Else
                        strPWR = strPWR & " " & vItem(j)
                    End If
                End If
            Next j
        Next i
        
        If strPWR = "" Then
            strLine = ""
        Else
            strLine = strPWR
        End If
        
        
        For i = 16 To 23
            strMR = ""
            vTemp = Split(UCase(vAttList(i).TextString), "=")
            If InStr(vTemp(0), cbClient.Value) > 0 Then
                lbPoles.List(iIndex, 4) = vTemp(1)
            End If
            
            If cbCompanies.ListCount > 0 Then
                For j = 0 To cbCompanies.ListCount - 1
                    If cbCompanies.List(j) = vTemp(0) Then
                        GoTo Found_Company2
                    End If
                Next j
            End If
        
            If InStr(vTemp(1), ")") > 0 Then cbCompanies.AddItem vTemp(0)
        
Found_Company2:
            
            vItem = Split(vTemp(1), " ")
            For j = 0 To UBound(vItem)
                If InStr(vItem(j), ")") > 0 Then
                    If strMR = "" Then
                        strMR = vTemp(0) & "=" & vItem(j)
                    Else
                        strMR = strMR & " " & vItem(j)
                    End If
                End If
                
                If InStr(vItem(j), "X") > 0 Then
                    If strMR = "" Then
                        strMR = vTemp(0) & "=" & vItem(j)
                    Else
                        strMR = strMR & " " & vItem(j)
                    End If
                End If
            Next j
            
            If Not strMR = "" Then
                If strLine = "" Then
                    strLine = strMR
                Else
                    strLine = strLine & " + " & strMR
                End If
            End If
        Next i
        
        lbPoles.List(iIndex, 5) = strLine
        
Next_objBlock:
    Next objBlock
    
    objSS.Clear
    objSS.Delete
End Sub

Private Sub GetData()
    Dim vLine, vItem, vData, vAttach As Variant
    Dim strLine, strOwner As String
    Dim iIndex, iHeight As Integer
    Dim iAttPole, iPower, iPWRPole As Integer
    Dim iCATV, iAtt, iATTCW, iTDS, iUTC, iDTC As Integer
    Dim iXO, iZAYO, iCLEC, iTelco As Integer
    Dim iCity, iTraffic, iOHG, iPoles As Integer
    Dim strMR As String
    
    On Error Resume Next
    
    lbMR.Clear
    lbOwners.Clear
    lbATT.Clear
    lbData.Clear
    tbPole.Value = ""
    tbAttach.Value = ""
    tbHC.Value = ""
    cbUpdate.Enabled = False
    cbOwners.Clear
    
    iHeight = 0
    iAttPole = 0: iPower = 0: iPWRPole = 0
    iCATV = 0: iAtt = 0: iATTCW = 0: iTDS = 0: iUTC = 0: iDTC = 0
    iXO = 0: iZAYO = 0: iCLEC = 0: iTelco = 0
    iCity = 0: iTraffic = 0: iOHG = 0: iPoles = 0
    
    For i = 0 To lbPoles.ListCount - 1
        ' Get Extra Height List data
        strOwner = lbPoles.List(i, 1)
        
        If lbOwners.ListCount > 0 Then
            For j = 0 To lbOwners.ListCount - 1
                If lbOwners.List(j, 0) = strOwner Then
                    iIndex = j
                    GoTo Existing_Owner
                End If
            Next j
        End If
            
        lbOwners.AddItem strOwner
        iIndex = lbOwners.ListCount - 1
        lbOwners.List(iIndex, 1) = "0"
        lbOwners.List(iIndex, 2) = "0"
        lbOwners.List(iIndex, 3) = "0"
Existing_Owner:
        
        'MsgBox "New: " & lbPoles.List(i, 3) & ">" & vbCr & "Exist: " & lbPoles.List(i, 4) & ">"
        
        If lbPoles.List(i, 4) = "" Then
            If Not lbPoles.List(i, 3) = "" Then
                lbOwners.List(iIndex, 3) = CInt(lbOwners.List(iIndex, 3)) + 1
            End If
        Else
            If lbPoles.List(i, 3) = "" Then
                lbOwners.List(iIndex, 1) = CInt(lbOwners.List(iIndex, 1)) + 1
            Else
                lbOwners.List(iIndex, 2) = CInt(lbOwners.List(iIndex, 2)) + 1
            End If
        End If
        
        If Not lbPoles.List(i, 3) = "" Then
            vAttach = Split(UCase(lbPoles.List(i, 3)), " ")
            
            For j = 0 To UBound(vAttach)
                strLine = Replace(vAttach(j), "T", "")
                vItem = Split(strLine, "-")
                
                iHeight = CInt(vItem(0)) * 12
                If UBound(vItem) > 0 Then iHeight = iHeight + CInt(vItem(1))
                If iHeight > 288 Then
                    lbData.AddItem lbPoles.List(i, 1)
                    lbData.List(lbData.ListCount - 1, 1) = lbPoles.List(i, 0)
                    lbData.List(lbData.ListCount - 1, 2) = lbPoles.List(i, 2)
                    lbData.List(lbData.ListCount - 1, 3) = lbPoles.List(i, 3)
                    GoTo Next_I
                End If
            Next j
        End If
Next_I:
    Next i
    
    If lbOwners.ListCount > 0 Then
        For i = 0 To lbOwners.ListCount - 1
            cbOwners.AddItem lbOwners.List(i, 0)
        Next i
    End If
    
    tbTotalEH.Value = lbData.ListCount
End Sub

Private Sub SortEH()
    Dim strTemp, strTotal As String
    Dim iCount, iOffset As Integer
    Dim iIndex As Integer
    Dim strAtt(0 To 1) As String
    
    iCount = lbEHReport.ListCount - 1
    If iCount < 1 Then Exit Sub
    
    On Error Resume Next
    
    For a = iCount To 0 Step -1
        For b = 0 To a - 1
            If lbEHReport.List(b, 0) > lbEHReport.List(b + 1, 0) Then
                If Not Err = 0 Then
                    MsgBox "Error sorting list"
                    lbEHReport.Selected(b) = True
                    lbEHReport.ListIndex = b
                    Exit Sub
                End If
                
                strAtt(0) = lbEHReport.List(b + 1, 0)
                strAtt(1) = lbEHReport.List(b + 1, 1)
                
                lbEHReport.List(b + 1, 0) = lbEHReport.List(b, 0)
                lbEHReport.List(b + 1, 1) = lbEHReport.List(b, 1)
                
                lbEHReport.List(b, 0) = strAtt(0)
                lbEHReport.List(b, 1) = strAtt(1)
            End If
        Next b
    Next a
End Sub

Attribute VB_Name = "FindMissingCallouts"
Attribute VB_Base = "0{2057E391-5C91-410C-9F48-A29116B4D6A0}{C5AA695B-D779-4DAB-8424-EE0B1452731F}"
Attribute VB_GlobalNameSpace = False
Attribute VB_Creatable = False
Attribute VB_PredeclaredId = True
Attribute VB_Exposed = False
Attribute VB_TemplateDerived = False
Attribute VB_Customizable = False
Private Sub cbMark_Click()
    If lbPoles.ListCount < 1 Then Exit Sub
    
    For i = 0 To lbPoles.ListCount - 1
        If Not lbPoles.List(i, 2) = "x" And Not lbPoles.List(i, 3) = "x" Then lbPoles.Selected(i) = True
        If lbPoles.List(i, 3) = "x" And i > 0 Then lbPoles.Selected(i - 1) = False
    Next i
End Sub

Private Sub cbSort_Click()
    Call SortPoles
End Sub

Private Sub cbWindow_Click()
    Dim filterType, filterValue As Variant
    Dim grpCode(0) As Integer
    Dim grpValue(0) As Variant
    Dim objSS As AcadSelectionSet
    Dim objBlock As AcadBlockReference
    Dim vAttList As Variant
    Dim vItem, vLine, vTemp, vL, vR As Variant
    Dim vPnt1, vPnt2 As Variant
    Dim strLine As String
    Dim iIndex, iPos, iLength As Integer
    
    On Error Resume Next
    
    Me.Hide
    
    lbPoles.Clear
        
    Err = 0
    vPnt1 = ThisDrawing.Utility.GetPoint(, "Get BL Corner: ")
    vPnt2 = ThisDrawing.Utility.GetCorner(vPnt1, vbCr & "Get UR Corner: ")
    If Not Err = 0 Then GoTo Exit_Sub
    
    grpCode(0) = 2
    grpValue(0) = "sPole,sPed,sHH"
    filterType = grpCode
    filterValue = grpValue
    
    Err = 0
    Set objSS = ThisDrawing.SelectionSets.Add("objSS")
    If Not Err = 0 Then
        Set objSS = ThisDrawing.SelectionSets.Item("objSS")
    End If
    objSS.Select acSelectionSetWindow, vPnt1, vPnt2, filterType, filterValue
    
    For Each objBlock In objSS
        vAttList = objBlock.GetAttributes
        If vAttList(0).TextString = "POLE" Then GoTo Next_objBlock
        If vAttList(0).TextString = "" Then GoTo Next_objBlock
        
        Select Case objBlock.Name
            Case "sPole"
                If vAttList(25).TextString = "" Then GoTo Next_objBlock
                iPos = 26
            Case Else
                If vAttList(5).TextString = "" Then GoTo Next_objBlock
                iPos = 6
        End Select
        
        strLine = UCase(vAttList(0).TextString)
        vTemp = Split(strLine, "/")
        vL = Split(vTemp(UBound(vTemp)), "L")
        vR = Split(vL(UBound(vL)), "R")
        
        iLength = Len(strLine) - Len(vR(UBound(vR)))
        
        lbPoles.AddItem Left(strLine, iLength)
        iIndex = lbPoles.ListCount - 1
        lbPoles.List(iIndex, 1) = vR(UBound(vR))
        If vAttList(iPos).TextString = "" Then
            lbPoles.List(iIndex, 2) = " "
        Else
            lbPoles.List(iIndex, 2) = "M"
        End If
        lbPoles.List(iIndex, 3) = " "
        lbPoles.List(iIndex, 4) = objBlock.InsertionPoint(0) & "," & objBlock.InsertionPoint(1)
Next_objBlock:
    Next objBlock
    
    objSS.Clear
    'Call SortPoles
    
    grpCode(0) = 2
    grpValue(0) = "Callout"
    filterType = grpCode
    filterValue = grpValue
    
    objSS.Select acSelectionSetWindow, vPnt1, vPnt2, filterType, filterValue
    
    For Each objBlock In objSS
        vAttList = objBlock.GetAttributes
        If vAttList(0).TextString = "" Then GoTo Next_Callout
        
        strLine = vAttList(0).TextString
        vTemp = Split(strLine, ": ")
        For i = 0 To lbPoles.ListCount - 1
            If vTemp(0) = lbPoles.List(i, 0) & lbPoles.List(i, 1) Then
                If Left(vAttList(1).TextString, 4) = "+HO1" Then
                    lbPoles.List(i, 2) = "x"
                Else
                    lbPoles.List(i, 3) = "x"
                End If
                GoTo Next_Callout
            End If
        Next i
        
Next_Callout:
    Next objBlock
    
    
Exit_Sub:
    objSS.Clear
    objSS.Delete
    
    Me.show
End Sub

Private Sub lbPoles_DblClick(ByVal Cancel As MSForms.ReturnBoolean)
    Dim vCoords As Variant
    Dim viewCoordsB(0 To 2) As Double
    Dim viewCoordsE(0 To 2) As Double
    
    Me.Hide
    
    On Error Resume Next
    
    vCoords = Split(lbPoles.List(lbPoles.ListIndex, 4), ",")
    
    viewCoordsB(0) = vCoords(0) - 300
    viewCoordsB(1) = vCoords(1) - 300
    viewCoordsB(2) = 0#
    viewCoordsE(0) = vCoords(0) + 300
    viewCoordsE(1) = vCoords(1) + 300
    viewCoordsE(2) = 0#
    
    ThisDrawing.Application.ZoomWindow viewCoordsB, viewCoordsE
    
    Load PlaceCountCallouts
        PlaceCountCallouts.show
    Unload PlaceCountCallouts
    
    Me.show
End Sub

Private Sub UserForm_Initialize()
    lbPoles.ColumnCount = 5
    lbPoles.ColumnWidths = "120;48;36;30;6"
End Sub

Private Sub SortPoles()
    Dim strTemp, strTotal As String
    Dim iCount, iOffset As Integer
    Dim iIndex As Integer
    Dim strAtt(0 To 4) As String
    'Dim strTemp As String
    Dim iB, iB1 As Integer
    
    iCount = lbPoles.ListCount - 1
    If iCount < 1 Then Exit Sub
    
    'On Error Resume Next
    
    For a = iCount To 0 Step -1
        For b = 0 To a - 1
            Select Case lbPoles.List(b, 0)
                Case Is < lbPoles.List(b + 1, 0)
                    GoTo Next_line
                Case Is = lbPoles.List(b + 1, 0)
                    'If CInt(lbPoles.List(b, 1)) < CInt(lbPoles.List(b + 1, 1)) Then GoTo Next_Line
                    strTemp = Replace(lbPoles.List(b, 1), "X", "")
                    iB = CInt(strTemp)
                    
                    strTemp = Replace(lbPoles.List(b + 1, 1), "X", "")
                    iB1 = CInt(strTemp)
                        
                    If iB < iB1 Then GoTo Next_line
            End Select
                
            strAtt(0) = lbPoles.List(b + 1, 0)
            strAtt(1) = lbPoles.List(b + 1, 1)
            strAtt(2) = lbPoles.List(b + 1, 2)
            strAtt(3) = lbPoles.List(b + 1, 3)
            strAtt(4) = lbPoles.List(b + 1, 4)
                
            lbPoles.List(b + 1, 0) = lbPoles.List(b, 0)
            lbPoles.List(b + 1, 1) = lbPoles.List(b, 1)
            lbPoles.List(b + 1, 2) = lbPoles.List(b, 2)
            lbPoles.List(b + 1, 3) = lbPoles.List(b, 3)
            lbPoles.List(b + 1, 4) = lbPoles.List(b, 4)
                
            lbPoles.List(b, 0) = strAtt(0)
            lbPoles.List(b, 1) = strAtt(1)
            lbPoles.List(b, 2) = strAtt(2)
            lbPoles.List(b, 3) = strAtt(3)
            lbPoles.List(b, 4) = strAtt(4)
Next_line:
        Next b
    Next a
End Sub

Attribute VB_Name = "GetCableLengths"
Attribute VB_Base = "0{A26F348A-6EFA-4A7A-9104-8F31780F4B2E}{BBAEE3A8-1324-4429-A65B-0EC1893A2ECB}"
Attribute VB_GlobalNameSpace = False
Attribute VB_Creatable = False
Attribute VB_PredeclaredId = True
Attribute VB_Exposed = False
Attribute VB_TemplateDerived = False
Attribute VB_Customizable = False

Private Sub cbBlock_Click()
    If cbBlock.Value = True Then
        cbLines.Value = False
        cbPolylines.Value = False
    End If
End Sub

Private Sub cbQuit_Click()
    Me.Hide
End Sub

Private Sub cbRun_Click()
    tbTotalFeet.Value = "0"
    tbLines.Value = "0"
    tbPolylines.Value = "0"
    tbBlock.Value = "0"
    
    Me.Hide
    
    For i = 0 To lbLayers.ListCount - 1
        If lbLayers.Selected(i) Then Call GetData(CStr(lbLayers.List(i)))
    Next i
    
    Me.show
End Sub

Private Sub Label1_Click()
    Dim objEntity As AcadEntity
    Dim vReturnPnt As Variant
    
    Me.Hide
    
    ThisDrawing.Utility.GetEntity objEntity, vReturnPnt, "Select Object on Layer:"
    
    For i = 0 To lbLayers.ListCount - 1
        lbLayers.Selected(i) = False
        If lbLayers.List(i) = objEntity.Layer Then lbLayers.Selected(i) = True
    Next i
    
    Me.show
End Sub

Private Sub UserForm_Initialize()
    Dim objLayers As AcadLayers
    Dim objLayer As AcadLayer
    
    Set objLayers = ThisDrawing.Layers
    For Each objLayer In objLayers
        lbLayers.AddItem objLayer.Name
    Next objLayer
    
    Call SortList
    
    For i = 0 To lbLayers.ListCount - 1
        If lbLayers.List(i) = "Integrity Cable-Aerial" Then lbLayers.Selected(i) = True
    Next i
    
    cbSelect.AddItem "Select All"
    cbSelect.AddItem "Window"
    cbSelect.AddItem "Existing Polygon"
    cbSelect.Value = "Existing Polygon"
End Sub

Private Sub GetData(strLayer As String)
    Dim objSS As AcadSelectionSet
    Dim grpCode(0) As Integer
    Dim grpValue(0) As Variant
    Dim filterType, filterValue As Variant
    Dim objEntity As AcadEntity
    Dim objBlock As AcadBlockReference
    Dim objLine As AcadLine
    Dim objLWP As AcadLWPolyline
    Dim vAttList, vLine As Variant
    Dim vReturnPnt As Variant
    Dim vCoords, vArray As Variant
    Dim strTemp As String
    Dim dCoords() As Double
    Dim iTemp, iCounter As Integer
    Dim lLine, lLWP, lBlock, lTotal As Long

    lLine = CLng(tbLines.Value)
    lLWP = CLng(tbPolylines.Value)
    lBlock = CLng(tbBlock.Value)
    lTotal = CLng(tbTotalFeet.Value) * 1000
    
    grpCode(0) = 8
    grpValue(0) = strLayer
    filterType = grpCode
    filterValue = grpValue
    
    On Error Resume Next
    Set objSS = ThisDrawing.SelectionSets.Item("objSS")
    If Not Err = 0 Then
        Set objSS = ThisDrawing.SelectionSets.Add("objSS")
        Err = 0
    End If
    
    Select Case cbSelect.Value
        Case "Select All"
            objSS.Select acSelectionSetAll, , , filterType, filterValue
        Case "Window"
            objSS.SelectOnScreen filterType, filterValue
        Case "Existing Polygon"
            ThisDrawing.Utility.GetEntity objEntity, vReturnPnt, "Select Polygon: "
            If Not objEntity.ObjectName = "AcDbPolyline" Then
                MsgBox "Error: Invalid Selection."
                GoTo Exit_Sub
            End If
    
            Set objLWP = objEntity
            vCoords = objLWP.Coordinates
    
            iTemp = (UBound(vCoords) + 1) / 2 * 3 - 1
            ReDim dCoords(iTemp) As Double
    
            iCounter = 0
            For i = 0 To UBound(vCoords) Step 2
                dCoords(iCounter) = vCoords(i)
                iCounter = iCounter + 1
                dCoords(iCounter) = vCoords(i + 1)
                iCounter = iCounter + 1
                dCoords(iCounter) = 0#
                iCounter = iCounter + 1
            Next i
    
            objSS.SelectByPolygon acSelectionSetWindowPolygon, dCoords, filterType, filterValue
    End Select
    
    For Each objEntity In objSS
        If TypeOf objEntity Is AcadLWPolyline Then
            Set objLWP = objEntity
            
            lLWP = lLWP + CLng(objLWP.Length)
        ElseIf TypeOf objEntity Is AcadLine Then
            Set objLine = objEntity
            
            lLine = lLine + CLng(objLine.Length)
        ElseIf TypeOf objEntity Is AcadBlockReference Then
            If cbBlock.Value = False Then GoTo Next_objEntity
            
            Set objBlock = objEntity
            If Not objBlock.Name = "cable_span" Then GoTo Next_objEntity
            
            vAttList = objBlock.GetAttributes
            vLine = Split(vAttList(2).TextString, " ")
            strTemp = Replace(vLine(UBound(vLine)), "'", "")
                
            lBlock = lBlock + CLng(strTemp)
        End If
        
Next_objEntity:
    Next objEntity
    
    If cbLines.Value = True Then
        tbLines.Value = lLine
        lTotal = lTotal + lLine
    Else
        tbLines.Value = "0"
    End If
    
    If cbPolylines.Value = True Then
        tbPolylines.Value = lLWP
        lTotal = lTotal + lLWP
    Else
        tbPolylines.Value = "0"
    End If
    
    If cbBlock.Value = True Then
        tbBlock.Value = lBlock
        lTotal = lTotal + lBlock
    Else
        tbBlock.Value = "0"
    End If
    
    tbTotalFeet.Value = lTotal / 1000
    tbTotalMiles.Value = CInt(lTotal / 5.28 + 0.5) / 1000
Exit_Sub:
    objSS.Clear
    objSS.Delete
    
End Sub

Private Sub SortList()
    Dim strLayer As String
    Dim iCount As Integer
    
    iCount = lbLayers.ListCount - 1
    
    For a = iCount To 1 Step -1
        For b = 0 To a - 1
            If lbLayers.List(b) > lbLayers.List(b + 1) Then
                strLayer = lbLayers.List(b + 1)
                
                lbLayers.List(b + 1) = lbLayers.List(b)
                
                lbLayers.List(b) = strLayer
            End If
        Next b
    Next a
End Sub

Attribute VB_Name = "GetDataByPoly"
Attribute VB_Base = "0{C7686C9D-E5F8-42C8-A40A-F30B0E871B8E}{199501CB-E165-4913-9823-F9AF57AA1BEF}"
Attribute VB_GlobalNameSpace = False
Attribute VB_Creatable = False
Attribute VB_PredeclaredId = True
Attribute VB_Exposed = False
Attribute VB_TemplateDerived = False
Attribute VB_Customizable = False
Dim dCoords() As Double
    
Private Sub cbClearTab_Click()
    lbTab.Clear
    
    For i = 0 To lbBlocks.ListCount - 1
        lbBlocks.List(i, 2) = Replace(lbBlocks.List(i, 2), "+ ", "")
    Next i
End Sub

Private Sub cbGetPolygon_Click()
    Dim objEntity As AcadEntity
    Dim objLWP As AcadLWPolyline
    Dim vReturnPnt As Variant
    Dim vCoords As Variant
    Dim iTemp, iCounter As Integer
    
    Me.Hide
    
    On Error Resume Next
    
    ThisDrawing.Utility.GetEntity objEntity, vReturnPnt, "Select Polygon: "
    If Not Err = 0 Then GoTo Exit_Sub
    
    If Not objEntity.ObjectName = "AcDbPolyline" Then
        MsgBox "Error: Invalid Selection."
        GoTo Exit_Sub
    End If
    
    Set objLWP = objEntity
    vCoords = objLWP.Coordinates
    
    iTemp = (UBound(vCoords) + 1) / 2 * 3 - 1
    ReDim dCoords(iTemp) As Double
    
    iCounter = 0
    For i = 0 To UBound(vCoords) Step 2
        dCoords(iCounter) = vCoords(i)
        iCounter = iCounter + 1
        dCoords(iCounter) = vCoords(i + 1)
        iCounter = iCounter + 1
        dCoords(iCounter) = 0#
        iCounter = iCounter + 1
    Next i
    
    For i = 0 To lbLayers.ListCount - 1
        Call GetLayerData(CStr(lbLayers.List(i)))
    Next i
    
Exit_Sub:
    Me.show
End Sub

Private Sub cbSort_Click()
    Dim iCount As Integer
    Dim iIndex As Integer
    Dim strAtt(1) As String
    
    iCount = lbTab.ListCount - 1
    
    On Error Resume Next
    
    For a = iCount To 0 Step -1
        For b = 0 To a - 1
            If lbTab.List(b, 0) > lbTab.List(b + 1, 0) Then
                strAtt(0) = lbTab.List(b + 1, 0)
                strAtt(1) = lbTab.List(b + 1, 1)
                
                lbTab.List(b + 1, 0) = lbTab.List(b, 0)
                lbTab.List(b + 1, 1) = lbTab.List(b, 1)
                
                lbTab.List(b, 0) = strAtt(0)
                lbTab.List(b, 1) = strAtt(1)
            End If
        Next b
    Next a
End Sub

Private Sub lbBlocks_DblClick(ByVal Cancel As MSForms.ReturnBoolean)
    If lbBlocks.ListCount < 1 Then Exit Sub
    If InStr(lbBlocks.List(lbBlocks.ListIndex, 2), "+ ") > 0 Then Exit Sub
    
    Dim objSS As AcadSelectionSet
    Dim grpCode(0) As Integer
    Dim grpValue(0) As Variant
    Dim filterType, filterValue As Variant
    Dim objEntity As AcadEntity
    Dim objBlock As AcadBlockReference
    Dim vAttList, vList, vItem As Variant
    Dim strBlock, strLayer As String
    Dim strLine As String
    
    strLayer = lbBlocks.List(lbBlocks.ListIndex, 0)
    strBlock = lbBlocks.List(lbBlocks.ListIndex, 1)
    lbBlocks.List(lbBlocks.ListIndex, 2) = "+ " & lbBlocks.List(lbBlocks.ListIndex, 2)
    
    grpCode(0) = 2
    grpValue(0) = strBlock
    filterType = grpCode
    filterValue = grpValue
    
    On Error Resume Next
    Set objSS = ThisDrawing.SelectionSets.Item("objSS")
    If Not Err = 0 Then
        Set objSS = ThisDrawing.SelectionSets.Add("objSS")
        objSS.Clear
        Err = 0
    End If
    
    objSS.SelectByPolygon acSelectionSetWindowPolygon, dCoords, filterType, filterValue
    
    For Each objBlock In objSS
        If Not objBlock.Layer = strLayer Then GoTo Next_objBlock
        
        vAttList = objBlock.GetAttributes
        Select Case objBlock.Name
            Case "sPole"
                strLine = vAttList(27).TextString
                
                Call GetStructureInfo(CStr(strLine))
            Case "sPed", "sHH", "sMH", "sPanel", "sFP"
                strLine = vAttList(7).TextString
                
                Call GetStructureInfo(CStr(strLine))
            Case "Customer"
                strLine = "<> " & vAttList(0).TextString
                
                Call GetCustomerInfo(CStr(strLine))
            Case "cable_span"
                strLine = vAttList(1).TextString & ";;" & Replace(vAttList(2).TextString, "'", "")
                
                Call GetCableSpanInfo(CStr(strLine))
            Case "Map coil"
                strLine = "CO(" & Replace(vAttList(1).TextString, "F", "") & ")COIL;;" & Replace(vAttList(0).TextString, "'", "")
                
                Call GetCableSpanInfo(CStr(strLine))
            Case "Map splice"
                strLine = "* " & vAttList(0).TextString
                
                Call GetCustomerInfo(CStr(strLine))
            Case "ExGuyOL", "ExGuyOR"
                strLine = "* PE1"
                If InStr(LCase(strLayer), "remove") > 0 Then strLine = "* XXPE1"
                If InStr(LCase(strLayer), "exist") > 0 Then GoTo Next_objBlock
                
                Call GetCustomerInfo(CStr(strLine))
            Case "ExAncOL", "ExAncOR"
                strLine = "* PF1"
                If InStr(LCase(strLayer), "remove") > 0 Then strLine = "* XXPF1"
                If InStr(LCase(strLayer), "exist") > 0 Then GoTo Next_objBlock
                
                Call GetCustomerInfo(CStr(strLine))
        End Select
        
Next_objBlock:
    Next objBlock
    
Exit_Sub:
    objSS.Clear
    objSS.Delete
End Sub

Private Sub UserForm_Initialize()
    lbLines.ColumnCount = 6
    lbLines.ColumnWidths = "120;36;72;36;72;72"
    
    lbBlocks.ColumnCount = 3
    lbBlocks.ColumnWidths = "120;120;48"
    
    lbTab.ColumnCount = 2
    lbTab.ColumnWidths = "132;54"
    
    Dim objLayer As AcadLayer
    For Each objLayer In ThisDrawing.Layers
        lbLayers.AddItem objLayer.Name
    Next objLayer
    
    If lbLayers.ListCount > 1 Then
        Dim iCount As Integer
        Dim iIndex As Integer
        Dim strAtt As String
    
        iCount = lbLayers.ListCount - 1
    
        On Error Resume Next
    
        For a = iCount To 0 Step -1
            For b = 0 To a - 1
                If lbLayers.List(b, 0) > lbLayers.List(b + 1, 0) Then
                    strAtt = lbLayers.List(b + 1, 0)
                    lbLayers.List(b + 1, 0) = lbLayers.List(b, 0)
                    lbLayers.List(b, 0) = strAtt
                End If
            Next b
        Next a
    End If
End Sub

Private Sub GetLayerData(strLayer As String)
    Dim objSS As AcadSelectionSet
    Dim grpCode(0) As Integer
    Dim grpValue(0) As Variant
    Dim filterType, filterValue As Variant
    Dim objEntity As AcadEntity
    Dim objBlock As AcadBlockReference
    Dim objLine As AcadLine
    Dim objLWP As AcadLWPolyline
    Dim vAttList, vLine As Variant
    Dim vReturnPnt As Variant
    
    Dim vCoords, vArray As Variant
    Dim strTemp As String
    Dim iTemp, iCounter As Integer
    Dim lLine, lLWP, lBlock, lTotal As Long
    Dim lNLine, lNLWP As Long
    
    lLine = 0
    lLWP = 0
    lBlock = 0
    lNLine = 0
    lNLWP = 0
    
    grpCode(0) = 8
    grpValue(0) = strLayer
    filterType = grpCode
    filterValue = grpValue
    
    On Error Resume Next
    Set objSS = ThisDrawing.SelectionSets.Item("objSS")
    If Not Err = 0 Then
        Set objSS = ThisDrawing.SelectionSets.Add("objSS")
        objSS.Clear
        Err = 0
    End If
    
    objSS.SelectByPolygon acSelectionSetWindowPolygon, dCoords, filterType, filterValue
    
    For Each objEntity In objSS
        If TypeOf objEntity Is AcadLWPolyline Then
            Set objLWP = objEntity
            
            lLWP = lLWP + CLng(objLWP.Length)
            lNLWP = lNLWP + 1
        ElseIf TypeOf objEntity Is AcadLine Then
            Set objLine = objEntity
            
            lLine = lLine + CLng(objLine.Length)
            lNLine = lNLine + 1
        ElseIf TypeOf objEntity Is AcadBlockReference Then
            Set objBlock = objEntity
            
            If lbBlocks.ListCount < 1 Then
                lbBlocks.AddItem strLayer
                lbBlocks.List(0, 1) = objBlock.Name
                lbBlocks.List(0, 2) = "1"
                
                GoTo Next_objEntity
            End If
            
            For i = 0 To lbBlocks.ListCount - 1
                If lbBlocks.List(i, 0) = strLayer Then
                    If lbBlocks.List(i, 1) = objBlock.Name Then
                        lbBlocks.List(i, 2) = CInt(lbBlocks.List(i, 2)) + 1
                        
                        GoTo Next_objEntity
                    End If
                End If
            Next i
            
            lbBlocks.AddItem strLayer
            lbBlocks.List(lbBlocks.ListCount - 1, 1) = objBlock.Name
            lbBlocks.List(lbBlocks.ListCount - 1, 2) = "1"
        End If
Next_objEntity:
    Next objEntity
    
    lTotal = lLine + lLWP
    If lTotal > 0 Then
        lbLines.AddItem strLayer
        lbLines.List(lbLines.ListCount - 1, 1) = lNLine
        lbLines.List(lbLines.ListCount - 1, 2) = lLine
        lbLines.List(lbLines.ListCount - 1, 3) = lNLWP
        lbLines.List(lbLines.ListCount - 1, 4) = lLWP
        lbLines.List(lbLines.ListCount - 1, 5) = lTotal
    End If
    
    objSS.Clear
    objSS.Delete
End Sub

Private Sub GetStructureInfo(strLine As String)
    If strLine = "" Then Exit Sub
    
    Dim vList, vItem, vTemp As Variant
    
    vList = Split(strLine, ";;")
    For i = 0 To UBound(vList)
        vItem = Split(vList(i), "=")
        vItem(0) = Replace(vItem(0), "+", "")
        vItem(1) = Replace(vItem(1), "'", "")
        
        If InStr(vItem(1), " ") > 0 Then
            vTemp = Split(vItem(1), "  ")
            vItem(0) = vItem(0) & vbTab & vTemp(UBound(vTemp))
            vItem(1) = vTemp(0)
        Else
            vItem(0) = vItem(0) & vbTab
        End If
        
        If lbTab.ListCount < 1 Then
            lbTab.AddItem vItem(0)
            lbTab.List(0, 1) = vItem(1)
            
            GoTo Next_I
        End If
        
        For j = 0 To lbTab.ListCount - 1
            If vItem(0) = lbTab.List(j, 0) Then
                lbTab.List(j, 1) = CLng(lbTab.List(j, 1)) + CLng(vItem(1))
                GoTo Next_I
            End If
        Next j
        
        lbTab.AddItem vItem(0)
        lbTab.List(lbTab.ListCount - 1, 1) = vItem(1)
        
Next_I:
    Next i
End Sub

Private Sub GetCustomerInfo(strLine As String)
    If strLine = "" Then Exit Sub
    
    If lbTab.ListCount < 1 Then
        lbTab.AddItem strLine
        lbTab.List(0, 1) = 1
        
        Exit Sub
    End If
    
    For i = 0 To lbTab.ListCount - 1
        If strLine = lbTab.List(i, 0) Then
            lbTab.List(i, 1) = CInt(lbTab.List(i, 1)) + 1
            
            Exit Sub
        End If
    Next i
    
    lbTab.AddItem strLine
    lbTab.List(lbTab.ListCount - 1, 1) = 1
End Sub

Private Sub GetCableSpanInfo(strLine As String)
    If strLine = "" Then Exit Sub
    
    Dim vItem, vCables As Variant
    Dim strCable As String
    
    vItem = Split(strLine, ";;")
    vCables = Split(vItem(0), " ")
    
    For i = 0 To UBound(vCables)
        strCable = "* " & vCables(i)
        
        If lbTab.ListCount < 1 Then
            lbTab.AddItem strCable
            lbTab.List(0, 1) = vItem(1)
            
            GoTo Next_I
        End If
        
        For j = 0 To lbTab.ListCount - 1
            If lbTab.List(j, 0) = strCable Then
                lbTab.List(j, 1) = CLng(lbTab.List(j, 1)) + CInt(vItem(1))
                
                GoTo Next_I
            End If
        Next j
        
        lbTab.AddItem strCable
        lbTab.List(lbTab.ListCount - 1, 1) = vItem(1)
Next_I:
    Next i
End Sub

Attribute VB_Name = "GetSpansReel"
Attribute VB_Base = "0{F6783FFC-21D9-4645-BC5D-90BD955A3749}{59736742-64BE-4C12-AEDA-0B9073204593}"
Attribute VB_GlobalNameSpace = False
Attribute VB_Creatable = False
Attribute VB_PredeclaredId = True
Attribute VB_Exposed = False
Attribute VB_TemplateDerived = False
Attribute VB_Customizable = False
Private Sub cbGetData_Click()
    Dim objSS As AcadSelectionSet
    Dim objEntity As AcadEntity
    Dim objBlock As AcadBlockReference
    Dim objLWP As AcadLWPolyline
    Dim vAttList, vUnits, vItem As Variant
    Dim vTemp, vReturnPnt, vCoords As Variant
    Dim filterType, filterValue As Variant
    Dim vPnt1, vPnt2 As Variant
    Dim grpCode(0) As Integer
    Dim grpValue(0) As Variant
    Dim dPnt1(0 To 2) As Double
    Dim dPnt2(0 To 2) As Double
    Dim strLine As String
    Dim iTemp, iCounter As Integer
    Dim dCoords() As Double

    grpCode(0) = 2
    grpValue(0) = "sPole,sPed,sHH,cable_span,Map coil"
    filterType = grpCode
    filterValue = grpValue
    
    lbUnits.Clear
    lbSpans.Clear
    
  On Error Resume Next
    
    Set objSS = ThisDrawing.SelectionSets.Add("objSS")
    If Not Err = 0 Then
        Set objSS = ThisDrawing.SelectionSets.Item("objSS")
        Err = 0
    End If
  
    Me.Hide
    
    If cbType.Value = "Polygon" Then
        ThisDrawing.Utility.GetEntity objEntity, vReturnPnt, "Select Polygon Border: "
        If Not objEntity.ObjectName = "AcDbPolyline" Then
            MsgBox "Error: Invalid Selection."
            Me.show
            Exit Sub
        End If
    
        Set objLWP = objEntity
        vCoords = objLWP.Coordinates
    
        iTemp = (UBound(vCoords) + 1) / 2 * 3 - 1
        ReDim dCoords(iTemp) As Double
    
        iCounter = 0
        For i = 0 To UBound(vCoords) Step 2
            dCoords(iCounter) = vCoords(i)
            iCounter = iCounter + 1
            dCoords(iCounter) = vCoords(i + 1)
            iCounter = iCounter + 1
            dCoords(iCounter) = 0#
            iCounter = iCounter + 1
        Next i
    
        objSS.SelectByPolygon acSelectionSetCrossingPolygon, dCoords
        'objSS.SelectByPolygon acSelectionSetWindowPolygon, dCoords
    Else
        vPnt1 = ThisDrawing.Utility.GetPoint(, "Get BL Corner: ")
        vPnt2 = ThisDrawing.Utility.GetCorner(vPnt1, vbCr & "Get UR Corner: ")
    
        dPnt1(0) = vPnt1(0)
        dPnt1(1) = vPnt1(1)
        dPnt1(2) = vPnt1(2)
    
        dPnt2(0) = vPnt2(0)
        dPnt2(1) = vPnt2(1)
        dPnt2(2) = vPnt2(2)
  
        objSS.Select acSelectionSetWindow, dPnt1, dPnt2, filterType, filterValue
    End If
    
    ReDim dCoords(0 To 2) As Double
    
    For Each objEntity In objSS
        If Not TypeOf objEntity Is AcadBlockReference Then GoTo Next_Object
            Set objBlock = objEntity
            
            dCoords = objBlock.InsertionPoint
            
            Select Case objBlock.Name
                Case "sPole"
                    vAttList = objBlock.GetAttributes
                    
                    'If vAttList(0).TextString = "xx" Then GoTo Next_Object
                    If vAttList(0).TextString = "" Then GoTo Next_Object
                    If vAttList(0).TextString = "POLE" Then GoTo Next_Object
                    If vAttList(27).TextString = "" Then GoTo Next_Object
                    
                    vUnits = Split(vAttList(27).TextString, ";;")
                    
                    For i = 0 To UBound(vUnits)
                        If Left(vUnits(i), 4) = "+CO(" Then
                            vItem = Split(vUnits(i), "=")
                            vTemp = Split(vItem(0), ")")
                            'If UCase(Right(vItem(0), 1)) = "E" Then
                                'lbUnits.AddItem Replace(vItem(0), "+", "")
                            'Else
                                lbUnits.AddItem Replace(vTemp(0), "+", "") & ")"
                            'End If
                            
                            strLine = Replace(vItem(1), "'", "")
                            strLine = Replace(strLine, "LOOP", "")
                            strLine = Replace(strLine, " ", "")
                                
                            lbUnits.List(lbUnits.ListCount - 1, 1) = strLine
                            lbUnits.List(lbUnits.ListCount - 1, 2) = dCoords(0) & "," & dCoords(1)
                        End If
                    Next i
                Case "sPed", "sHH"
                    vAttList = objBlock.GetAttributes
                    
                    If vAttList(0).TextString = "xx" Then GoTo Next_Object
                    If vAttList(3).TextString = "" Then GoTo Next_Object
                    If vAttList(3).TextString = "POLE" Then GoTo Next_Object
                    If vAttList(7).TextString = "" Then GoTo Next_Object
                    
                    vUnits = Split(vAttList(7).TextString, ";;")
                    
                    For i = 0 To UBound(vUnits)
                        Select Case Left(vUnits(i), 4)
                            Case "+BFO", "+UO("
                                vItem = Split(vUnits(i), "=")
                                vTemp = Split(vItem(0), ")")
                                
                                lbUnits.AddItem Replace(vTemp(0), "+", "") & ")"
                                
                                strLine = Replace(vItem(1), "'", "")
                                strLine = Replace(strLine, "LOOP", "")
                                strLine = Replace(strLine, " ", "")
                                
                                lbUnits.List(lbUnits.ListCount - 1, 1) = strLine
                                lbUnits.List(lbUnits.ListCount - 1, 2) = dCoords(0) & "," & dCoords(1)
                        End Select
                    Next i
                Case "cable_span"
                    If InStr(LCase(objBlock.Layer), "existing") > 0 Then GoTo Next_Object
                    vAttList = objBlock.GetAttributes
                    
                    If InStr(vAttList(2).TextString, "=") > 0 Then GoTo Next_Object
                    
                    If objBlock.Layer = "Integrity Proposed-Buried" Then
                        strLine = cbBuried.Value & "("
                    Else
                        strLine = "CO("
                    End If
                    
                    If Right(vAttList(1).TextString, 1) = " " Then
                        vAttList(1).TextString = Left(vAttList(1).TextString, Len(vAttList(1).TextString) - 1)
                    End If
                    
                    If vAttList(1).TextString = "" Then
                        strLine = strLine & "?)"
                        
                        lbSpans.AddItem strLine
                        lbSpans.List(lbSpans.ListCount - 1, 1) = Replace(vAttList(2).TextString, "'", "")
                        lbSpans.List(lbSpans.ListCount - 1, 2) = dCoords(0) & "," & dCoords(1)
                    Else
                        If InStr(vAttList(1).TextString, " ") > 0 Then
                            vTemp = Split(vAttList(1).TextString, " ")
                            
                            For i = 0 To UBound(vTemp)
                                If InStr(vTemp(i), "(") > 0 Then
                                    lbSpans.AddItem Replace(UCase(vTemp(i)), "E", "")
                                Else
                                    lbSpans.AddItem strLine & Replace(UCase(vTemp(i)), "F", "") & ")"
                                End If
                                lbSpans.List(lbSpans.ListCount - 1, 1) = Replace(vAttList(2).TextString, "'", "")
                                lbSpans.List(lbSpans.ListCount - 1, 2) = dCoords(0) & "," & dCoords(1)
                            Next i
                        Else
                            'strLine = strLine & Replace(UCase(vAttList(2).TextString), "F", "") & ")"
                            If InStr(vAttList(1).TextString, "(") > 0 Then
                                lbSpans.AddItem Replace(UCase(vAttList(1).TextString), "E", "")
                            Else
                                lbSpans.AddItem strLine & Replace(UCase(vAttList(1).TextString), "F", "") & ")"
                            End If
                            lbSpans.List(lbSpans.ListCount - 1, 1) = Replace(vAttList(2).TextString, "'", "")
                            lbSpans.List(lbSpans.ListCount - 1, 2) = dCoords(0) & "," & dCoords(1)
                        End If
                    End If
                Case "Map coil"
                    If InStr(LCase(objBlock.Layer), "existing") > 0 Then GoTo Next_Object
                    vAttList = objBlock.GetAttributes
                    
                    If InStr(LCase(objBlock.Layer), "buried") > 0 Then
                        lbSpans.AddItem cbBuried.Value & "(" & Replace(UCase(vAttList(1).TextString), "F", "") & ")"
                    Else
                        lbSpans.AddItem "CO(" & Replace(UCase(vAttList(1).TextString), "F", "") & ")"
                    End If
                    lbSpans.List(lbSpans.ListCount - 1, 1) = Replace(vAttList(0).TextString, "'", "")
                    lbSpans.List(lbSpans.ListCount - 1, 2) = dCoords(0) & "," & dCoords(1)
            End Select
            
                    
Next_Object:
    Next objEntity
    
Exit_Sub:
    Call GetTotals
    
    objSS.Clear
    objSS.Delete
    Me.show
End Sub

Private Sub cbQuit_Click()
    Me.Hide
End Sub

Private Sub cbRemoveSame_Click()
    If lbUnits.ListCount < 1 Then Exit Sub
    If lbSpans.ListCount < 1 Then Exit Sub
    
    For i = lbUnits.ListCount - 1 To 0 Step -1
        For j = lbSpans.ListCount - 1 To 0 Step -1
            If lbUnits.List(i, 0) = lbSpans.List(j, 0) Then
                If lbUnits.List(i, 1) = lbSpans.List(j, 1) Then
                    lbUnits.RemoveItem i
                    lbSpans.RemoveItem j
                
                    GoTo Next_I
                End If
            End If
        Next j
Next_I:
    Next i
    
    Call GetTotals
End Sub

Private Sub cbSave_Click()
    If lbSpans.ListCount = 0 Then Exit Sub
    
    Dim strFileName As String
    Dim strDWGName As String
    Dim vLine As Variant
    
    'Dim objData As New DataObject
    Dim strCopy As String
    Dim vUnit As Variant
    
    strCopy = ""
    
    For i = 0 To lbUnits.ListCount - 1
        If i = 0 Then
            strCopy = lbUnits.List(i, 0) & "," & lbUnits.List(i, 1)
        Else
            strCopy = strCopy & vbCr & lbUnits.List(i, 0) & "," & lbUnits.List(i, 1)
        End If
    Next i
    
    'If cbCopyToFile.Value = True Then
        strFileName = ThisDrawing.Path & "\"
        vLine = Split(ThisDrawing.Name, " ")
        strFileName = strFileName & vLine(0) & "-Spans and Coils.csv"

        Open strFileName For Output As #1
        
        Print #1, "UNIT,LENGTH"
        Print #1, strCopy
        Close #1
    
        MsgBox "Copied to File"
    'Else
        'objData.SetText strCopy
        'objData.PutInClipboard
    
        'MsgBox "Copied to Clipboard"
    'End If
End Sub

Private Sub lbSpans_DblClick(ByVal Cancel As MSForms.ReturnBoolean)
    Dim vCoords, vAttList As Variant
    Dim viewCoordsB(0 To 2) As Double
    Dim viewCoordsE(0 To 2) As Double
    
    Me.Hide
    
    vCoords = Split(lbSpans.List(lbSpans.ListIndex, 2), ",")
    
    viewCoordsB(0) = vCoords(0) - 200
    viewCoordsB(1) = vCoords(1) - 200
    viewCoordsB(2) = 0#
    viewCoordsE(0) = vCoords(0) + 200
    viewCoordsE(1) = vCoords(1) + 200
    viewCoordsE(2) = 0#
    
    ThisDrawing.Application.ZoomWindow viewCoordsB, viewCoordsE
    
    Me.show
End Sub

Private Sub lbUnits_DblClick(ByVal Cancel As MSForms.ReturnBoolean)
    Dim vCoords, vAttList As Variant
    Dim viewCoordsB(0 To 2) As Double
    Dim viewCoordsE(0 To 2) As Double
    
    Me.Hide
    
    vCoords = Split(lbUnits.List(lbUnits.ListIndex, 2), ",")
    
    viewCoordsB(0) = vCoords(0) - 200
    viewCoordsB(1) = vCoords(1) - 200
    viewCoordsB(2) = 0#
    viewCoordsE(0) = vCoords(0) + 200
    viewCoordsE(1) = vCoords(1) + 200
    viewCoordsE(2) = 0#
    
    ThisDrawing.Application.ZoomWindow viewCoordsB, viewCoordsE
    
    Me.show
End Sub

Private Sub UserForm_Initialize()
    lbUnits.ColumnCount = 3
    lbUnits.ColumnWidths = "72;30;8"
    
    lbSpans.ColumnCount = 3
    lbSpans.ColumnWidths = "72;30;8"
    
    cbType.AddItem "Window"
    cbType.AddItem "Polygon"
    cbType.Value = "Window"
    
    cbBuried.AddItem "BFO"
    cbBuried.AddItem "UO"
    cbBuried.Value = "UO"
End Sub

Private Sub GetTotals()
    Dim lTotal As Long
    
    lTotal = 0
    
    tbUnitCount.Value = lbUnits.ListCount
    tbSpanCount.Value = lbSpans.ListCount
    
    If Not lbUnits.ListCount < 1 Then
        For i = 0 To lbUnits.ListCount - 1
            lTotal = lTotal + CInt(lbUnits.List(i, 1))
        Next i
        
        tbUnits.Value = lTotal
    Else
        tbUnits.Value = "0"
    End If
    
    lTotal = 0
    
    If Not lbSpans.ListCount < 1 Then
        For i = 0 To lbSpans.ListCount - 1
            lTotal = lTotal + CInt(lbSpans.List(i, 1))
        Next i
        
        tbSpans.Value = lTotal
    Else
        tbSpans.Value = "0"
    End If
    
    tbDiffCount.Value = lbUnits.ListCount - lbSpans.ListCount
    tbDiffTotal.Value = CLng(tbUnits.Value) - CLng(tbSpans.Value)
End Sub

Attribute VB_Name = "LoadBlocks"
Attribute VB_Base = "0{897ABB0B-9C1C-46F9-A68E-CAD5779B5CD3}{3B9FB0A3-5908-4BA4-976D-8ED037E02660}"
Attribute VB_GlobalNameSpace = False
Attribute VB_Creatable = False
Attribute VB_PredeclaredId = True
Attribute VB_Exposed = False
Attribute VB_TemplateDerived = False
Attribute VB_Customizable = False

Private Sub cbClear_Click()
    tbRES.Value = "0"
    tbSG.Value = "0"
    tbBUS.Value = "0"
    tbSGNeed.Value = ""
    tbRESNeed.Value = ""
    tbBUSNeed.Value = ""
    tbFibers.Value = ""
    tbSize.Value = ""
End Sub

Private Sub cbCustomers_Click()
    Dim basePoint(0 To 2) As Double
    Dim scaleFactor As Double
    Dim ObjInSS As AcadObject
    Dim obrGP As AcadBlockReference
    Dim vAttItem, basePnt As Variant
    Dim ssObj As AcadSelectionSet
    Dim iSG As Integer
    Dim iRes, iBus, iSize As Integer
    Dim dNeeded As Double
    
    Me.Hide
    On Error Resume Next
    
    iSG = CInt(tbSG.Value)
    iRes = CInt(tbRES.Value)
    iBus = CInt(tbBUS.Value)
    
    Set ssObj = ThisDrawing.SelectionSets.Add("LoadBlocks")
    If Not Err = 0 Then
        Set ssObj = ThisDrawing.SelectionSets.Item("LoadBlocks")
        Err = 0
    End If
    ssObj.SelectOnScreen
    
    For Each ObjInSS In ssObj
        If TypeOf ObjInSS Is AcadBlockReference Then
            Set obrGP = ObjInSS
            Select Case obrGP.Name
                Case "RES", "LOT", "TRLR", "MDU", "CHURCH", "SCHOOL"
                    iRes = iRes + 1
                Case "BUSINESS", "SCHOOL"
                    iBus = iBus + 1
                Case "SG"
                    iSG = iSG + 1
                Case "Customer"
                    vAttList = obrGP.GetAttributes
                    Select Case vAttList(5).TextString
                        Case "", "R", "T", "M", "C"
                            iRes = iRes + 1
                        Case "B", "S"
                            iBus = iBus + 1
                    End Select
                'Case "testblock"    '<------------------------------------- need to get SG in existing load block
                    'attItem = obrGP.GetAttributes
                    'iRes = iRes + cint(attItem(0).TextString)
                    'iBus = iBus + cint(attItem(1).TextString)
            End Select
        End If
        Set obrGP = Nothing
    Next ObjInSS
    
    tbSG.Value = iSG
    tbRES.Value = iRes
    tbBUS.Value = iBus
    tbAll.Value = iSG + iRes + iBus
    tbSGNeed.Value = CInt(iSG * CDbl(TextBox3.Value) + 0.5) 'iSG
    tbRESNeed.Value = CInt(iRes * CDbl(tbGFRES.Value) + 0.5)
    tbBUSNeed.Value = CInt(iBus * CDbl(tbGFBUS.Value) + 0.5)
    tbFibers.Value = CInt(tbSGNeed.Value) + CInt(tbRESNeed.Value) + CInt(tbBUSNeed.Value)
    
    Select Case CInt(tbFibers.Value)
        Case Is < 25
            tbSize.Value = "24"
        Case Is < 37
            tbSize.Value = "36"
        Case Is < 49
            tbSize.Value = "48"
        Case Is < 73
            tbSize.Value = "72"
        Case Is < 97
            tbSize.Value = "96"
        Case Is < 145
            tbSize.Value = "144"
        Case Is < 217
            tbSize.Value = "216"
        Case Is < 289
            tbSize.Value = "288"
        Case Is < 361
            tbSize.Value = "360"
        Case Is < 433
            tbSize.Value = "432"
    End Select
    
    ssObj.Clear
    ssObj.Delete
    'ThisDrawing.SelectionSets.Item("LoadBlocks").Delete
    Me.show
End Sub

Private Sub cbExport_Click()
    Dim objSS As AcadSelectionSet
    Dim objEntity As AcadEntity
    Dim objLWP As AcadLWPolyline
    Dim objBlock As AcadBlockReference
    Dim vReturnPnt As Variant
    Dim vCoords, vArray As Variant
    Dim dCoords() As Double
    Dim strFileName As String
    Dim vTemp As Variant
    
    'Dim iRES, iBUS, iSG, iTemp, iCounter As Integer
    
    iRes = 0: iBus = 0: iSG = 0
    
    On Error Resume Next
    
    vTemp = Split(ThisDrawing.Name, " ")
    strFileName = ThisDrawing.Path & "\" & vTemp(0) & " Homes Passed.csv"
    
    Me.Hide
    
    ThisDrawing.Utility.GetEntity objEntity, vReturnPnt, "Select Trim Border: "
    If Not objEntity.ObjectName = "AcDbPolyline" Then
        MsgBox "Error: Invalid Selection."
        Me.show
        Exit Sub
    End If
    
    Set objLWP = objEntity
    vCoords = objLWP.Coordinates
    
    iTemp = (UBound(vCoords) + 1) / 2 * 3 - 1
    ReDim dCoords(iTemp) As Double
    
    iCounter = 0
    For i = 0 To UBound(vCoords) Step 2
        dCoords(iCounter) = vCoords(i)
        iCounter = iCounter + 1
        dCoords(iCounter) = vCoords(i + 1)
        iCounter = iCounter + 1
        dCoords(iCounter) = 0#
        iCounter = iCounter + 1
    Next i
    
    Err = 0
    Set objSS = ThisDrawing.SelectionSets.Add("objSS")
    If Not Err = 0 Then Set objSS = ThisDrawing.SelectionSets.Item("objSS")
    
    objSS.SelectByPolygon acSelectionSetWindowPolygon, dCoords
    
    If objSS.count < 1 Then GoTo Exit_Sub
    
    Open strFileName For Output As #1
    Print #1, "Type, House #,Street Name,Note"
    
    For Each objEntity In objSS
        If TypeOf objEntity Is AcadBlockReference Then
            Set objBlock = objEntity
            Select Case objBlock.Name
                Case "RES", "LOT", "TRLR", "MDU", "CHURCH", "SCHOOL", "BUSINESS", "SCHOOL"
                    vTemp = objBlock.GetAttributes
                    
                    Print #1, objBlock.Name & "," & vTemp(0).TextString & "," & vTemp(1).TextString & "," & vTemp(2).TextString
                Case "Customer"
                    vTemp = objBlock.GetAttributes
                    
                    Print #1, vTemp(0).TextString & "," & vTemp(1).TextString & "," & vTemp(2).TextString & "," & vTemp(3).TextString
            End Select
        Set objBlock = Nothing
        End If
    Next objEntity
    
    Close #1
    
Exit_Sub:
    objSS.Clear
    objSS.Delete
    
    Me.show
End Sub

Private Sub cbGetLB_Click()
    Dim basePoint(0 To 2) As Double
    Dim scaleFactor As Double
    Dim ObjInSS As AcadObject
    Dim obrGP As AcadBlockReference
    Dim attItem, basePnt As Variant
    Dim ssObj As AcadSelectionSet
    Dim iSG As Integer
    Dim iRes, iBus, iSize As Integer
    Dim dNeeded As Double
    
    Me.Hide
    On Error Resume Next
    
    iSG = CInt(tbSG.Value)
    iRes = CInt(tbRES.Value)
    iBus = CInt(tbBUS.Value)
    
    Set ssObj = ThisDrawing.SelectionSets.Add("LoadBlocks")
    ssObj.SelectOnScreen
    
    For Each ObjInSS In ssObj
        If TypeOf ObjInSS Is AcadBlockReference Then
            Set obrGP = ObjInSS
            
            If obrGP.Name = "loadblock2" Then
                attItem = obrGP.GetAttributes
                iSG = iSG + CInt(attItem(0).TextString)
                iRes = iRes + CInt(attItem(1).TextString)
                iBus = iBus + CInt(attItem(2).TextString)
            End If
        End If
        Set obrGP = Nothing
    Next ObjInSS
    
    tbSG.Value = iSG
    tbRES.Value = iRes
    tbBUS.Value = iBus
    tbAll.Value = iSG + iRes + iBus
    tbSGNeed.Value = CInt(iSG * CDbl(TextBox3.Value) + 0.5) 'iSG
    tbRESNeed.Value = CInt(iRes * CDbl(tbGFRES.Value) + 0.5)
    tbBUSNeed.Value = CInt(iBus * CDbl(tbGFBUS.Value) + 0.5)
    tbFibers.Value = CInt(tbSGNeed.Value) + CInt(tbRESNeed.Value) + CInt(tbBUSNeed.Value)
    
    Select Case CInt(tbFibers.Value)
        Case Is < 25
            tbSize.Value = "24"
        Case Is < 37
            tbSize.Value = "36"
        Case Is < 49
            tbSize.Value = "48"
        Case Is < 73
            tbSize.Value = "72"
        Case Is < 97
            tbSize.Value = "96"
        Case Is < 145
            tbSize.Value = "144"
        Case Is < 217
            tbSize.Value = "216"
        Case Is < 289
            tbSize.Value = "288"
        Case Is < 361
            tbSize.Value = "360"
        Case Is < 433
            tbSize.Value = "432"
    End Select
    
    ThisDrawing.SelectionSets.Item("LoadBlocks").Delete
    Me.show
End Sub

Private Sub cbPlace_Click()
    Dim objBlock As AcadBlockReference
    Dim returnPnt, attItem As Variant
    Dim dScale As Double
    Dim iRes As Integer
    
    dScale = 2#
    
    Me.Hide
    
    returnPnt = ThisDrawing.Utility.GetPoint(, "Select Point: ")
    
    Set objBlock = ThisDrawing.ModelSpace.InsertBlock(returnPnt, "loadblock2", dScale, dScale, dScale, 0)
    
    'iRes = CInt(tbRES.Value) + CInt(tbSG.Value)
    
    attItem = objBlock.GetAttributes
    attItem(0).TextString = tbSG.Value
    attItem(1).TextString = tbRES.Value
    attItem(2).TextString = tbBUS.Value
    attItem(3).TextString = tbFibers.Value
    attItem(4).TextString = tbSize.Value
    objBlock.Update
    
    tbRES.Value = ""
    tbBUS.Value = ""
    tbRESNeed.Value = ""
    tbBUSNeed.Value = ""
    tbFibers.Value = ""
    tbSize.Value = ""
    
    Me.show
End Sub

Private Sub cbPolygon_Click()
    Dim objSS As AcadSelectionSet
    Dim objEntity As AcadEntity
    Dim objLWP As AcadLWPolyline
    Dim objBlock As AcadBlockReference
    Dim vReturnPnt As Variant
    Dim vCoords, vArray As Variant
    Dim vAttList As Variant
    Dim dCoords() As Double
    Dim iRes, iBus, iSG, iTemp, iCounter As Integer
    
    iRes = 0: iBus = 0: iSG = 0
    
    On Error Resume Next
    
    Me.Hide
    
    ThisDrawing.Utility.GetEntity objEntity, vReturnPnt, "Select Polygon Border: "
    If Not objEntity.ObjectName = "AcDbPolyline" Then
        MsgBox "Error: Invalid Selection."
        Me.show
        Exit Sub
    End If
    
    Set objLWP = objEntity
    vCoords = objLWP.Coordinates
    
    iTemp = (UBound(vCoords) + 1) / 2 * 3 - 1
    ReDim dCoords(iTemp) As Double
    
    iCounter = 0
    For i = 0 To UBound(vCoords) Step 2
        dCoords(iCounter) = vCoords(i)
        iCounter = iCounter + 1
        dCoords(iCounter) = vCoords(i + 1)
        iCounter = iCounter + 1
        dCoords(iCounter) = 0#
        iCounter = iCounter + 1
    Next i
    
    Err = 0
    Set objSS = ThisDrawing.SelectionSets.Add("objSS")
    If Not Err = 0 Then Set objSS = ThisDrawing.SelectionSets.Item("objSS")
    
    objSS.SelectByPolygon acSelectionSetWindowPolygon, dCoords
    
    For Each objEntity In objSS
        If TypeOf objEntity Is AcadBlockReference Then
            Set objBlock = objEntity
            Select Case objBlock.Name
                Case "RES", "LOT", "TRLR", "MDU", "CHURCH", "SCHOOL"
                    iRes = iRes + 1
                Case "BUSINESS", "SCHOOL"
                    iBus = iBus + 1
                Case "SG"
                    iSG = iSG + 1
                Case "Customer"
                    vAttList = objBlock.GetAttributes
                    
                    Select Case vAttList(5).TextString
                        Case "", "T", "M", "C"
                            iRes = iRes + 1
                        Case "B", "S"
                            iBus = iBus + 1
                        Case "!"
                            iSG = iSG + 1
                    End Select
            End Select
        Set objBlock = Nothing
        End If
    Next objEntity
    
    objSS.Clear
    objSS.Delete
    
    tbSG.Value = CInt(tbSG.Value) + iSG
    tbRES.Value = CInt(tbRES.Value) + iRes
    tbBUS.Value = CInt(tbBUS.Value) + iBus
    tbAll.Value = CInt(tbSG.Value) + CInt(tbRES.Value) + CInt(tbBUS.Value)
    tbSGNeed.Value = CInt(iSG * CDbl(TextBox3.Value) + 0.5) 'iSG
    tbRESNeed.Value = CInt(iRes * CDbl(tbGFRES.Value) + 0.5)
    tbBUSNeed.Value = CInt(iBus * CDbl(tbGFBUS.Value) + 0.5)
    tbFibers.Value = CInt(tbSGNeed.Value) + CInt(tbRESNeed.Value) + CInt(tbBUSNeed.Value)
    
    Select Case CInt(tbFibers.Value)
        Case Is < 25
            tbSize.Value = "24"
        Case Is < 37
            tbSize.Value = "36"
        Case Is < 49
            tbSize.Value = "48"
        Case Is < 73
            tbSize.Value = "72"
        Case Is < 97
            tbSize.Value = "96"
        Case Is < 145
            tbSize.Value = "144"
        Case Is < 217
            tbSize.Value = "216"
        Case Is < 289
            tbSize.Value = "288"
        Case Is < 361
            tbSize.Value = "360"
        Case Is < 433
            tbSize.Value = "432"
    End Select
    
    Me.show
End Sub

Private Sub cbQuit_Click()
    Me.Hide
End Sub

Private Sub cbSenerio_Change()
    Select Case cbSenerio.Value
        Case "UTC"
            TextBox3.Value = "1"
            tbGFRES.Value = "1.25"
            tbGFBUS.Value = "2"
        Case "Lor Rural"
            TextBox3.Value = "1"
            tbGFRES.Value = "1.5"
            tbGFBUS.Value = "1.5"
        Case "Lor Urban"
            TextBox3.Value = "1"
            tbGFRES.Value = "1.75"
            tbGFBUS.Value = "1.75"
    End Select
    
    tbSGNeed.Value = CInt(CInt(tbSG.Value) * CDbl(TextBox3.Value) + 0.5)
    tbRESNeed.Value = CInt(CInt(tbRES.Value) * CDbl(tbGFRES.Value) + 0.5)
    tbBUSNeed.Value = CInt(CInt(tbBUS.Value) * CDbl(tbGFBUS.Value) + 0.5)
    tbFibers.Value = CInt(tbSGNeed.Value) + CInt(tbRESNeed.Value) + CInt(tbBUSNeed.Value)
End Sub

Private Sub UserForm_Initialize()
    cbSenerio.AddItem ""
    cbSenerio.AddItem "UTC"
    cbSenerio.AddItem "Lor Rural"
    cbSenerio.AddItem "Lor Urban"
    
    cbSenerio.Value = "UTC"
End Sub

Attribute VB_Name = "LotUpdate"
Attribute VB_Base = "0{D2E39704-5706-4537-AC4E-61B65A5DADAD}{3021E685-924F-4DD9-8C09-E2EA47FB1AF0}"
Attribute VB_GlobalNameSpace = False
Attribute VB_Creatable = False
Attribute VB_PredeclaredId = True
Attribute VB_Exposed = False
Attribute VB_TemplateDerived = False
Attribute VB_Customizable = False
Option Explicit
Dim objSS, objSS2 As AcadSelectionSet

Private Sub btn_GenerateMCL_Click()
    Dim filterType, filterValue, filterValue2 As Variant
    Dim grpCode(0) As Integer
    Dim grpValue(0), grpValue2(0) As Variant
    
    Dim vPnt1, vPnt2 As Variant
    Dim dCoords() As Double
    Dim vReturnPnt, vCoords As Variant
    Dim iCounter As Integer
    Dim dPnt1(0 To 2) As Double
    Dim dPnt2(0 To 2) As Double
           
    Dim objEntity As AcadEntity
    Dim objPoint As AcadPoint
    Dim objBlock As AcadBlockReference
    Dim objLWP As AcadLWPolyline
    Dim vBlockAtt As Variant

    Dim strAttList() As String
    Dim strAttTemp() As String
    Dim strLine, strTemp As Variant
    Dim str1, str2, str3 As String
    Dim iCount, iTest As Integer
    Dim iTemp As Integer
    Dim vLine, vTemp, vForm As Variant
    Dim vData As Variant
    On Error Resume Next
    
    'WINDOW SELECT SETTTINGS
    Set objSS = ThisDrawing.SelectionSets.Add("objSS")
    If Not Err = 0 Then
        Set objSS = ThisDrawing.SelectionSets.Item("objSS")
        objSS.Clear
    End If

    
    grpCode(0) = 2
    grpValue(0) = "Customer"
    filterType = grpCode
    filterValue = grpValue
    objSS.Clear
    
    Err = 0
    
    Me.Hide
    
    'WINDOW SELECT SUBROUTINE
    vPnt1 = ThisDrawing.Utility.GetPoint(, "Get BL Corner: ")
    vPnt2 = ThisDrawing.Utility.GetCorner(vPnt1, vbCr & "Get UR Corner: ")
    
    dPnt1(0) = vPnt1(0)
    dPnt1(1) = vPnt1(1)
    dPnt1(2) = vPnt1(2)
    
    dPnt2(0) = vPnt2(0)
    dPnt2(1) = vPnt2(1)
    dPnt2(2) = vPnt2(2)
    
    objSS.Select acSelectionSetWindow, dPnt1, dPnt2, filterType, filterValue
    MsgBox "Customer" & " found:  " & objSS.count
    
    'CODE TO GRAB THE DATA FROM THE MCL FILE
    Dim strFile, strFolder As String
    Dim strFileName As String
    Dim vName, vItem, strText, vText As Variant
    Dim strTab, strCable As String
    Dim fName As String
    Dim iIndex, j As Integer
    
    strFolder = ThisDrawing.Path & "\*.*"
    
    strFile = Dir$(strFolder)
    
    Do While strFile <> ""      '<> is not equal to
        If InStr(strFile, ".mcl") Then
            strTab = Replace(strFile, ".mcl", "")
            vLine = Split(strTab, " -")
            'TabStrip1.Tabs.Add vLine(1), vLine(1)   'THIS CREATES NEW TABS FOR THE LISTS WHICH WE WONT NEED
            
            strFileName = ThisDrawing.Path & "\" & strFile
            
            'OPEN THE FILE AND SAVE THE CONTENTS AND REMOVE VBLF(NEXT LINE) AND VBCR(PARAGRAPH ENTER)
            Open strFileName For Input As #1
                strText = Input(LOF(1), 1)
            Close #1
            
            strText = Replace(strText, vbLf, "")
            vText = Split(strText, vbCr)
            
            txtbx_test = vText(0)
            
            'UPDATING THE FIRST HEADER LINE OF THE TEXT FILE IF IT ALSO HAS A LOT NUMBER (AS OF 10.4.23 MAY NOT BE NEEDED AS WE WILL USE GPS INSTEAD)
            vTemp = Split(vText(0), " ")
            For Each objEntity In objSS
                Set objBlock = objEntity
                vBlockAtt = objBlock.GetAttributes
                
                If InStr(1, vBlockAtt(3).TextString, ", ") > 0 Then
                    strTemp = Split(vBlockAtt(3).TextString, ", ")
                Else
                    GoTo No_Match1
                End If
                
                If vTemp(1) = strTemp(1) Then
                    vTemp(1) = vBlockAtt(1).TextString
                    vText(0) = vTemp(0) & " " & vTemp(1) & " " & vTemp(2)
                End If
No_Match1:
            Next objEntity
            
            'FIND, MATCH, AND REPLACE EACH ROW OF THE TEXT FILE IF THE ADDRESS ROW MATCHES THE LOT
            For j = 1 To UBound(vText)
                    vItem = Split(vText(j), vbTab)
                    
                    For Each objEntity In objSS
                        Set objBlock = objEntity
                        vBlockAtt = objBlock.GetAttributes
                        
                        If InStr(1, vBlockAtt(3).TextString, ", ") > 0 Then
                            strTemp = Split(vBlockAtt(3).TextString, ", ")
                        Else
                            GoTo No_Match2
                        End If

                        If strTemp(1) = vItem(2) Then
                            If Not vItem(2) = "<>" Then
                            
                                vItem(2) = vBlockAtt(1).TextString
                                vItem(3) = vBlockAtt(2).TextString
                                vItem(5) = vBlockAtt(3).TextString
                                
                                
                                vText(j) = vItem(0) & vbTab & vItem(1) & vbTab & vItem(2) & vbTab & vItem(3) & vbTab & vItem(4) & vbTab & vItem(5)
                                
                                GoTo Found_Match
                            End If
                        End If
No_Match2:
                    Next objEntity
Found_Match:

            Next j
            
            'COMBINING THE TEXT FILE ROWS TO MAKE A COMPLETE FILE
            strText = vText(0)
            If UBound(vText) > 0 Then
                For j = 1 To UBound(vText)
                    If Not vText(j) = "" Then strText = strText & vbCr & vText(j)
                Next j
            End If
            
            
            Open strFileName For Output As #1
                Print #1, strText
            Close #1
            

        End If
        strFile = Dir$
    Loop
    
    strTemp.Clear
    vTemp.Clear
    vItem.Clear
    Me.show
    
End Sub

Private Sub btn_UpdateLots_Click()
    Dim vLotsList As Variant
    Dim vStreetNumbersList As Variant
    Dim vAddressesList As Variant
    Dim vTempList1 As String
    Dim vTempList2 As String
    Dim vTempList3 As String
    Dim i, j As Integer
    
    Dim filterType, filterValue, filterValue2 As Variant
    Dim grpCode(0) As Integer
    Dim grpValue(0), grpValue2(0) As Variant
    
    Dim vPnt1, vPnt2 As Variant
    Dim dCoords() As Double
    Dim vReturnPnt, vCoords As Variant
    Dim iCounter As Integer
    Dim dPnt1(0 To 2) As Double
    Dim dPnt2(0 To 2) As Double

    Dim objEntity As AcadEntity
    Dim objPoint As AcadPoint
    Dim objBlock As AcadBlockReference
    Dim objLWP As AcadLWPolyline
    Dim vBlockAtt As Variant

    Dim strAttList() As String
    Dim strAttTemp() As String
    Dim strLine, strTemp As String
    Dim str1, str2, str3 As String
    Dim iCount, iTest As Integer
    Dim iTemp As Integer
    Dim vLine, vTemp, vForm As Variant
    Dim vData As Variant
    
    On Error Resume Next
    
    Set objSS = ThisDrawing.SelectionSets.Add("objSS")
    If Not Err = 0 Then
        Set objSS = ThisDrawing.SelectionSets.Item("objSS")
        objSS.Clear
    End If
    
    Set objSS2 = ThisDrawing.SelectionSets.Add("objSS2")
    If Not Err = 0 Then
        Set objSS2 = ThisDrawing.SelectionSets.Item("objSS2")
        objSS2.Clear
    End If
    
    'create a itemized list of the copy pasted row of Lots
    vTempList1 = txtbx_Lots.Text
    vLotsList = Split(vTempList1, vbTab)
    
    'create an itemized list of the copy pasted street numbers
    vTempList2 = txtbx_StreetNumbers.Text
    vStreetNumbersList = Split(vTempList2, vbTab)
    
    'create an itemized list of the copy pasted Addresses (not needed at this time)
    vTempList3 = txtbx_Addresses.Text
    vAddressesList = Split(vTempList3, vbTab)
        
    grpCode(0) = 2
    grpValue(0) = "Customer"
    grpValue2(0) = "iSplitter"
    filterType = grpCode
    filterValue = grpValue
    filterValue2 = grpValue2
    objSS.Clear
    objSS2.Clear
    
    Err = 0
    
    Me.Hide
    'select all
    'objSS.Select acSelectionSetAll, , , filterType, filterValue
    
    'window select
    vPnt1 = ThisDrawing.Utility.GetPoint(, "Get BL Corner: ")
    vPnt2 = ThisDrawing.Utility.GetCorner(vPnt1, vbCr & "Get UR Corner: ")
    
    dPnt1(0) = vPnt1(0)
    dPnt1(1) = vPnt1(1)
    dPnt1(2) = vPnt1(2)
    
    dPnt2(0) = vPnt2(0)
    dPnt2(1) = vPnt2(1)
    dPnt2(2) = vPnt2(2)
    
    objSS.Select acSelectionSetWindow, dPnt1, dPnt2, filterType, filterValue
    objSS2.Select acSelectionSetWindow, dPnt1, dPnt2, filterType, filterValue2
    
    MsgBox "Customer" & " found:  " & objSS.count
    
    For Each objEntity In objSS
        Set objBlock = objEntity
        vBlockAtt = objBlock.GetAttributes
        
        For i = 0 To UBound(vLotsList)
            If vLotsList(i) = vBlockAtt(1).TextString Then
                vBlockAtt(3).TextString = vBlockAtt(3).TextString & ", " & vLotsList(i)
                vBlockAtt(1).TextString = vStreetNumbersList(i)
                vBlockAtt(2).TextString = vAddressesList(i)
                
                GoTo match_found
            End If
        Next i
match_found:
        objBlock.Update
    
    Next objEntity
    
    For Each objEntity In objSS2
        Set objBlock = objEntity
        vBlockAtt = objBlock.GetAttributes
        
        For i = 0 To UBound(vLotsList)
            vTemp = Split(vBlockAtt(1).TextString, " ")
            
            If vLotsList(i) = vTemp(1) Then
                vTemp(1) = vStreetNumbersList(i)
                vTemp(2) = vAddressesList(i)
                vBlockAtt(1).TextString = vTemp(0) & " " & vTemp(1) & " " & vTemp(2)


                GoTo match_found2
            End If
        Next i
match_found2:
    objBlock.Update
    
    Next objEntity
    
    Me.show
    
End Sub

Attribute VB_Name = "MRReview"
Attribute VB_Base = "0{C6FAF6F2-1884-43CB-8C05-EE1E3534DE50}{B14D56C2-08CA-41FB-94DA-F74E25572D87}"
Attribute VB_GlobalNameSpace = False
Attribute VB_Creatable = False
Attribute VB_PredeclaredId = True
Attribute VB_Exposed = False
Attribute VB_TemplateDerived = False
Attribute VB_Customizable = False
Dim objSS As AcadSelectionSet

Private Sub cbExport_Click()
    If lbAll.ListCount < 1 Then Exit Sub
    
    Dim strPath, strName, strFile As String
    Dim vTemp As Variant
    
    strPath = ThisDrawing.Path
    strName = ThisDrawing.Name
    vTemp = Split(strName, " ")
    
    strFile = strPath & "\" & vTemp(0) & " MR Report.csv"
    
    Open strFile For Output As #1
    
    Print #1, "Structure Number,Owner,New Attachment,MR,Status"
    
    For i = 0 To lbAll.ListCount - 1
        Print #1, lbAll.List(i, 0) & "," & lbAll.List(i, 1) & "," & lbAll.List(i, 2) & "," & lbAll.List(i, 3) & "," & lbAll.List(i, 4)
    Next i
    
    Close #1
End Sub

Private Sub cbFilter_Click()
    If lbAll.ListCount < 1 Then Exit Sub
    If cbOwner.Value = "" And cbStatus.Value = "" Then Exit Sub
    
    Dim strOwner, strStatus As String
    Dim iResult As Integer
    
    strOwner = cbOwner.Value
    strStatus = cbStatus.Value
    
    For i = lbAll.ListCount - 1 To 0 Step -1
        iResult = 0
        
        If strOwner = "" Then
            iResult = 1
        Else
            If strOwner = lbAll.List(i, 1) Then iResult = 1
        End If
        
        If strStatus = "" Then
            iResult = iResult + 1
        Else
            If InStr(lbAll.List(i, 4), strStatus) > 0 Then iResult = iResult + 1
        End If
        
        If iResult < 2 Then lbAll.RemoveItem i
    Next i
End Sub

Private Sub cbFRColumn_Change()
    Dim vLine As Variant
    
    cbFRValue.Clear
    If lbAll.ListCount < 2 Then Exit Sub
    
    Select Case cbFRColumn.Value
        Case "0: Pole Number"
            cbFRValue.AddItem lbAll.List(0, 0)
            
            For i = 1 To lbAll.ListCount - 1
                For j = 0 To cbFRValue.ListCount - 1
                    If cbFRValue.List(j) = lbAll.List(i, 0) Then GoTo Exit_PN
                Next j
        
                cbFRValue.AddItem lbAll.List(i, 0)
Exit_PN:
            Next i
        Case "1: Owner"
            cbFRValue.AddItem lbAll.List(0, 1)
            
            For i = 1 To lbAll.ListCount - 1
                For j = 0 To cbFRValue.ListCount - 1
                    If cbFRValue.List(j) = lbAll.List(i, 1) Then GoTo Exit_J
                Next j
        
                cbFRValue.AddItem lbAll.List(i, 1)
Exit_J:
            Next i
        Case "2: New At"
            cbFRValue.AddItem "none"
            cbFRValue.AddItem "**T"
            cbFRValue.AddItem "**F"
            cbFRValue.AddItem "**O"
            cbFRValue.AddItem "<="
            cbFRValue.AddItem ">="
            cbFRValue.AddItem "="
            
            cbFRValue.Value = "none"
        Case "3: MR"
            cbFRValue.AddItem "none"
            
            For i = 0 To lbAll.ListCount - 1
                If Not lbAll.List(i, 4) = "" Then
                    vLine = Split(lbAll.List(i, 3), ", ")
            
                    For j = 0 To UBound(vLine)
                        If Not cbFRValue.ListCount < 0 Then
                            For k = 0 To cbFRValue.ListCount - 1
                                If cbFRValue.List(k) = vLine(j) Then GoTo Exit_L
                            Next k
                        End If
                        
                        cbFRValue.AddItem vLine(j)
Exit_L:
                    Next j
                End If
            Next i
            
            If cbFRValue.ListCount > 0 Then
                For i = cbFRValue.ListCount - 1 To 0 Step -1
                    If cbFRValue.List(i) = "" Then cbFRValue.RemoveItem i
                    'If cbFRValue.List(i) = " " Then cbFRValue.RemoveItem i
                Next i
            End If
            
            cbFRValue.Value = "none"
        Case "4: Status"
            If Not lbAll.List(0, 4) = "" Then
                vLine = Split(lbAll.List(0, 4), ";")
                For j = 0 To UBound(vLine)
                    cbFRValue.AddItem vLine(j)
                Next j
            End If
            
            For i = 1 To lbAll.ListCount - 1
                If Not lbAll.List(i, 4) = "" Then
                    vLine = Split(lbAll.List(i, 4), ";")
            
                    For j = 0 To UBound(vLine)
                        If Not cbFRValue.ListCount < 0 Then
                            For k = 0 To cbFRValue.ListCount - 1
                                If cbFRValue.List(k) = vLine(j) Then GoTo Exit_K
                            Next k
                        End If
                        
                        cbFRValue.AddItem vLine(j)
Exit_K:
                    Next j
                End If
            Next i
            
            If cbFRValue.ListCount > 0 Then
                For i = cbFRValue.ListCount - 1 To 0 Step -1
                    If cbFRValue.List(i) = "" Then cbFRValue.RemoveItem i
                    'If cbFRValue.List(i) = " " Then cbFRValue.RemoveItem i
                Next i
            End If
        Case Else
    End Select
End Sub

Private Sub cbFROption_Change()
    'If cbFROption.Value = "Filter" Then
        'cbFRRun.Caption = "Filter"
    'Else
        'cbFRRun.Caption = "Remove"
    'End If
End Sub

Private Sub cbFRRun_Click()
    If lbAll.ListCount < 2 Then Exit Sub
    
    Select Case cbFRColumn.Value
        Case "0: Pole Number"
            Call FilterRemovePN
        Case "1: Owner"
            Call FilterRemoveOwner
        Case "2: New At"
            Call FilterRemoveNewAt
        Case "3: MR"
            Call FilterRemoveMR
        Case "4: Status"
            Call FilterRemoveStatus
    End Select
End Sub

Private Sub cbGetPoles_Click()
    Me.Hide
        Call GetAllPoles
    Me.show
End Sub

Private Sub cbQuit_Click()
    Me.Hide
End Sub

Private Sub cbRemove24only_Click()
    Dim iIndex As Integer
    Dim objBlock As AcadBlockReference
    Dim vAttList As Variant
    Dim iMax, iCOMM, iNew, iTemp As Integer
    Dim vLine, vAttach As Variant
    Dim strTemp As String
    
    For i = lbAll.ListCount - 1 To 0 Step -1
        iIndex = CInt(lbAll.List(i, 5))
        
        Set objBlock = objSS.Item(iIndex)
        vAttList = objBlock.GetAttributes
        
        If vAttList(15).TextString = "" Then GoTo Next_I
        
        vLine = Split(vAttList(15).TextString, " ")
        
        If UBound(vLine) > 0 Then GoTo Next_I
        
        strTemp = Replace(UCase(vLine(0)), "T", "")
            
        vAttach = Split(strTemp, "-")
        iNew = CInt(vAttach(0)) * 12
        If UBound(vAttach) > 0 Then iNew = iNew + CInt(vAttach(1))
        
        iMax = FindMaxHeight(iIndex)
        
        'MsgBox "Pwr Max:  " & iMax
        
        If iMax < 288 Then GoTo Next_I
        
        iCOMM = FindTopCOMM(iIndex)
        
        'MsgBox "Top COMM:  " & iCOMM
        
        If iCOMM > 0 Then GoTo Next_I
        
        lbAll.RemoveItem i
Next_I:
    Next i
    
    tbListCount = lbAll.ListCount
End Sub

Private Sub cbRemoveCOMM1_Click()
    Dim iIndex As Integer
    Dim objBlock As AcadBlockReference
    Dim vAttList As Variant
    Dim iMax, iCOMM, iNew, iTemp As Integer
    Dim vLine, vAttach As Variant
    Dim strTemp As String
    
    For i = lbAll.ListCount - 1 To 0 Step -1
        iIndex = CInt(lbAll.List(i, 5))
        
        Set objBlock = objSS.Item(iIndex)
        vAttList = objBlock.GetAttributes
        
        If vAttList(15).TextString = "" Then GoTo Next_I
        
        iMax = FindMaxHeight(iIndex)
        
        iCOMM = FindTopCOMM(iIndex) + 12
        If iCOMM = 1012 Then GoTo Next_I
        
        vLine = Split(vAttList(15).TextString, " ")
        For j = 0 To UBound(vLine)
            strTemp = Replace(UCase(vLine(j)), "T", "")
            vAttach = Split(strTemp, "-")
            
            iNew = CInt(vAttach(0)) * 12
            If UBound(vAttach) > 0 Then iNew = iNew + CInt(vAttach(1))
            
            If iNew > iMax Then GoTo Next_I
            If Not iNew = iCOMM Then GoTo Next_I
        Next j
        
        lbAll.RemoveItem i
Next_I:
    Next i
    
    tbListCount = lbAll.ListCount
End Sub

Private Sub cbRemoveCOMM2_Click()
    Dim iIndex As Integer
    Dim objBlock As AcadBlockReference
    Dim vAttList As Variant
    Dim iMax, iCOMM, iNew, iTemp As Integer
    Dim vLine, vAttach As Variant
    Dim strTemp As String
    
    For i = lbAll.ListCount - 1 To 0 Step -1
        iIndex = CInt(lbAll.List(i, 5))
        
        Set objBlock = objSS.Item(iIndex)
        vAttList = objBlock.GetAttributes
        
        If vAttList(15).TextString = "" Then GoTo Next_I
        
        iMax = FindMaxHeight(iIndex)
        
        iCOMM = FindTopCOMM(iIndex) + 24
        If iCOMM = 1024 Then GoTo Next_I
        
        vLine = Split(vAttList(15).TextString, " ")
        For j = 0 To UBound(vLine)
            strTemp = Replace(UCase(vLine(j)), "T", "")
            vAttach = Split(strTemp, "-")
            
            iNew = CInt(vAttach(0)) * 12
            If UBound(vAttach) > 0 Then iNew = iNew + CInt(vAttach(1))
            
            If iNew > iMax Then GoTo Next_I
            If Not iNew = iCOMM Then GoTo Next_I
        Next j
        
        lbAll.RemoveItem i
Next_I:
    Next i
    
    tbListCount = lbAll.ListCount
End Sub

Private Sub cbRemoveNone_Click()
    For i = lbAll.ListCount - 1 To 0 Step -1
        If lbAll.List(i, 2) = "none" Then lbAll.RemoveItem i
    Next i
    
    tbListCount = lbAll.ListCount
End Sub

Private Sub cbRemoveOCALC_Click()
    If lbAll.ListCount < 1 Then Exit Sub
    If tbRemoveOcalc.Value = "" Then Exit Sub
    
    Dim objTemp As AcadBlockReference
    Dim vAtt As Variant
    Dim strOwner, strStatus As String
    Dim iIndex As Integer
    
    strOwner = UCase(tbRemoveOcalc.Value)
    
    For i = lbAll.ListCount - 1 To 0 Step -1
        If InStr(lbAll.List(i, 4), "OCALC") > 0 Then
            iIndex = CInt(lbAll.List(i, 5))
            
            lbAll.List(i, 4) = Replace(lbAll.List(i, 4), "OCALC;", "")
            lbAll.List(i, 4) = Replace(lbAll.List(i, 4), "OCALC", "")
            
            Set objTemp = objSS.Item(iIndex)
            vAtt = objTemp.GetAttributes
            vAtt(24).TextString = Replace(vAtt(24).TextString, "OCALC;", "")
            vAtt(24).TextString = Replace(vAtt(24).TextString, "OCALC", "")
            objTemp.Update
        End If
    Next i
End Sub

Private Sub cbRemoveQC_Click()
    For i = lbAll.ListCount - 1 To 0 Step -1
        If InStr(lbAll.List(i, 4), "MR-QC") > 0 Then lbAll.RemoveItem i
    Next i
    
    tbListCount = lbAll.ListCount
End Sub

Private Sub cbRemoveTag_Click()
    For i = lbAll.ListCount - 1 To 0 Step -1
        If InStr(UCase(lbAll.List(i, 2)), "T") > 0 Then lbAll.RemoveItem i
    Next i
    
    tbListCount = lbAll.ListCount
End Sub

Private Sub cbReset_Click()
    lbAll.Clear
    
    For i = 0 To lbList.ListCount - 1
        If cbInclude.Value = False Then
            If Not lbList.List(i, 0) = "POLE" Then
                lbAll.AddItem lbList.List(i, 0)
                lbAll.List(lbAll.ListCount - 1, 1) = lbList.List(i, 1)
                lbAll.List(lbAll.ListCount - 1, 2) = lbList.List(i, 2)
                lbAll.List(lbAll.ListCount - 1, 3) = lbList.List(i, 3)
                lbAll.List(lbAll.ListCount - 1, 4) = lbList.List(i, 4)
                lbAll.List(lbAll.ListCount - 1, 5) = lbList.List(i, 5)
            End If
        Else
            lbAll.AddItem lbList.List(i, 0)
            lbAll.List(lbAll.ListCount - 1, 1) = lbList.List(i, 1)
            lbAll.List(lbAll.ListCount - 1, 2) = lbList.List(i, 2)
            lbAll.List(lbAll.ListCount - 1, 3) = lbList.List(i, 3)
            lbAll.List(lbAll.ListCount - 1, 4) = lbList.List(i, 4)
            lbAll.List(lbAll.ListCount - 1, 5) = lbList.List(i, 5)
        End If
    Next i
    
    tbListCount.Value = lbAll.ListCount
End Sub

Private Sub cbSort_Click()
    Dim strTemp, strTotal As String
    Dim iCount, iOffset As Integer
    Dim iIndex As Integer
    Dim strAtt(0 To 5) As String
    
    iCount = lbAll.ListCount - 1
    If iCount < 1 Then Exit Sub
    
    On Error Resume Next
    
    For a = iCount To 0 Step -1
        For b = 0 To a - 1
            If lbAll.List(b, 0) > lbAll.List(b + 1, 0) Then
                If Not Err = 0 Then
                    MsgBox "Error sorting list"
                    lbAll.Selected(b) = True
                    lbAll.ListIndex = b
                    Exit Sub
                End If
                
                strAtt(0) = lbAll.List(b + 1, 0)
                strAtt(1) = lbAll.List(b + 1, 1)
                strAtt(2) = lbAll.List(b + 1, 2)
                strAtt(3) = lbAll.List(b + 1, 3)
                strAtt(4) = lbAll.List(b + 1, 4)
                strAtt(5) = lbAll.List(b + 1, 5)
                
                lbAll.List(b + 1, 0) = lbAll.List(b, 0)
                lbAll.List(b + 1, 1) = lbAll.List(b, 1)
                lbAll.List(b + 1, 2) = lbAll.List(b, 2)
                lbAll.List(b + 1, 3) = lbAll.List(b, 3)
                lbAll.List(b + 1, 4) = lbAll.List(b, 4)
                lbAll.List(b + 1, 5) = lbAll.List(b, 5)
                
                lbAll.List(b, 0) = strAtt(0)
                lbAll.List(b, 1) = strAtt(1)
                lbAll.List(b, 2) = strAtt(2)
                lbAll.List(b, 3) = strAtt(3)
                lbAll.List(b, 4) = strAtt(4)
                lbAll.List(b, 5) = strAtt(5)
            End If
        Next b
    Next a
End Sub

Private Sub Label24NoCOMM_Click()
    Dim iIndex As Integer
    Dim objBlock As AcadBlockReference
    Dim vAttList As Variant
    Dim iMax, iCOMM, iNew, iTemp As Integer
    Dim vLine, vAttach As Variant
    Dim strTemp As String
    
    For i = lbAll.ListCount - 1 To 0 Step -1
        iIndex = CInt(lbAll.List(i, 5))
        
        Set objBlock = objSS.Item(iIndex)
        vAttList = objBlock.GetAttributes
        
        If vAttList(15).TextString = "" Then GoTo Next_I
        
        vLine = Split(vAttList(15).TextString, " ")
        
        If UBound(vLine) > 0 Then GoTo Next_I
        
        strTemp = Replace(UCase(vLine(0)), "T", "")
            
        vAttach = Split(strTemp, "-")
        iNew = CInt(vAttach(0)) * 12
        If UBound(vAttach) > 0 Then iNew = iNew + CInt(vAttach(1))
        
        iMax = FindMaxHeight(iIndex)
        
        'MsgBox "Pwr Max:  " & iMax
        
        If iMax < 288 Then GoTo Next_I
        
        iCOMM = FindTopCOMM(iIndex)
        
        'MsgBox "Top COMM:  " & iCOMM
        
        If iCOMM > 0 Then GoTo Next_I
        
        lbAll.RemoveItem i
Next_I:
    Next i
    
    tbListCount = lbAll.ListCount
End Sub

Private Sub LabelCOMM1_Click()
    Dim iIndex As Integer
    Dim objBlock As AcadBlockReference
    Dim vAttList As Variant
    Dim iMax, iCOMM, iNew, iTemp As Integer
    Dim vLine, vAttach As Variant
    Dim strTemp As String
    
    For i = lbAll.ListCount - 1 To 0 Step -1
        iIndex = CInt(lbAll.List(i, 5))
        
        Set objBlock = objSS.Item(iIndex)
        vAttList = objBlock.GetAttributes
        
        If vAttList(15).TextString = "" Then GoTo Next_I
        
        iMax = FindMaxHeight(iIndex)
        
        iCOMM = FindTopCOMM(iIndex) + 12
        If iCOMM = 1012 Then GoTo Next_I
        
        vLine = Split(vAttList(15).TextString, " ")
        For j = 0 To UBound(vLine)
            strTemp = Replace(UCase(vLine(j)), "T", "")
            vAttach = Split(strTemp, "-")
            
            iNew = CInt(vAttach(0)) * 12
            If UBound(vAttach) > 0 Then iNew = iNew + CInt(vAttach(1))
            
            If iNew > iMax Then GoTo Next_I
            If Not iNew = iCOMM Then GoTo Next_I
        Next j
        
        lbAll.RemoveItem i
Next_I:
    Next i
    
    tbListCount = lbAll.ListCount
End Sub

Private Sub LabelCOMM2_Click()
    Dim iIndex As Integer
    Dim objBlock As AcadBlockReference
    Dim vAttList As Variant
    Dim iMax, iCOMM, iNew, iTemp As Integer
    Dim vLine, vAttach As Variant
    Dim strTemp As String
    
    For i = lbAll.ListCount - 1 To 0 Step -1
        iIndex = CInt(lbAll.List(i, 5))
        
        Set objBlock = objSS.Item(iIndex)
        vAttList = objBlock.GetAttributes
        
        If vAttList(15).TextString = "" Then GoTo Next_I
        
        iMax = FindMaxHeight(iIndex)
        
        iCOMM = FindTopCOMM(iIndex) + 24
        If iCOMM = 1024 Then GoTo Next_I
        
        vLine = Split(vAttList(15).TextString, " ")
        For j = 0 To UBound(vLine)
            strTemp = Replace(UCase(vLine(j)), "T", "")
            vAttach = Split(strTemp, "-")
            
            iNew = CInt(vAttach(0)) * 12
            If UBound(vAttach) > 0 Then iNew = iNew + CInt(vAttach(1))
            
            If iNew > iMax Then GoTo Next_I
            If Not iNew = iCOMM Then GoTo Next_I
        Next j
        
        lbAll.RemoveItem i
Next_I:
    Next i
    
    tbListCount = lbAll.ListCount
End Sub

Private Sub LabelMRQC_Click()
    For i = lbAll.ListCount - 1 To 0 Step -1
        If InStr(lbAll.List(i, 4), "MR-QC") > 0 Then lbAll.RemoveItem i
    Next i
    
    tbListCount = lbAll.ListCount
End Sub

Private Sub LabelNoNew_Click()
    For i = lbAll.ListCount - 1 To 0 Step -1
        If lbAll.List(i, 2) = "none" Then lbAll.RemoveItem i
    Next i
    
    tbListCount = lbAll.ListCount
End Sub

Private Sub LabelTAG_Click()
    For i = lbAll.ListCount - 1 To 0 Step -1
        If InStr(UCase(lbAll.List(i, 2)), "T") > 0 Then lbAll.RemoveItem i
    Next i
    
    tbListCount = lbAll.ListCount
End Sub

Private Sub lbAll_DblClick(ByVal Cancel As MSForms.ReturnBoolean)
    'Dim str As String
    Dim objTemp As AcadBlockReference
    Dim vCoords, vAttList As Variant
    Dim viewCoordsB(0 To 2) As Double
    Dim viewCoordsE(0 To 2) As Double
    Dim iIndex, iList As Integer
    
    Me.Hide
    
    iIndex = CInt(lbAll.List(lbAll.ListIndex, 5))
    Set objTemp = objSS.Item(iIndex)
    
    vCoords = objTemp.InsertionPoint
    
    'MsgBox iIndex
    
    'vCoords = Split(lbAll.List(lbAll.ListIndex, 5), ",")
    
    viewCoordsB(0) = vCoords(0) - 300
    viewCoordsB(1) = vCoords(1) - 300
    viewCoordsB(2) = 0#
    viewCoordsE(0) = vCoords(0) + 300
    viewCoordsE(1) = vCoords(1) + 300
    viewCoordsE(2) = 0#
    
    ThisDrawing.Application.ZoomWindow viewCoordsB, viewCoordsE
    
    Load MRWorksheet
        Set MRWorksheet.objPole = objSS.Item(iIndex)
        Call MRWorksheet.GetPoleData
        Call MRWorksheet.SortList
        
        MRWorksheet.cbGetAttach.Enabled = False
        MRWorksheet.cbSaveData.SetFocus
        MRWorksheet.show
    
        vAttList = objTemp.GetAttributes
        
        If MRWorksheet.iChanged = 1 Then
            If InStr(vAttList(24).TextString, "MR-QC") = 0 Then
                vAttList(24).TextString = "MR-QC;" & vAttList(24).TextString
            End If
            objTemp.Update
            
            lbAll.List(lbAll.ListIndex, 4) = vAttList(24).TextString
            iList = CInt(lbAll.List(lbAll.ListIndex, 5))
            lbList.List(iList, 4) = vAttList(24).TextString
        End If
    Unload MRWorksheet
    
    If Not lbAll.ListCount = lbAll.ListIndex + 1 Then lbAll.ListIndex = lbAll.ListIndex + 1
    lbAll.Selected(lbAll.ListIndex) = True
    
    Me.show
End Sub

Private Sub lbAll_KeyDown(ByVal KeyCode As MSForms.ReturnInteger, ByVal Shift As Integer)
    Select Case KeyCode
        Case vbKeyReturn
            Dim objTemp As AcadBlockReference
            Dim vCoords, vAttList As Variant
            Dim viewCoordsB(0 To 2) As Double
            Dim viewCoordsE(0 To 2) As Double
            Dim iIndex As Integer
    
            Me.Hide
    
            iIndex = CInt(lbAll.List(lbAll.ListIndex, 5))
            Set objTemp = objSS.Item(iIndex)
    
            vCoords = objTemp.InsertionPoint
    
            viewCoordsB(0) = vCoords(0) - 300
            viewCoordsB(1) = vCoords(1) - 300
            viewCoordsB(2) = 0#
            viewCoordsE(0) = vCoords(0) + 300
            viewCoordsE(1) = vCoords(1) + 300
            viewCoordsE(2) = 0#
    
            ThisDrawing.Application.ZoomWindow viewCoordsB, viewCoordsE
    
            Load MRWorksheet
                Set MRWorksheet.objPole = objSS.Item(iIndex)
                Call MRWorksheet.GetPoleData
                Call MRWorksheet.SortList
                
                MRWorksheet.cbGetAttach.Enabled = False
                MRWorksheet.cbSaveData.SetFocus
                MRWorksheet.show
    
                vAttList = objTemp.GetAttributes
        
                If MRWorksheet.iChanged = 1 Then
                    If InStr(vAttList(24).TextString, "MR-QC") = 0 Then
                        vAttList(24).TextString = "MR-QC;" & vAttList(24).TextString
                    End If
                    lbAll.List(lbAll.ListIndex, 4) = vAttList(24).TextString
                End If
            Unload MRWorksheet
            
            If Not lbAll.ListCount = lbAll.ListIndex + 1 Then lbAll.ListIndex = lbAll.ListIndex + 1
            lbAll.Selected(lbAll.ListIndex) = True
    
            Me.show
    End Select
End Sub

Private Sub UserForm_Initialize()
    lbAll.ColumnCount = 6
    lbAll.ColumnWidths = "126;48;72;72;96;12"
    
    lbList.ColumnCount = 6
    lbList.ColumnWidths = "30;30;30;30;30;30"
    
    cbSSType.AddItem "All"
    cbSSType.AddItem "Window"
    cbSSType.Value = "Window"
    
    cbFROption.AddItem "Filter"
    cbFROption.AddItem "Remove"
    cbFROption.Value = "Filter"
    
    cbFRColumn.AddItem "0: Pole Number"
    cbFRColumn.AddItem "1: Owner"
    cbFRColumn.AddItem "2: New At"
    cbFRColumn.AddItem "3: MR"
    cbFRColumn.AddItem "4: Status"
    'cbFRColumn.Value = "1: Owner"
    
    Call GetAllPoles
    
    tbListCount.Value = lbAll.ListCount
    
    'Call FindOwnerStatus
End Sub

Private Sub GetAllPoles()
    Dim filterType, filterValue As Variant
    Dim grpCode(0) As Integer
    Dim grpValue(0) As Variant
    'Dim objSS As AcadSelectionSet
    Dim objBlock As AcadBlockReference
    Dim vAttList As Variant
    Dim vLine, vTemp As Variant
    Dim vPnt1, vPnt2 As Variant
    Dim iCount, iIndex, iTest As Integer
    
    On Error Resume Next
    
    lbAll.Clear
    cbOwner.Clear
    cbStatus.Clear
    
    iCount = 0
    iIndex = 0
    iTest = 0
    
    grpCode(0) = 2
    grpValue(0) = "sPole"
    filterType = grpCode
    filterValue = grpValue
    
    Err = 0
    Set objSS = ThisDrawing.SelectionSets.Add("objSS")
    If Not Err = 0 Then
        Set objSS = ThisDrawing.SelectionSets.Item("objSS")
        objSS.Clear
    End If
    
    'Select Case cbSSType.Value
        'Case "All"
            'objSS.Select acSelectionSetAll, , , filterType, filterValue
        'Case Else
            vPnt1 = ThisDrawing.Utility.GetPoint(, "Get BL Corner: ")
            vPnt2 = ThisDrawing.Utility.GetCorner(vPnt1, vbCr & "Get UR Corner: ")
            
            objSS.Select acSelectionSetWindow, vPnt1, vPnt2, filterType, filterValue
    'End Select
    
    iCount = objSS.count
    
    For i = 0 To objSS.count - 1
        Set objBlock = objSS.Item(i)
        vAttList = objBlock.GetAttributes
        
        If vAttList(0).TextString = "" Then GoTo Next_objBlock
        'If cbInclude.Value = False Then
            'If vAttList(0).TextString = "POLE" Then GoTo Next_objBlock
        'End If
        
        lbAll.AddItem vAttList(0).TextString
        lbAll.List(iIndex, 1) = vAttList(2).TextString
        If vAttList(15).TextString = "" Then
            lbAll.List(iIndex, 2) = "none"
        Else
            lbAll.List(iIndex, 2) = vAttList(15).TextString
        End If
        lbAll.List(iIndex, 3) = "none"
        
        For j = 16 To 23
            If Not vAttList(j).TextString = "" Then
                vLine = Split(vAttList(j).TextString, "=")
                    
                If InStr(vLine(1), ")") > 0 Then
                    If lbAll.List(iIndex, 3) = "none" Then
                        lbAll.List(iIndex, 3) = vLine(0)
                    Else
                        lbAll.List(iIndex, 3) = lbAll.List(iIndex, 3) & ", " & vLine(0)
                    End If
                End If
                
                If InStr(LCase(vLine(1)), "v") > 0 Then
                    If lbAll.List(iIndex, 3) = "none" Then
                        lbAll.List(iIndex, 3) = "LASHED"
                    Else
                        lbAll.List(iIndex, 3) = "LASHED, " & lbAll.List(iIndex, 3)
                    End If
                End If
            End If
        Next j
        
        For j = 9 To 23
            If Not vAttList(j).TextString = "" Then iTest = 1
        Next j
        
        If iTest = 0 Then lbAll.List(iIndex, 3) = "no attach"
        
        'If InStr(vAttList(24).TextString, "MR-QC;") > 0 Then
            'lbAll.List(iIndex, 4) = "MR-QC"
        'Else
            'lbAll.List(iIndex, 4) = ""
        'End If
        lbAll.List(iIndex, 4) = vAttList(24).TextString
        
        lbAll.List(iIndex, 5) = i
        
        iIndex = iIndex + 1
        
Next_objBlock:
    Next i
    
    If lbAll.ListCount > 0 Then
        lbList.Clear
        
        For i = 0 To lbAll.ListCount - 1
            lbList.AddItem lbAll.List(i, 0)
            lbList.List(i, 1) = lbAll.List(i, 1)
            lbList.List(i, 2) = lbAll.List(i, 2)
            lbList.List(i, 3) = lbAll.List(i, 3)
            lbList.List(i, 4) = lbAll.List(i, 4)
            lbList.List(i, 5) = lbAll.List(i, 5)
        Next i
        
        If cbInclude.Value = False Then
            For i = lbAll.ListCount - 1 To 0 Step -1
                If lbAll.List(i, 0) = "POLE" Then lbAll.RemoveItem i
            Next i
        End If
    End If
    
    'objSS.Clear
    'objSS.Delete
    
    tbListCount.Value = lbAll.ListCount
    
    'If Not cbSSType.Value = "All" Then Me.show
End Sub

Private Sub UserForm_Terminate()
    objSS.Clear
    objSS.Delete
End Sub

Private Function FindMaxHeight(iIndex As Integer)
    Dim objBlock As AcadBlockReference
    Dim vAttList As Variant
    Dim iMax, iTemp As Integer
    Dim vLine, vAttach, vTemp As Variant
    
    iMax = 840  ' 70 feet
        
    Set objBlock = objSS.Item(iIndex)
    vAttList = objBlock.GetAttributes
        
        If Not vAttList(9).TextString = "" Then
            vLine = Split(vAttList(9).TextString, " ")
            
            For j = 0 To UBound(vLine)
                If InStr(vLine(j), ")") > 0 Then
                    vTemp = Split(vLine(j), ")")
                    vAttach = Split(vTemp(1), "-")
                Else
                    vAttach = Split(vLine(j), "-")
                End If
                
                iTemp = CInt(vAttach(0)) * 12
                If UBound(vAttach) > 0 Then iTemp = iTemp + CInt(vAttach(1))
                
                iTemp = iTemp - 40
                
                If iTemp < iMax Then iMax = iTemp
            Next j
        End If
        
        If Not vAttList(10).TextString = "" Then
            vLine = Split(vAttList(10).TextString, " ")
            
            For j = 0 To UBound(vLine)
                If InStr(vLine(j), ")") > 0 Then
                    vTemp = Split(vLine(j), ")")
                    vAttach = Split(vTemp(1), "-")
                Else
                    vAttach = Split(vLine(j), "-")
                End If
                
                iTemp = CInt(vAttach(0)) * 12
                If UBound(vAttach) > 0 Then iTemp = iTemp + CInt(vAttach(1))
                
                iTemp = iTemp - 30
                
                If iTemp < iMax Then iMax = iTemp
            Next j
        End If
        
        If Not vAttList(11).TextString = "" Then
            vLine = Split(vAttList(11).TextString, " ")
            
            For j = 0 To UBound(vLine)
                If InStr(vLine(j), ")") > 0 Then
                    vTemp = Split(vLine(j), ")")
                    vAttach = Split(vTemp(1), "-")
                Else
                    vAttach = Split(vLine(j), "-")
                End If
                
                iTemp = CInt(vAttach(0)) * 12
                If UBound(vAttach) > 0 Then iTemp = iTemp + CInt(vAttach(1))
                
                iTemp = iTemp - 40
                
                If iTemp < iMax Then iMax = iTemp
            Next j
        End If
        
        If Not vAttList(12).TextString = "" Then
            vLine = Split(vAttList(12).TextString, " ")
            
            For j = 0 To UBound(vLine)
                If InStr(vLine(j), ")") > 0 Then
                    vTemp = Split(vLine(j), ")")
                    vAttach = Split(vTemp(1), "-")
                Else
                    vAttach = Split(vLine(j), "-")
                End If
                
                iTemp = CInt(vAttach(0)) * 12
                If UBound(vAttach) > 0 Then iTemp = iTemp + CInt(vAttach(1))
                
                iTemp = iTemp - 40
                
                If iTemp < iMax Then iMax = iTemp
            Next j
        End If
        
        If Not vAttList(13).TextString = "" Then
            vLine = Split(vAttList(13).TextString, " ")
            
            For j = 0 To UBound(vLine)
                If InStr(vLine(j), ")") > 0 Then
                    vTemp = Split(vLine(j), ")")
                    vAttach = Split(vTemp(1), "-")
                Else
                    vAttach = Split(vLine(j), "-")
                End If
                
                iTemp = CInt(vAttach(0)) * 12
                If UBound(vAttach) > 0 Then iTemp = iTemp + CInt(vAttach(1))
                
                iTemp = iTemp - 40
                
                If iTemp < iMax Then iMax = iTemp
            Next j
        End If
        
        If Not vAttList(14).TextString = "" Then
            vLine = Split(vAttList(14).TextString, " ")
            
            For j = 0 To UBound(vLine)
                If InStr(vLine(j), ")") > 0 Then
                    vTemp = Split(vLine(j), ")")
                    vAttach = Split(vTemp(1), "-")
                Else
                    vAttach = Split(vLine(j), "-")
                End If
                
                iTemp = CInt(vAttach(0)) * 12
                If UBound(vAttach) > 0 Then iTemp = iTemp + CInt(vAttach(1))
                
                iTemp = iTemp - 12
                
                If iTemp < iMax Then iMax = iTemp
            Next j
        End If
        
    FindMaxHeight = iMax
End Function

Private Function FindTopCOMM(iIndex As Integer)
    Dim objBlock As AcadBlockReference
    Dim vAttList As Variant
    Dim iMax, iTemp As Integer
    Dim vTemp, vLine, vAttach As Variant
    Dim strTemp As String
    
    iMax = 0
        
    Set objBlock = objSS.Item(iIndex)
    vAttList = objBlock.GetAttributes
    
    For i = 16 To 23
        If Not vAttList(i).TextString = "" Then
            strTemp = Replace(UCase(vAttList(i).TextString), "C", "")
            'strTemp = Replace(strTemp, "D", "")
            strTemp = Replace(strTemp, "O", "")
            strTemp = Replace(strTemp, "S", "")
            strTemp = Replace(strTemp, "X", "")
            
            vTemp = Split(strTemp, "=")
            vLine = Split(vTemp(1), " ")
            
            For j = 0 To UBound(vLine)
                If InStr(vLine(j), "D") > 0 Then GoTo Next_J
                If InStr(vLine(j), ")") > 0 Then
                    FindTopCOMM = 1000
                    Exit Function
                    'vTemp = Split(vLine(j), ")")
                    'vAttach = Split(vTemp(1), "-")
                Else
                    vAttach = Split(vLine(j), "-")
                End If
                
                iTemp = CInt(vAttach(0)) * 12
                If UBound(vAttach) > 0 Then iTemp = iTemp + CInt(vAttach(1))
                
                If iTemp > iMax Then iMax = iTemp
Next_J:
            Next j
        End If
    Next i
        
    FindTopCOMM = iMax
End Function

Private Function FindNewAttach(iIndex As Integer)
    Dim objBlock As AcadBlockReference
    Dim vAttList As Variant
    Dim iMax, iTemp As Integer
    Dim vLine, vAttach As Variant
    Dim strTemp As String
    
    iMax = 0
        
    Set objBlock = objSS.Item(iIndex)
    vAttList = objBlock.GetAttributes
    
    If vAttList(15).TextString = "" Then
        vLine = 0
    Else
        vLine = Split(vAttList(15).TextString, " ")
        
        For i = 0 To UBound(vLine)
            strTemp = Replace(UCase(vLine(i)), "T", "")
            
            vAttach = Split(strTemp, "-")
            iTemp = CInt(vAttach(0)) * 12
            If UBound(vAttach) > 0 Then iTemp = iTemp + CInt(vAttach(1))
                
            vLine(i) = iTemp
        Next i
    End If
    
    FindNewAttach = vLine
End Function

Private Sub FindOwnerStatus()
    If lbAll.ListCount < 2 Then Exit Sub
    
    'MsgBox "Here"
    Dim vLine As Variant
    
    cbOwner.Clear
    cbStatus.Clear
    
    cbOwner.AddItem lbAll.List(0, 1)
    
    If Not lbAll.List(0, 4) = "" Then
        vLine = Split(lbAll.List(0, 4), ";")
        For j = 0 To UBound(vLine)
            cbStatus.AddItem vLine(j)
        Next j
    End If
    
    For i = 1 To lbAll.ListCount - 1
        For j = 0 To cbOwner.ListCount - 1
            If cbOwner.List(j) = lbAll.List(i, 1) Then GoTo Exit_J
        Next j
        
        cbOwner.AddItem lbAll.List(i, 1)
Exit_J:
        
        If Not lbAll.List(i, 4) = "" Then
            vLine = Split(lbAll.List(i, 4), ";")
            
            For j = 0 To UBound(vLine)
                If Not cbStatus.ListCount < 0 Then
                    For k = 0 To cbStatus.ListCount - 1
                        If cbStatus.List(k) = vLine(j) Then GoTo Exit_K
                    Next k
                End If
                
                cbStatus.AddItem vLine(j)
Exit_K:
            Next j
        End If
    Next i
    
    If cbOwner.ListCount > 0 Then
        cbFRValue.Clear
        For i = 0 To cbOwner.ListCount - 1
            cbFRValue.AddItem cbOwner.List(i)
        Next i
    End If
    
    If cbStatus.ListCount > 0 Then
        For i = cbStatus.ListCount - 1 To 0 Step -1
            If cbStatus.List(i) = "" Then cbStatus.RemoveItem i
            'If cbStatus.List(i) = " " Then cbStatus.RemoveItem i
        Next i
    End If
End Sub

Private Sub FilterRemovePN()
    If lbAll.ListCount < 2 Then Exit Sub
    'If cbFRValue.Value = "" Then Exit Sub
    
    Dim strOwner As String
    
    strOwner = UCase(cbFRValue.Value)
    
    For i = lbAll.ListCount - 1 To 0 Step -1
        If cbFROption.Value = "Filter" Then
            If InStr(lbAll.List(i, 0), strOwner) = 0 Then lbAll.RemoveItem i
        Else
            If InStr(lbAll.List(i, 0), strOwner) > 0 Then lbAll.RemoveItem i
        End If
    Next i
    
    tbListCount.Value = lbAll.ListCount
End Sub

Private Sub FilterRemoveOwner()
    If lbAll.ListCount < 2 Then Exit Sub
    If cbFRValue.Value = "" Then Exit Sub
    
    Dim strOwner As String
    
    strOwner = cbFRValue.Value
    
    For i = lbAll.ListCount - 1 To 0 Step -1
        If cbFROption.Value = "Filter" Then
            If Not lbAll.List(i, 1) = strOwner Then lbAll.RemoveItem i
        Else
            If lbAll.List(i, 1) = strOwner Then lbAll.RemoveItem i
        End If
    Next i
    
    tbListCount.Value = lbAll.ListCount
End Sub

Private Sub FilterRemoveStatus()
    If lbAll.ListCount < 2 Then Exit Sub
    'If cbFRValue.Value = "" Then Exit Sub
    
    Dim vLine As Variant
    Dim strStatus, strLine As String
    Dim iCount As Integer
    
    strStatus = cbFRValue.Value
    
    For i = lbAll.ListCount - 1 To 0 Step -1
        iCount = 0
        
        If Not lbAll.List(i, 4) = "" Then
            vLine = Split(lbAll.List(i, 4), ";")
            For j = 0 To UBound(vLine)
                If vLine(j) = strStatus Then iCount = 1
            Next j
        End If
            
        If cbFROption.Value = "Filter" Then
            If iCount = 0 Then lbAll.RemoveItem i
        Else
            If iCount = 1 Then lbAll.RemoveItem i
        End If
    Next i
    
    tbListCount.Value = lbAll.ListCount
End Sub

Private Sub FilterRemoveNewAt()
    If lbAll.ListCount < 2 Then Exit Sub
    If cbFRValue.Value = "" Then Exit Sub
    
    Dim vLine, vTemp As Variant
    Dim strType, strLine As String
    Dim iSHeight, iCHeight As Integer
    Dim iCount As Integer
    
    Select Case cbFRValue.Value
        Case "none"
            For i = lbAll.ListCount - 1 To 0 Step -1
                If cbFROption.Value = "Filter" Then
                    If Not lbAll.List(i, 2) = "none" Then lbAll.RemoveItem i
                Else
                    If lbAll.List(i, 2) = "none" Then lbAll.RemoveItem i
                End If
            Next i
        Case "**T"
            For i = lbAll.ListCount - 1 To 0 Step -1
                If cbFROption.Value = "Filter" Then
                    If InStr(LCase(lbAll.List(i, 2)), "t") = 0 Then lbAll.RemoveItem i
                Else
                    If InStr(LCase(lbAll.List(i, 2)), "t") > 0 Then lbAll.RemoveItem i
                End If
            Next i
        Case "**F"
            For i = lbAll.ListCount - 1 To 0 Step -1
                If cbFROption.Value = "Filter" Then
                    If InStr(LCase(lbAll.List(i, 2)), "f") = 0 Then lbAll.RemoveItem i
                Else
                    If InStr(LCase(lbAll.List(i, 2)), "f") > 0 Then lbAll.RemoveItem i
                End If
            Next i
        Case "**O"
            For i = lbAll.ListCount - 1 To 0 Step -1
                If cbFROption.Value = "Filter" Then
                    If InStr(LCase(lbAll.List(i, 2)), "o") = 0 Then lbAll.RemoveItem i
                Else
                    If InStr(LCase(lbAll.List(i, 2)), "o") > 0 Then lbAll.RemoveItem i
                End If
            Next i
        Case Else
            If InStr(cbFRValue.Value, "=") = 0 Then Exit Sub
            
            vLine = Split(cbFRValue.Value, "=")
            If vLine(1) = "" Then Exit Sub
            
            strType = vLine(0)
            
            vTemp = Split(vLine(1), "-")
            iSHeight = CInt(vTemp(0)) * 12
            If UBound(vTemp) > 0 Then iSHeight = iSHeight + CInt(vTemp(1))
            
            For i = lbAll.ListCount - 1 To 0 Step -1
                'If InStr(lbAll.List(i, 2), " ") > 0 Then GoTo Next_NewAt
                If lbAll.List(i, 2) = "none" Then
                    lbAll.RemoveItem i
                    GoTo Next_NewAt
                End If
                
                strLine = LCase(lbAll.List(i, 2))
                strLine = Replace(strLine, "o", "")
                strLine = Replace(strLine, "f", "")
                strLine = Replace(strLine, "t", "")
                vLine = Split(strLine, " ")
                
                iCount = 0
                For j = 0 To UBound(vLine)
                    vTemp = Split(vLine(j), "-")
                    iCHeight = CInt(vTemp(0)) * 12
                    If UBound(vTemp) > 0 Then iCHeight = iCHeight + CInt(vTemp(1))
                    
                    Select Case strType
                        Case "<"
                            If iCHeight < iSHeight Then iCount = iCount + 1
                        Case ">"
                            If iCHeight > iSHeight Then iCount = iCount + 1
                        Case Else
                            If iCHeight = iSHeight Then iCount = iCount + 1
                    End Select
                Next j
                    
                If cbFROption.Value = "Filter" Then
                    If iCount = 0 Then lbAll.RemoveItem i
                Else
                    If iCount = UBound(vTemp) + 1 Then lbAll.RemoveItem i
                End If
Next_NewAt:
            Next i
    End Select
        
    tbListCount.Value = lbAll.ListCount
    
    
    
    
    
    
    
    
    
    
    
    

            'cbFRValue.AddItem "none"
            'cbFRValue.AddItem "**T"
            'cbFRValue.AddItem "**F"
            'cbFRValue.AddItem "**E"
            'cbFRValue.AddItem "<="
            'cbFRValue.AddItem ">="
            'cbFRValue.AddItem "="
End Sub

Private Sub FilterRemoveMR()
    If lbAll.ListCount < 2 Then Exit Sub
    If cbFRValue.Value = "" Then Exit Sub
    
    'Dim vLine As Variant
    
    If cbFRValue.Value = "none" Then
        For i = lbAll.ListCount - 1 To 0 Step -1
            If cbFROption.Value = "Filter" Then
                If Not lbAll.List(i, 3) = "none" Then lbAll.RemoveItem i
            Else
                If lbAll.List(i, 3) = "none" Then lbAll.RemoveItem i
            End If
        Next i
        
        tbListCount.Value = lbAll.ListCount
        Exit Sub
    End If
    
    Dim vLine As Variant
    Dim strMR As String
    Dim iCount As Integer
    
    strMR = cbFRValue.Value
    
    For i = lbAll.ListCount - 1 To 0 Step -1
        If InStr(lbAll.List(i, 3), ",") > 0 Then
            vLine = Split(lbAll.List(i, 3), ", ")
            iCount = 0
            For j = 0 To UBound(vLine)
                If vLine(j) = strMR Then
                    iCount = 1
                End If
            Next j
            
            If cbFROption.Value = "Filter" And iCount = 0 Then lbAll.RemoveItem i
        Else
            If cbFROption.Value = "Filter" Then
                If Not lbAll.List(i, 3) = strMR Then lbAll.RemoveItem i
            Else
                If lbAll.List(i, 3) = strMR Then lbAll.RemoveItem i
            End If
        End If
'Next_MR:
    Next i
        
    tbListCount.Value = lbAll.ListCount
End Sub

Attribute VB_Name = "MRSheets"
Attribute VB_Base = "0{B1EEF465-13E0-4DA5-AE16-DF37FB385D36}{C07A78EE-E8F6-4DDE-81FC-04D3BA76CCB5}"
Attribute VB_GlobalNameSpace = False
Attribute VB_Creatable = False
Attribute VB_PredeclaredId = True
Attribute VB_Exposed = False
Attribute VB_TemplateDerived = False
Attribute VB_Customizable = False
Private Sub cbAddReport_Click()
    If cbReports.Value = "" Then Exit Sub
    
    lbReports.AddItem cbReports.Value
End Sub

Private Sub cbATTForm_Click()
    Dim strExistingName, strFileName As String
    Dim strTemp, strFormName As String
    Dim strAttach As String
    Dim vTemp, vTemp2, vLine As Variant
    Dim fName As String
    Dim objExcel As Workbook
    Dim objDoc As Object
    Dim iRow As Integer
    
    iRow = 4
    
    vTemp = Split(ThisDrawing.Name, " ")
    strFileName = ThisDrawing.Path & "\" & vTemp(0) & " MR Report - ATT-Owner Lower.txt"
    strExistingName = ThisDrawing.Path & "\" & vTemp(0) & " ATT - Pole-Data-003_Pole_Data_Request-Part (A).xlsx"
    
    'fName = Dir(strFileName)
    'If fName = "" Then
        'Exit Sub
    'End If
    
    Open strFileName For Input As #1
    
    'Set objExcel = CreateObject("Excel.Application")
    'objExcel.Visible = False
    
    fName = Dir(strExistingName)
    If fName = "" Then
        strTemp = ThisDrawing.Path
        vTemp2 = Split(LCase(strTemp), "dropbox")
        strFormName = vTemp2(0) & "Dropbox\UNITED COMMUNICATIONS JOB INFORMATION\5 - FORMS\ATT\ATT - Pole-Data-003_Pole_Data_Request-Part (A).xlsx"
        
        Set objExcel = Workbooks.Open(strFormName)
        objExcel.SaveAs (strExistingName)
        MsgBox "Created New File."
    Else
        Set objExcel = Workbooks.Open(strExistingName)
        MsgBox "Opened Existing File"
    End If
    
    objExcel.Sheets("Sheet1").Cells(1, 17).Value = Date
    objExcel.Sheets("Sheet1").Cells(2, 9).Value = vTemp(0)
    
    While Not EOF(1)
        Line Input #1, strTemp
        If strTemp = "" Then GoTo Next_line
        If Left(strTemp, 1) = "-" Then GoTo Next_line
        
        vTemp2 = Split(strTemp, vbTab)
        
        If Not vTemp2(0) = "ATT" Then
            While Not strTemp = ""
                Line Input #1, strTemp
            Wend
            GoTo Next_line
        End If
        
        objExcel.Sheets("Sheet1").Cells(iRow, 2).Value = vTemp2(UBound(vTemp2))
        
        Line Input #1, strTemp
        While Not Left(strTemp, 1) = "-"
            vTemp2 = Split(strTemp, vbTab)
            Select Case vTemp2(0)
                Case "UNITED#"
                    objExcel.Sheets("Sheet1").Cells(iRow, 3).Value = vTemp2(UBound(vTemp2))
                Case "SIZE-CLASS"
                    vLine = Split(vTemp2(1), "-")
                    If UBound(vLine) > 0 Then objExcel.Sheets("Sheet1").Cells(iRow, 5).Value = vLine(0)
                    If UBound(vLine) > 0 Then objExcel.Sheets("Sheet1").Cells(iRow, 6).Value = vLine(1)
                Case "LOCATION:"
                    vLine = Split(vTemp2(1), " ")
                    If UBound(vLine) > 0 Then objExcel.Sheets("Sheet1").Cells(iRow, 4).Value = vLine(1)
                Case Else
                    If UBound(vTemp2) = 0 Then objExcel.Sheets("Sheet1").Cells(iRow, 7).Value = strTemp
            End Select
            
            Line Input #1, strTemp
        Wend
        
        strAttach = ""
        
        While Not strTemp = ""
            vLine = Split(strTemp, vbTab)
            
            If vLine(UBound(vLine)) = "NEW" Or vLine(UBound(vLine)) = "FUTURE" Then
                If strAttach = "" Then
                    strAttach = vLine(UBound(vLine) - 1)
                Else
                    strAttach = strAttach & vbCrLf & vLine(UBound(vLine) - 1)
                End If
                
                'If objExcel.Sheets("Sheet1").Cells(iRow, 10).Value = "" Then
                    'objExcel.Sheets("Sheet1").Cells(iRow, 10).Value = vLine(UBound(vLine) - 1)
                'Else
                    'objExcel.Sheets("Sheet1").Cells(iRow, 10).Value = objExcel.Sheets("Sheet1").Cells(iRow, 10).Value & vbCrLf & vLine(UBound(vLine) - 1)
                'End If
                
                If vLine(UBound(vLine)) = "FUTURE" Then
                    strAttach = strAttach & " FUTURE"
                End If
            
                objExcel.Sheets("Sheet1").Cells(iRow, 9).Value = "C"
            End If
            
            Line Input #1, strTemp
        Wend
        objExcel.Sheets("Sheet1").Cells(iRow, 10).Value = strAttach
        
        iRow = iRow + 1
        
Next_line:
    Wend
    
    'MsgBox objExcel.Sheets("Sheet1").Cells(4, 3).Value
    
    objExcel.Save
    objExcel.Close
    Close #1
    
    MsgBox "Form Completed."
End Sub

Private Sub cbCompany_Change()
    If cbCompany.Value = "" Then Exit Sub
    'If cbCompany.Value = "MTEMC" Then
        'lbCompany.Clear
        'Exit Sub
    'End If
    
    Dim vLine, vItem As Variant
    Dim vAttach, vValue, vHeight As Variant
    Dim strCompany As String
    Dim iIndex, iTest As Integer
    Dim iExist, iProp As Integer
    
    lbCompany.Clear
    strCompany = cbCompany.Value
    
    For i = 0 To lbAll.ListCount - 1
        iTest = 0
        
        If strCompany = "LASH" Then
            If InStr(UCase(lbAll.List(i, 5)), "V ") > 0 Or InStr(UCase(lbAll.List(i, 5)), "V;;") > 0 Then
                lbCompany.AddItem lbAll.List(i, 0)
                iIndex = lbCompany.ListCount - 1
                lbCompany.List(iIndex, 1) = lbAll.List(i, 2)
                lbCompany.List(iIndex, 2) = ""
                lbCompany.List(iIndex, 3) = ""
                lbCompany.List(iIndex, 4) = lbAll.List(i, 6)
                lbCompany.List(iIndex, 5) = lbAll.List(i, 8)
            End If
            
            If Right(UCase(lbAll.List(i, 5)), 1) = "V" Then
                lbCompany.AddItem lbAll.List(i, 0)
                iIndex = lbCompany.ListCount - 1
                lbCompany.List(iIndex, 1) = lbAll.List(i, 2)
                lbCompany.List(iIndex, 2) = ""
                lbCompany.List(iIndex, 3) = ""
                lbCompany.List(iIndex, 4) = lbAll.List(i, 6)
                lbCompany.List(iIndex, 5) = lbAll.List(i, 8)
            End If
            
            GoTo Next_I
        End If
        
        If lbAll.List(i, 2) = strCompany Then
            lbCompany.AddItem lbAll.List(i, 0)
            iIndex = lbCompany.ListCount - 1
            lbCompany.List(iIndex, 1) = lbAll.List(i, 2)
            lbCompany.List(iIndex, 2) = ""
            lbCompany.List(iIndex, 3) = ""
            lbCompany.List(iIndex, 4) = lbAll.List(i, 6)
            lbCompany.List(iIndex, 5) = lbAll.List(i, 8)
            iTest = 1
        End If
        
        Select Case strCompany
            Case "MTE", "MTEMC", "DRE", "DREMC" 'May need more PWR CO added
            Case Else
                If InStr(lbAll.List(i, 5), strCompany) = 0 Then GoTo Next_I
        End Select
        
        If iTest = 0 Then
            lbCompany.AddItem lbAll.List(i, 0)
            iIndex = lbCompany.ListCount - 1
            lbCompany.List(iIndex, 1) = lbAll.List(i, 2)
            lbCompany.List(iIndex, 2) = ""
            lbCompany.List(iIndex, 3) = ""
            lbCompany.List(iIndex, 4) = lbAll.List(i, 6)
            lbCompany.List(iIndex, 5) = lbAll.List(i, 8)
        End If
        
        vLine = Split(UCase(lbAll.List(i, 5)), ";;")
        For j = 0 To UBound(vLine)
            vItem = Split(vLine(j), "=")
            
            Select Case strCompany
                Case vItem(0)
                    vAttach = Split(vItem(1), " ")
                    For k = 0 To UBound(vAttach)
                        vAttach(k) = Replace(vAttach(k), "C", "")
                        vAttach(k) = Replace(vAttach(k), "D", "")
                        vAttach(k) = Replace(vAttach(k), "F", "")
                        vAttach(k) = Replace(vAttach(k), "O", "")
                        vAttach(k) = Replace(vAttach(k), "T", "")
                        vAttach(k) = Replace(vAttach(k), "V", "")
                        If InStr(vAttach(k), "X") > 0 Then
                            vAttach(k) = Replace(vAttach(k), "X", "")
                            If lbCompany.List(iIndex, 3) = "" Then
                                lbCompany.List(iIndex, 3) = "1"
                            Else
                                lbCompany.List(iIndex, 3) = CInt(lbCompany.List(iIndex, 3)) + 1
                            End If
                            GoTo Next_K
                        End If
                    
                        If InStr(vAttach(k), ")") > 0 Then
                            vAttach(k) = Replace(vAttach(k), "(", "")
                            vValue = Split(vAttach(k), ")")
                        
                            vHeight = Split(vValue(0), "-")
                            iExist = CInt(vHeight(0)) * 12
                            If UBound(vHeight) > 0 Then iExist = iExist + CInt(vHeight(1))
                        
                            vHeight = Split(vValue(1), "-")
                            iProp = CInt(vHeight(0)) * 12
                            If UBound(vHeight) > 0 Then iProp = iProp + CInt(vHeight(1))
                        
                            Select Case iProp - iExist
                                Case Is < 0
                                    If lbCompany.List(iIndex, 2) = "" Then
                                        lbCompany.List(iIndex, 2) = "1"
                                    Else
                                        lbCompany.List(iIndex, 2) = CInt(lbCompany.List(iIndex, 2)) + 1
                                    End If
                                Case Else
                                    If lbCompany.List(iIndex, 3) = "" Then
                                        lbCompany.List(iIndex, 3) = "1"
                                    Else
                                        lbCompany.List(iIndex, 3) = CInt(lbCompany.List(iIndex, 3)) + 1
                                    End If
                            End Select
                        End If
Next_K:
                Next k
            Case "MTE", "MTEMC", "DRE", "DREMC"     'May need more PWR CO added
                Select Case vItem(0)
                    Case "NEUTRAL", "TRANSFORMER", "LOW POWER", "ANTENNA", "ST LT CIRCUIT", "ST LT", "PWR"
                        If InStr(vItem(1), ")") > 0 Then
                            If lbCompany.List(iIndex, 3) = "" Then
                                lbCompany.List(iIndex, 3) = "1"
                            Else
                                lbCompany.List(iIndex, 3) = CInt(lbCompany.List(iIndex, 3)) + 1
                            End If
                        End If
                End Select
            End Select
        Next j
        
Next_I:
    Next i
    
    Dim iPoles, iVisits, iOwner, iLower, iRaise As Integer
    Dim iLTotal, iRTotal, iTemp As Integer
    
    iPoles = lbCompany.ListCount
    iVisits = 0
    iOwner = 0
    iLower = 0
    iRaise = 0
    iLTotal = 0
    iRTotal = 0
    
    For i = 0 To iPoles - 1
        iTemp = 0
        
        If lbCompany.List(i, 1) = cbCompany.Value Then
            iTemp = iTemp + 1
            iOwner = iOwner + 1
        End If
        
        If Not lbCompany.List(i, 2) = "" Then
            iTemp = iTemp + 1
            iLower = iLower + 1
            iLTotal = iLTotal + CInt(lbCompany.List(i, 2))
        End If
        
        If Not lbCompany.List(i, 3) = "" Then
            iTemp = iTemp + 1
            iRaise = iRaise + 1
            iRTotal = iRTotal + CInt(lbCompany.List(i, 3))
        End If
        
        If iTemp > 0 Then iVisits = iVisits + 1
    Next i
    
    tbAttPole.Value = iPoles
    tbAttVisit.Value = iVisits
    tbAtt.Value = iOwner
    tbATTL.Value = iLower
    tbATTR.Value = iRaise
    tbATTLTotal.Value = iLTotal
    tbATTRTotal.Value = iRTotal
    
    Dim strLine As String
    
    strLine = ""
    
    lbReports.Clear
    
    If InStr(cbCompany.Value, "TDS") > 0 Then
        strLine = "TDS Reports Needed:" & vbCr & vbCr & "Owner" & vbCr & "Non Owner/MR"
        lbReports.AddItem "Owner"
        lbReports.AddItem "Non Owner/MR"
    End If
    
    If InStr(cbCompany.Value, "ATT") > 0 Then
        strLine = "ATT Reports Needed:" & vbCr & vbCr & "Owner/Lower" & vbCr & "Non Owner/R/T/A"
        lbReports.AddItem "Owner/Lower"
        lbReports.AddItem "Non Owner/R/T/A"
    End If
    
    If lbReports.ListCount < 1 Then lbReports.AddItem "All MR"
    
    'If cbCompany.Value = "NEW 6M" And lbCompany.ListCount > 0 Then
    If lbCompany.ListCount > 0 Then
        Select Case cbCompany.Value
            Case "NEW 6M", "LASH"
                strLine = lbCompany.List(0, 1) & "=1"
        
                If lbCompany.ListCount > 1 Then
                    For i = 1 To lbCompany.ListCount - 1
                        vLine = Split(strLine, ";;")
                        For j = 0 To UBound(vLine)
                            vItem = Split(vLine(j), "=")
                            If lbCompany.List(i, 1) = vItem(0) Then
                                vItem(1) = CInt(vItem(1)) + 1
                                vLine(j) = vItem(0) & "=" & vItem(1)
                                
                                strLine = vLine(0)
                                If UBound(vLine) > 0 Then
                                    For k = 1 To UBound(vLine)
                                        strLine = strLine & ";;" & vLine(k)
                                    Next k
                                End If
                                
                                GoTo Next_lbCompany
                            End If
                        Next j
                
                        strLine = strLine & ";;" & lbCompany.List(i, 1) & "=1"
Next_lbCompany:
                    Next i
                End If
        
                strLine = Replace(strLine, ";;", vbCr)
            Case Else
        End Select
    End If
    
    LHelp.Caption = strLine
    tbResult.Value = ""
End Sub

Private Sub cbCreateReports_Click()
    If lbReports.ListCount < 1 Then Exit Sub
    
    For i = 0 To lbReports.ListCount - 1
        Call GetReports(lbReports.List(i))
    Next i
End Sub

Private Sub cbFillForm_Click()
    Dim strFileName, fName As String
    Dim vTemp As Variant
    
    vTemp = Split(ThisDrawing.Name, " ")
    strFileName = ThisDrawing.Path & "\" & vTemp(0)
    
    Select Case cbFormList.Value
        Case ""
            Exit Sub
        Case "ATT Form"
            strFileName = strFileName & " MR Report - ATT-Owner Lower.txt"
            
            fName = Dir(strFileName)
            If fName = "" Then
                MsgBox "MR Report - ATT-Owner Lower  form not found"
                Exit Sub
            End If
            
            Call AttForm
        Case "TDS Owner Form"
            strFileName = strFileName & " MR Report - TDS-Owner.txt"
            
            fName = Dir(strFileName)
            If fName = "" Then
                MsgBox "MR Report - TDS-Owner  form not found"
                Exit Sub
            End If
            
            Call TDSForm(CStr(strFileName))
        Case "TDS MR Form"
            strFileName = strFileName & " MR Report - TDS-NonOwner MR.txt"
            
            fName = Dir(strFileName)
            If fName = "" Then
                MsgBox "MR Report - TDS-NonOwner MR  form not found"
                Exit Sub
            End If
            
            Call TDSForm(CStr(strFileName))
    End Select
End Sub

Private Sub cbQuit_Click()
    Me.Hide
End Sub

'Private Sub cbTDS_Click()
'    Dim objDocument
'    Dim objField As Word.FormField
'    Dim strFile, strFileName As String
'    Dim strLine As String
'    Dim vTemp, vLine As Variant
'    Dim fName As String
'    Dim iCount As Integer
'
'    iCount = 0
'
'    strFile = "C:\Integrity\Temp\Delete This\CustomerTest\TDS Pole Form with info.docx"
'    Set objDocument = CreateObject("word.application")
'    objDocument.Documents.Open strFile
'    objDocument.Visible = False
'
'    'strFileName = ThisDrawing.Path & "\" & vTemp(0) & " MR Report - ATT-Owner Lower.txt"
'
'    'fName = Dir(strFileName)
'    'If fName = "" Then
'        'Exit Sub
'    'End If
'
'    'Open strFileName For Input As #1
'
'
'
'
'
'
'    'objDocument.ActiveDocument.FormFields.Item(29).result = "TEST"
'    objDocument.ActiveDocument.FormFields(28).result = Date
'    objDocument.ActiveDocument.FormFields(29).result = "Changed"
'
'    objDocument.Documents.Close
'    'Close #1
'
'    MsgBox "Form Completed."
'End Sub

Private Sub cbWindow_Click()
    Dim filterType, filterValue As Variant
    Dim grpCode(0) As Integer
    Dim grpValue(0) As Variant
    Dim objSS As AcadSelectionSet
    Dim objBlock As AcadBlockReference
    Dim vAttList As Variant
    Dim vItem, vLine, vTemp As Variant
    Dim vPnt1, vPnt2 As Variant
    Dim strPole, strOwner, strCompany, strNew As String
    Dim strExisting, strProposed, strExtra, strNote As String
    Dim strAttachments As String
    Dim strDWG As String
    Dim iIndex As Integer
    Dim iExist, iProp, iPole As Integer
    
    On Error Resume Next
    
    Me.Hide
    
    lbAll.Clear
    lbCompany.Clear
    cbCompany.Clear
    tbOwners.Value = ""
    strDWG = "Window"
    iPole = 0
        
    Err = 0
    vPnt1 = ThisDrawing.Utility.GetPoint(, "Get BL Corner: ")
    vPnt2 = ThisDrawing.Utility.GetCorner(vPnt1, vbCr & "Get UR Corner: ")
    If Not Err = 0 Then GoTo Exit_Sub
    
    grpCode(0) = 2
    grpValue(0) = "sPole"
    filterType = grpCode
    filterValue = grpValue
    
    Err = 0
    Set objSS = ThisDrawing.SelectionSets.Add("objSS")
    If Not Err = 0 Then
        Set objSS = ThisDrawing.SelectionSets.Item("objSS")
    End If
    objSS.Select acSelectionSetWindow, vPnt1, vPnt2, filterType, filterValue
    
    For Each objBlock In objSS
        vAttList = objBlock.GetAttributes
        If vAttList(0).TextString = "POLE" Then GoTo Next_objBlock
        If vAttList(0).TextString = "" Then GoTo Next_objBlock
        
        iPole = iPole + 1
        strAttachments = ""
    
        strOwner = Replace(tbOwners.Value, vbLf, "")
        
        If vAttList(2).TextString = "" Then GoTo Next_Z
        
        If strOwner = "" Then
            strOwner = vAttList(2).TextString & " : 1"
        Else
            vTemp = Split(strOwner, vbCr)
            For i = 0 To UBound(vTemp)
                vItem = Split(vTemp(i), " : ")
                If vItem(0) = vAttList(2).TextString Then
                    vTemp(i) = vItem(0) & " : " & CInt(vItem(1)) + 1
                    GoTo Found_Item
                End If
            Next i
            
            strOwner = strOwner & vbCr & vAttList(2).TextString & " : 1"
            GoTo Next_Z
Found_Item:
            strOwner = vTemp(0)
            If UBound(vTemp) > 0 Then
                For i = 1 To UBound(vTemp)
                    strOwner = strOwner & vbCr & vTemp(i)
                Next i
            End If
        End If
Next_Z:
        tbOwners.Value = strOwner
        
        lbAll.AddItem vAttList(0).TextString, 0
        iIndex = lbAll.ListCount - 1
        If vAttList(5).TextString = "" Then
            lbAll.List(0, 1) = ""
        Else
            lbAll.List(0, 1) = vAttList(5).TextString
        End If
        If vAttList(2).TextString = "" Then
            lbAll.List(0, 2) = ""
        Else
            lbAll.List(0, 2) = vAttList(2).TextString
        End If
        If vAttList(3).TextString = "" Then
            lbAll.List(0, 3) = ""
        Else
            lbAll.List(0, 3) = Replace(vAttList(3).TextString, " ", " & ")
        End If
        If vAttList(4).TextString = "" Then
            lbAll.List(0, 4) = ""
        Else
            If UCase(vAttList(4).TextString) = "NA" Then
                lbAll.List(0, 4) = ""
            ElseIf InStr(vAttList(4).TextString, "=") < 1 Then
                lbAll.List(0, 4) = "???=" & vAttList(4).TextString
            Else
                lbAll.List(0, 4) = vAttList(4).TextString
            End If
        End If
        
        vPnt1 = objBlock.InsertionPoint
        lbAll.List(0, 6) = FindDWGNumber(vPnt1)
        lbAll.List(0, 7) = vAttList(7).TextString
        lbAll.List(0, 8) = vPnt1(0) & "," & vPnt1(1)
        
        For i = 9 To 23
            If Not vAttList(i).TextString = "" Then
                Select Case i
                    Case Is = 9
                        If strAttachments = "" Then
                            strAttachments = "NEUTRAL=" & vAttList(i).TextString
                        Else
                            strAttachments = strAttachments & ";;" & "NEUTRAL=" & vAttList(i).TextString
                        End If
                    Case Is = 10
                        If strAttachments = "" Then
                            strAttachments = "TRANSFORMER=" & vAttList(i).TextString
                        Else
                            strAttachments = strAttachments & ";;" & "TRANSFORMER=" & vAttList(i).TextString
                        End If
                    Case Is = 11
                        If strAttachments = "" Then
                            strAttachments = "LOW POWER=" & vAttList(i).TextString
                        Else
                            strAttachments = strAttachments & ";;" & "LOW POWER=" & vAttList(i).TextString
                        End If
                    Case Is = 12
                        If strAttachments = "" Then
                            strAttachments = "ANTENNA=" & vAttList(i).TextString
                        Else
                            strAttachments = strAttachments & ";;" & "ANTENNA=" & vAttList(i).TextString
                        End If
                    Case Is = 13
                        If strAttachments = "" Then
                            strAttachments = "ST LT CIRCUIT=" & vAttList(i).TextString
                        Else
                            strAttachments = strAttachments & ";;" & "ST LT CIRCUIT=" & vAttList(i).TextString
                        End If
                    Case Is = 14
                        If strAttachments = "" Then
                            strAttachments = "ST LT=" & vAttList(i).TextString
                        Else
                            strAttachments = strAttachments & ";;" & "ST LT=" & vAttList(i).TextString
                        End If
                    Case Is = 15
                        If strAttachments = "" Then
                            strAttachments = "NEW 6M=" & vAttList(i).TextString
                        Else
                            strAttachments = strAttachments & ";;" & "NEW 6M=" & vAttList(i).TextString
                        End If
                    Case Else
                        If strAttachments = "" Then
                            strAttachments = vAttList(i).TextString
                        Else
                            strAttachments = strAttachments & ";;" & vAttList(i).TextString
                        End If
                        
                        vTemp = Split(vAttList(i).TextString, "=")
                        
                        If cbCompany.ListCount < 1 Then
                            cbCompany.AddItem vTemp(0)
                        Else
                            For n = 0 To cbCompany.ListCount - 1
                                If cbCompany.List(n) = vTemp(0) Then GoTo Found_Company
                            Next n
            
                            cbCompany.AddItem vTemp(0)
                        End If
Found_Company:
                End Select
            End If
        Next i
        
        If strAttachments = "" Then
            lbAll.List(0, 5) = ""
        Else
            lbAll.List(0, 5) = strAttachments
        End If
        
Next_objBlock:
    Next objBlock
    
Exit_Sub:
    objSS.Clear
    objSS.Delete
    
    'Call SortAllList
    
    Call CreateCompanyList
    tbNumberPoles.Value = iPole
    tbResult.Value = ""
    
    Me.show
End Sub

Private Sub Label38_Click()
    'If lbAll.ListCount < 1 Then Exit Sub
    
    'Dim strAtt(8) As String
    'Dim iCount As Integer
    
    'iCount = lbAll.ListCount - 1
    
    'For a = iCount To 0 Step -1
        'For b = 0 To a - 1
            'If lbAll.List(b, 6) > lbAll.List(b + 1, 6) Then
                'strAtt(0) = lbAll.List(b + 1, 0)
                'strAtt(1) = lbAll.List(b + 1, 1)
                'strAtt(2) = lbAll.List(b + 1, 2)
                'strAtt(3) = lbAll.List(b + 1, 3)
                'strAtt(4) = lbAll.List(b + 1, 4)
                'strAtt(5) = lbAll.List(b + 1, 5)
                'strAtt(6) = lbAll.List(b + 1, 6)
                'strAtt(7) = lbAll.List(b + 1, 7)
                'strAtt(8) = lbAll.List(b + 1, 8)

                'lbAll.List(b + 1, 0) = lbAll.List(b, 0)
                'lbAll.List(b + 1, 1) = lbAll.List(b, 1)
                'lbAll.List(b + 1, 2) = lbAll.List(b, 2)
                'lbAll.List(b + 1, 3) = lbAll.List(b, 3)
                'lbAll.List(b + 1, 4) = lbAll.List(b, 4)
                'lbAll.List(b + 1, 5) = lbAll.List(b, 5)
                'lbAll.List(b + 1, 6) = lbAll.List(b, 6)
                'lbAll.List(b + 1, 7) = lbAll.List(b, 7)
                'lbAll.List(b + 1, 8) = lbAll.List(b, 8)

                'lbAll.List(b, 0) = strAtt(0)
                'lbAll.List(b, 1) = strAtt(1)
                'lbAll.List(b, 2) = strAtt(2)
                'lbAll.List(b, 3) = strAtt(3)
                'lbAll.List(b, 4) = strAtt(4)
                'lbAll.List(b, 5) = strAtt(5)
                'lbAll.List(b, 6) = strAtt(6)
                'lbAll.List(b, 7) = strAtt(7)
                'lbAll.List(b, 8) = strAtt(8)
            'End If
        'Next b
    'Next a
End Sub

Private Sub lbAll_DblClick(ByVal Cancel As MSForms.ReturnBoolean)
    strLine = GetPoleData(CStr(lbAll.List(lbAll.ListIndex, 0)))
    tbResult.Value = strLine
End Sub

Private Sub lbAll_KeyDown(ByVal KeyCode As MSForms.ReturnInteger, ByVal Shift As Integer)
    Dim strPole As String
    Dim i, i2 As Integer
    Dim strAtt(8) As String
    
    Dim strLine As String
    Dim vLine As Variant
    Dim viewCoordsB(0 To 2) As Double
    Dim viewCoordsE(0 To 2) As Double
    
    Select Case KeyCode
        Case vbKeyReturn
            Me.Hide
    
            strLine = GetPoleData(CStr(lbAll.List(lbAll.ListIndex, 0)))
            tbResult.Value = strLine
    
            vLine = Split(lbAll.List(lbAll.ListIndex, 8), ",")
    
            viewCoordsB(0) = CDbl(vLine(0)) - 300
            viewCoordsB(1) = CDbl(vLine(1)) - 300
            viewCoordsB(2) = 0#
            viewCoordsE(0) = viewCoordsB(0) + 600
            viewCoordsE(1) = viewCoordsB(1) + 600
            viewCoordsE(2) = 0#
    
            ThisDrawing.Application.ZoomWindow viewCoordsB, viewCoordsE
            MsgBox strLine
    
            Me.show
        Case vbKeyUp
            If lbAll.ListIndex = 0 Then Exit Sub
            i = lbAll.ListIndex
            i2 = i - 1
            
            strAtt(0) = lbAll.List(i, 0)
            strAtt(1) = lbAll.List(i, 1)
            strAtt(2) = lbAll.List(i, 2)
            strAtt(3) = lbAll.List(i, 3)
            strAtt(4) = lbAll.List(i, 4)
            strAtt(5) = lbAll.List(i, 5)
            strAtt(6) = lbAll.List(i, 6)
            strAtt(7) = lbAll.List(i, 7)
            strAtt(8) = lbAll.List(i, 8)
            
            lbAll.List(i, 0) = lbAll.List(i2, 0)
            lbAll.List(i, 1) = lbAll.List(i2, 1)
            lbAll.List(i, 2) = lbAll.List(i2, 2)
            lbAll.List(i, 3) = lbAll.List(i2, 3)
            lbAll.List(i, 4) = lbAll.List(i2, 4)
            lbAll.List(i, 5) = lbAll.List(i2, 5)
            lbAll.List(i, 6) = lbAll.List(i2, 6)
            lbAll.List(i, 7) = lbAll.List(i2, 7)
            lbAll.List(i, 8) = lbAll.List(i2, 8)
            
            lbAll.List(i2, 0) = strAtt(0)
            lbAll.List(i2, 1) = strAtt(1)
            lbAll.List(i2, 2) = strAtt(2)
            lbAll.List(i2, 3) = strAtt(3)
            lbAll.List(i2, 4) = strAtt(4)
            lbAll.List(i2, 5) = strAtt(5)
            lbAll.List(i2, 6) = strAtt(6)
            lbAll.List(i2, 7) = strAtt(7)
            lbAll.List(i2, 8) = strAtt(8)
        Case vbKeyDown
            If lbAll.ListIndex = (lbAll.ListCount - 1) Then Exit Sub
            i = lbAll.ListIndex
            i2 = i + 1
            
            strAtt(0) = lbAll.List(i, 0)
            strAtt(1) = lbAll.List(i, 1)
            strAtt(2) = lbAll.List(i, 2)
            strAtt(3) = lbAll.List(i, 3)
            strAtt(4) = lbAll.List(i, 4)
            strAtt(5) = lbAll.List(i, 5)
            strAtt(6) = lbAll.List(i, 6)
            strAtt(7) = lbAll.List(i, 7)
            strAtt(8) = lbAll.List(i, 8)
            
            lbAll.List(i, 0) = lbAll.List(i2, 0)
            lbAll.List(i, 1) = lbAll.List(i2, 1)
            lbAll.List(i, 2) = lbAll.List(i2, 2)
            lbAll.List(i, 3) = lbAll.List(i2, 3)
            lbAll.List(i, 4) = lbAll.List(i2, 4)
            lbAll.List(i, 5) = lbAll.List(i2, 5)
            lbAll.List(i, 6) = lbAll.List(i2, 6)
            lbAll.List(i, 7) = lbAll.List(i2, 7)
            lbAll.List(i, 8) = lbAll.List(i2, 8)
            
            lbAll.List(i2, 0) = strAtt(0)
            lbAll.List(i2, 1) = strAtt(1)
            lbAll.List(i2, 2) = strAtt(2)
            lbAll.List(i2, 3) = strAtt(3)
            lbAll.List(i2, 4) = strAtt(4)
            lbAll.List(i2, 5) = strAtt(5)
            lbAll.List(i2, 6) = strAtt(6)
            lbAll.List(i2, 7) = strAtt(7)
            lbAll.List(i2, 8) = strAtt(8)
    End Select
End Sub

Private Sub lbCompany_DblClick(ByVal Cancel As MSForms.ReturnBoolean)
    Dim strPole As String
    
    strPole = GetPoleData(CStr(lbCompany.List(lbCompany.ListIndex, 0)))
    tbResult.Value = strPole
    'MsgBox strPole
End Sub

Private Sub lbCompany_KeyDown(ByVal KeyCode As MSForms.ReturnInteger, ByVal Shift As Integer)
    Dim strLine As String
    Dim vLine As Variant
    Dim viewCoordsB(0 To 2) As Double
    Dim viewCoordsE(0 To 2) As Double
    
    Select Case KeyCode
        Case vbKeyReturn
            Me.Hide
    
            strLine = GetPoleData(CStr(lbCompany.List(lbCompany.ListIndex, 0)))
            tbResult.Value = strLine
    
            vLine = Split(lbCompany.List(lbCompany.ListIndex, 5), ",")
    
            viewCoordsB(0) = CDbl(vLine(0)) - 300
            viewCoordsB(1) = CDbl(vLine(1)) - 300
            viewCoordsB(2) = 0#
            viewCoordsE(0) = viewCoordsB(0) + 600
            viewCoordsE(1) = viewCoordsB(1) + 600
            viewCoordsE(2) = 0#
    
            ThisDrawing.Application.ZoomWindow viewCoordsB, viewCoordsE
            MsgBox strLine
    
            Me.show
    End Select
End Sub

Private Sub lbReports_KeyDown(ByVal KeyCode As MSForms.ReturnInteger, ByVal Shift As Integer)
    If lbReports.ListIndex < 0 Then Exit Sub
    
    Select Case KeyCode
        Case vbKeyDelete
            lbReports.RemoveItem lbReports.ListIndex
    End Select
End Sub

Private Sub UserForm_Initialize()
    lbAll.ColumnCount = 9
    lbAll.ColumnWidths = "102;36;48;60;102;144;48;42;0"
    
    lbCompany.ColumnCount = 6
    lbCompany.ColumnWidths = "102;48;48;48;48;0"
    
    cbReports.AddItem "All"
    cbReports.AddItem "All MR"
    cbReports.AddItem "Visits"
    cbReports.AddItem "Owner"
    cbReports.AddItem "Owner/MR"
    cbReports.AddItem "Non Owner/MR"
    cbReports.AddItem "Non Owner/R/T/A"
    cbReports.AddItem "Owner/Lower"
    cbReports.AddItem "Lower"
    cbReports.AddItem "R/T/A"
    cbReports.Value = "Visits"
    
    cbFormList.AddItem "ATT Form"
    cbFormList.AddItem "TDS Owner Form"
    cbFormList.AddItem "TDS MR Form"
End Sub

Private Sub CreateCompanyList()
    If lbAll.ListCount < 1 Then Exit Sub
    
    cbCompany.AddItem "NEW 6M"
    cbCompany.AddItem "LASH"
    
    For i = 0 To lbAll.ListCount - 1
        For j = 0 To cbCompany.ListCount - 1
            If cbCompany.List(j) = lbAll.List(i, 2) Then GoTo Next_I
        Next j
            
        cbCompany.AddItem lbAll.List(i, 2)
Next_I:
    Next i
End Sub

Private Sub SortAllList()
    If lbAll.ListCount < 1 Then Exit Sub
    
    Dim vNumber, vL, vR As Variant
    Dim strRoute, strPole As String
    Dim strRoute1, strPole1 As String
    Dim strAtt(8) As String
    Dim iCount As Integer
    
    'Dim strTemp As String
    
    On Error Resume Next
    
    iCount = lbAll.ListCount - 1
    
    For a = iCount To 0 Step -1
        For b = 0 To a - 1
            vL = Split(UCase(lbAll.List(b, 0)), "L")
            vR = Split(vL(UBound(vL)), "R")
            strPole = vR(UBound(vR))
            strRoute = Left(lbAll.List(b, 0), (Len(lbAll.List(b, 0)) - Len(strPole)))
            strPole = Replace(strPole, "X", "")
           
            vL = Split(UCase(lbAll.List(b + 1, 0)), "L")
            vR = Split(vL(UBound(vL)), "R")
            strPole1 = vR(UBound(vR))
            strRoute1 = Left(lbAll.List(b, 0), (Len(lbAll.List(b, 0)) - Len(strPole1)))
            strPole1 = Replace(strPole1, "X", "")
            
            'strTemp = strRoute & vbTab & strPole & vbCr & strRoute1 & vbTab & strPole1
            'strTemp = strTemp & vbCr & (strRoute > strRoute1) & vbCr
            'strTemp = strTemp & (strRoute = strRoute1) & vbTab & (strPole > strPole1)
            'MsgBox strTemp
            
            If strRoute > strRoute1 Then
                    strAtt(0) = lbAll.List(b + 1, 0)
                    strAtt(1) = lbAll.List(b + 1, 1)
                    strAtt(2) = lbAll.List(b + 1, 2)
                    strAtt(3) = lbAll.List(b + 1, 3)
                    strAtt(4) = lbAll.List(b + 1, 4)
                    strAtt(5) = lbAll.List(b + 1, 5)
                    strAtt(6) = lbAll.List(b + 1, 6)
                    strAtt(7) = lbAll.List(b + 1, 7)
                    strAtt(8) = lbAll.List(b + 1, 8)
                
                    lbAll.List(b + 1, 0) = lbAll.List(b, 0)
                    lbAll.List(b + 1, 1) = lbAll.List(b, 1)
                    lbAll.List(b + 1, 2) = lbAll.List(b, 2)
                    lbAll.List(b + 1, 3) = lbAll.List(b, 3)
                    lbAll.List(b + 1, 4) = lbAll.List(b, 4)
                    lbAll.List(b + 1, 5) = lbAll.List(b, 5)
                    lbAll.List(b + 1, 6) = lbAll.List(b, 6)
                    lbAll.List(b + 1, 7) = lbAll.List(b, 7)
                    lbAll.List(b + 1, 8) = lbAll.List(b, 8)
                
                    lbAll.List(b, 0) = strAtt(0)
                    lbAll.List(b, 1) = strAtt(1)
                    lbAll.List(b, 2) = strAtt(2)
                    lbAll.List(b, 3) = strAtt(3)
                    lbAll.List(b, 4) = strAtt(4)
                    lbAll.List(b, 5) = strAtt(5)
                    lbAll.List(b, 6) = strAtt(6)
                    lbAll.List(b, 7) = strAtt(7)
                    lbAll.List(b, 8) = strAtt(8)
            ElseIf strRoute = strRoute1 Then
                If strPole > strPole1 Then
                        strAtt(0) = lbAll.List(b + 1, 0)
                        strAtt(1) = lbAll.List(b + 1, 1)
                        strAtt(2) = lbAll.List(b + 1, 2)
                        strAtt(3) = lbAll.List(b + 1, 3)
                        strAtt(4) = lbAll.List(b + 1, 4)
                        strAtt(5) = lbAll.List(b + 1, 5)
                        strAtt(6) = lbAll.List(b + 1, 6)
                        strAtt(7) = lbAll.List(b + 1, 7)
                        strAtt(8) = lbAll.List(b + 1, 8)
                
                        lbAll.List(b + 1, 0) = lbAll.List(b, 0)
                        lbAll.List(b + 1, 1) = lbAll.List(b, 1)
                        lbAll.List(b + 1, 2) = lbAll.List(b, 2)
                        lbAll.List(b + 1, 3) = lbAll.List(b, 3)
                        lbAll.List(b + 1, 4) = lbAll.List(b, 4)
                        lbAll.List(b + 1, 5) = lbAll.List(b, 5)
                        lbAll.List(b + 1, 6) = lbAll.List(b, 6)
                        lbAll.List(b + 1, 7) = lbAll.List(b, 7)
                        lbAll.List(b + 1, 8) = lbAll.List(b, 8)
                
                        lbAll.List(b, 0) = strAtt(0)
                        lbAll.List(b, 1) = strAtt(1)
                        lbAll.List(b, 2) = strAtt(2)
                        lbAll.List(b, 3) = strAtt(3)
                        lbAll.List(b, 4) = strAtt(4)
                        lbAll.List(b, 5) = strAtt(5)
                        lbAll.List(b, 6) = strAtt(6)
                        lbAll.List(b, 7) = strAtt(7)
                        lbAll.List(b, 8) = strAtt(8)
                End If
            End If
        Next b
    Next a
    
End Sub

Private Function GetAttachmentData(strLine As String)
    Dim vResult As Variant
    Dim strResult(3) As String
    Dim vLine, vItem, vTemp As Variant
    Dim iExist, iProp As Integer
    
    strLine = UCase(strLine)
    
    strResult(0) = ""
    strResult(1) = ""
    strResult(2) = ""
    strResult(3) = ""
    
    If InStr(strLine, "C") > 0 Then
        strResult(3) = " C-WIRE"
        strLine = Replace(strLine, "C", "")
    End If
    
    If InStr(strLine, "D") > 0 Then
        strResult(3) = " DROP"
        strLine = Replace(strLine, "D", "")
    End If
    
    If InStr(strLine, "F") > 0 Then
        strResult(2) = "FUTURE"
        strLine = Replace(strLine, "F", "")
    End If
    
    If InStr(strLine, "O") > 0 Then
        strResult(3) = " OHG"
        strLine = Replace(strLine, "O", "")
    End If
    
    If InStr(strLine, "S") > 0 Then
        strResult(3) = " SS"
        strLine = Replace(strLine, "S", "")
    End If
    
    If InStr(strLine, "T") > 0 Then
        strResult(2) = "MTE TAG"
        strLine = Replace(strLine, "T", "")
    End If
    
    If InStr(strLine, "V") > 0 Then
        strResult(3) = "LASH TO "
        strLine = Replace(strLine, "V", "")
    End If
    
    If InStr(strLine, "X") > 0 Then
        strResult(2) = "ATTACH"
        strLine = Replace(strLine, "X", "")
    End If
    
    If InStr(strLine, ")") > 0 Then
        vLine = Split(strLine, ")")
        strResult(0) = Replace(vLine(0), "(", "")
        strResult(1) = vLine(1)
    Else
        strResult(0) = strLine
        GoTo Skip_Next
    End If
    
    vItem = Split(strResult(0), "-")
    iExist = CInt(vItem(0)) * 12 + CInt(vItem(1))
    
    vItem = Split(strResult(1), "-")
    iProp = CInt(vItem(0)) * 12 + CInt(vItem(1))
    
    Select Case (iProp - iExist)
        Case Is > 0
            strResult(2) = "RAISE"
        Case Is = 0
            strResult(2) = "TRANSFER"
        Case Else
            strResult(2) = "LOWER"
    End Select
    
Skip_Next:
    vResult = strResult
    GetAttachmentData = vResult
End Function

Private Function FindDWGNumber(vPnt As Variant)
    Dim objSSTemp As AcadSelectionSet
    Dim objBlock As AcadBlockReference
    Dim filterType, filterValue As Variant
    Dim grpCode(0) As Integer
    Dim grpValue(0) As Variant
    Dim vAttList As Variant
    Dim dLL(2), dUR(2) As Double
    Dim dPnt(1) As Double
    Dim dScale As Double
    Dim strDWG As String
    
    On Error Resume Next
    
    strDWG = "??"
    dPnt(0) = vPnt(0)
    dPnt(1) = vPnt(1)
    
    grpCode(0) = 2
    grpValue(0) = "SS-11x17"
    filterType = grpCode
    filterValue = grpValue
    
    Err = 0
    Set objSSTemp = ThisDrawing.SelectionSets.Add("objSSTemp")
    If Not Err = 0 Then
        Set objSSTemp = ThisDrawing.SelectionSets.Item("objSSTemp")
        Err = 0
    End If
    
    objSSTemp.Select acSelectionSetAll, , , filterType, filterValue
    
    For Each objBlock In objSSTemp
        vAttList = objBlock.GetAttributes
        dScale = objBlock.XScaleFactor
        
        dLL(0) = objBlock.InsertionPoint(0)
        dLL(1) = objBlock.InsertionPoint(1)
        
        dUR(0) = dLL(0) + (1650 * dScale)
        dUR(1) = dLL(1) + (1050 * dScale)
        
        If dPnt(0) > dLL(0) And dPnt(0) < dUR(0) Then
            If dPnt(1) > dLL(1) And dPnt(1) < dUR(1) Then
                strDWG = vAttList(0).TextString
                'MsgBox "Found:" & strDWG
                GoTo Exit_Sub
            End If
        End If
    Next objBlock
    
Exit_Sub:
    objSSTemp.Clear
    objSSTemp.Delete
    
    FindDWGNumber = strDWG
End Function

Private Function GetPoleData(strPoleNumber As String)
    If lbAll.ListCount < 1 Then Exit Function
    
    Dim strData, strAttach, strLine As String
    Dim vLine, vItem, vTemp As Variant
    
    strData = ""
    strAttach = ""
    
    For i = 0 To lbAll.ListCount - 1
        If lbAll.List(i, 0) = strPoleNumber Then
            If Len(lbAll.List(i, 2)) < 8 Then
                strData = lbAll.List(i, 2) & vbTab & vbTab & lbAll.List(i, 3)
            Else
                strData = lbAll.List(i, 2) & vbTab & lbAll.List(i, 3)
            End If
                
            strData = strData & vbCr & "UNITED#" & vbTab & vbTab & lbAll.List(i, 0)
                
            If Not lbAll.List(i, 4) = "" Then
                vTemp = Split(lbAll.List(i, 4), " ")
                For j = 0 To UBound(vTemp)
                    vItem = Split(vTemp(j), "=")
                    If Len(vItem(0)) < 8 Then
                        strData = strData & vbCr & vItem(0) & vbTab & vbTab & vItem(1)
                    Else
                        strData = strData & vbCr & vItem(0) & vbTab & vItem(1)
                    End If
                Next j
            End If
            
            strData = strData & vbCr & "SIZE-CLASS" & vbTab & lbAll.List(i, 1)  'Could move ahead of SIZE-CLASS
            
            If Not lbAll.List(i, 6) = "" Then strData = strData & vbCr & "LOCATION" & vbTab & lbAll.List(i, 6)
                
            If Not lbAll.List(i, 7) = "" Then strData = strData & vbCr & lbAll.List(i, 7)
                
            strData = strData & vbCr & "----------  ATTACHMENTS  ----------"
            
            strAttach = GetAttachments(CStr(lbAll.List(i, 5)))
            
            GoTo Exit_Next
        End If
    Next i
Exit_Next:
    
    strData = strData & vbCr & strAttach
    
    GetPoleData = strData
End Function

Private Function GetAttachments(strLine As String)
    Dim vLine, vItem, vTemp, vHeight As Variant
    Dim vTotal As Variant
    Dim strAttach, strAll, strCO As String
    Dim strTemp, strExtra As String
    Dim iExist, iCurrent, iNext, iCount As Integer
    
    strAll = ""
    
    vLine = Split(strLine, ";;")
    For i = 0 To UBound(vLine)
        vItem = Split(vLine(i), "=")
        vTemp = Split(UCase(vItem(1)), " ")
        For j = 0 To UBound(vTemp)
            If vTemp(j) = "" Then GoTo Next_J
            
            strCO = vItem(0)
            strExtra = ""
            
            If InStr(vItem(0), "NEW ") > 0 Then strExtra = "NEW"
            
            If InStr(vTemp(j), "C") > 0 Then
                strCO = vItem(0) & " C_WIRE"
                vTemp(j) = Replace(vTemp(j), "C", "")
            End If
        
            If InStr(vTemp(j), "D") > 0 Then
                strCO = vItem(0) & " DROP"
                vTemp(j) = Replace(vTemp(j), "D", "")
            End If
        
            If InStr(vTemp(j), "F") > 0 Then
                strExtra = "FUTURE"
                vTemp(j) = Replace(vTemp(j), "F", "")
            End If
        
            If InStr(vTemp(j), "O") > 0 Then
                strCO = vItem(0) & " OHG"
                vTemp(j) = Replace(vTemp(j), "O", "")
            End If
        
            If InStr(vTemp(j), "S") > 0 Then
                strCO = vItem(0) & " SS"
                vTemp(j) = Replace(vTemp(j), "S", "")
            End If
        
            If InStr(vTemp(j), "T") > 0 Then
                strExtra = "MTE TAG"
                vTemp(j) = Replace(vTemp(j), "T", "")
            End If
        
            If InStr(vTemp(j), "V") > 0 Then
                strCO = "LASH TO " & vItem(0)
                vTemp(j) = Replace(vTemp(j), "V", "")
            End If
        
            If InStr(vTemp(j), "X") > 0 Then
                strExtra = "ATTACH"
                vTemp(j) = Replace(vTemp(j), "X", "")
            End If
            
            vHeight = Split(vTemp(j), ")")
            vTotal = Split(vHeight(UBound(vHeight)), "-")
            iExist = CInt(vTotal(0)) * 12
            If UBound(vTotal) > 0 Then iExist = iExist + CInt(vTotal(1))
            
            If strAll = "" Then
                strAll = iExist & "=" & strCO & "=" & Replace(vTemp(j), ")", ")=")
            Else
                strAll = strAll & ";;" & iExist & "=" & strCO & "=" & Replace(vTemp(j), ")", ")=")
            End If
            
            If Not strExtra = "" Then strAll = strAll & "=" & strExtra
Next_J:
            
        Next j
    Next i
    
    vLine = Split(strAll, ";;")
    iCount = UBound(vLine)
    
    For a = iCount To 0 Step -1
        For b = 0 To a - 1
            vItem = Split(vLine(b), "=")
            iCurrent = CInt(vItem(0))
            vItem = Split(vLine(b + 1), "=")
            iNext = CInt(vItem(0))
            
            If iCurrent < iNext Then
                strTemp = vLine(b + 1)
                vLine(b + 1) = vLine(b)
                vLine(b) = strTemp
            End If
        Next b
    Next a
    
    strAttach = "NONE"
    
    For i = 0 To iCount
        vItem = Split(vLine(i), "=")
        strTemp = vItem(1)
        If Len(strTemp) < 8 Then
            strTemp = strTemp & vbTab & vbTab & vItem(2)
        Else
            strTemp = strTemp & vbTab & vItem(2)
        End If
        If UBound(vItem) > 2 Then strTemp = strTemp & vbTab & vItem(3)
        
        If strAttach = "NONE" Then
            strAttach = strTemp
        Else
            strAttach = strAttach & vbCr & strTemp
        End If
    Next i
    
    GetAttachments = strAttach
End Function

Private Sub GetReports(strReport As String)
    If lbCompany.ListCount < 1 Then Exit Sub
    
    Dim vTemp As Variant
    Dim strDWGName, strFileName As String
    Dim strPole As String
    Dim iTest, iCount As Integer
    
    iCount = 0
    
    vTemp = Split(ThisDrawing.Name, " ")
    strDWGName = ThisDrawing.Path & "\" & vTemp(0)
    
    Select Case strReport
        Case "All"
            If tbAttPole.Value = "" Or tbAttPole.Value = "0" Then
                MsgBox "No poles to add to a report."
                Exit Sub
            End If
            
            strDWGName = strDWGName & " MR Report - " & cbCompany.Value & "-All Poles.txt"
        Case "All MR"
            If tbATTR.Value = "" Or tbATTR.Value = "0" Then
                If tbATTL.Value = "" Or tbATTL.Value = "0" Then
                    MsgBox "No poles to add to a report."
                    Exit Sub
                End If
            End If
            
            strDWGName = strDWGName & " MR Report - " & cbCompany.Value & "-All MR.txt"
        Case "Visits"
            If tbAttVisit.Value = "" Or tbAttVisit.Value = "0" Then
                MsgBox "No poles to add to a report."
                Exit Sub
            End If
            
            strDWGName = strDWGName & " MR Report - " & cbCompany.Value & "-Visits.txt"
        Case "Owner"
            If tbAtt.Value = "" Or tbAtt.Value = "0" Then
                MsgBox "No poles to add to a report."
                Exit Sub
            End If
            
            strDWGName = strDWGName & " MR Report - " & cbCompany.Value & "-Owner.txt"
        Case "Owner/MR"
            If tbATTR.Value = "" Or tbATTR.Value = "0" Then
                If tbATTL.Value = "" Or tbATTL.Value = "0" Then
                    MsgBox "No poles to add to a report."
                    Exit Sub
                End If
            End If
            
            strDWGName = strDWGName & " MR Report - " & cbCompany.Value & "-Owner MR.txt"
        Case "Non Owner/MR"
            If tbATTR.Value = "" Or tbATTR.Value = "0" Then
                If tbATTL.Value = "" Or tbATTL.Value = "0" Then
                    MsgBox "No poles to add to a report."
                    Exit Sub
                End If
            End If
            
            strDWGName = strDWGName & " MR Report - " & cbCompany.Value & "-NonOwner MR.txt"
        Case "Non Owner/R/T/A"
            If tbATTR.Value = "" Or tbATTR.Value = "0" Then
                If Not tbATTL.Value = "" Or Not tbATTL.Value = "0" Then
                    MsgBox "No poles to add to a report."
                    Exit Sub
                End If
            End If
            
            strDWGName = strDWGName & " MR Report - " & cbCompany.Value & "-NonOwner RTA.txt"
        Case "Lower"
            If tbATTL.Value = "" Or tbATTL.Value = "0" Then
                MsgBox "No poles to add to a report."
                Exit Sub
            End If
            
            strDWGName = strDWGName & " MR Report - " & cbCompany.Value & "-Lower.txt"
        Case "R/T/A"
            If tbATTR.Value = "" Or tbATTR.Value = "0" Then
                MsgBox "No poles to add to a report."
                Exit Sub
            End If
            
            strDWGName = strDWGName & " MR Report - " & cbCompany.Value & "-RTA.txt"
        Case Else
            iTest = CInt(tbAtt.Value) + CInt(tbATTL.Value)
            If iTest = 0 Then Exit Sub
            
            strDWGName = strDWGName & " MR Report - " & cbCompany.Value & "-Owner Lower.txt"
    End Select
    
    Open strDWGName For Output As #1
    
    For i = 0 To lbCompany.ListCount - 1
        Select Case strReport
            Case "All"
                strPole = GetPoleData(CStr(lbCompany.List(i, 0)))
                
                Print #1, strPole
                Print #1, ""
                Print #1, ""
                
                iCount = iCount + 1
            Case "All MR"
                If Not lbCompany.List(i, 2) = "" Or Not lbCompany.List(i, 3) = "" Then
                    strPole = GetPoleData(CStr(lbCompany.List(i, 0)))
                
                    Print #1, strPole
                    Print #1, ""
                    Print #1, ""
                
                    iCount = iCount + 1
                End If
            Case "Visits"
                If lbCompany.List(i, 1) = cbCompany.Value Or Not lbCompany.List(i, 2) = "" Or Not lbCompany.List(i, 3) = "" Then
                    strPole = GetPoleData(CStr(lbCompany.List(i, 0)))
                
                    Print #1, strPole
                    Print #1, ""
                    Print #1, ""
                
                    iCount = iCount + 1
                End If
            Case "Owner"
                If lbCompany.List(i, 1) = cbCompany.Value Then
                    strPole = GetPoleData(CStr(lbCompany.List(i, 0)))
                
                    Print #1, strPole
                    Print #1, ""
                    Print #1, ""
                
                    iCount = iCount + 1
                End If
            Case "Owner/MR"
                If Not lbCompany.List(i, 2) = "" Or Not lbCompany.List(i, 3) = "" Then
                    If lbCompany.List(i, 1) = cbCompany.Value Then
                        strPole = GetPoleData(CStr(lbCompany.List(i, 0)))
                
                        Print #1, strPole
                        Print #1, ""
                        Print #1, ""
                
                        iCount = iCount + 1
                    End If
                End If
            Case "Non Owner/MR"
                If Not lbCompany.List(i, 2) = "" Or Not lbCompany.List(i, 3) = "" Then
                    If Not lbCompany.List(i, 1) = cbCompany.Value Then
                        strPole = GetPoleData(CStr(lbCompany.List(i, 0)))
                
                        Print #1, strPole
                        Print #1, ""
                        Print #1, ""
                
                        iCount = iCount + 1
                    End If
                End If
            Case "Non Owner/R/T/A"
                If lbCompany.List(i, 2) = "" And Not lbCompany.List(i, 3) = "" Then
                    If Not lbCompany.List(i, 1) = cbCompany.Value Then
                        strPole = GetPoleData(CStr(lbCompany.List(i, 0)))
                
                        Print #1, strPole
                        Print #1, ""
                        Print #1, ""
                
                        iCount = iCount + 1
                    End If
                End If
            Case "Owner/Lower"
                If lbCompany.List(i, 1) = cbCompany.Value Or Not lbCompany.List(i, 2) = "" Then
                    strPole = GetPoleData(CStr(lbCompany.List(i, 0)))
                
                    Print #1, strPole
                    Print #1, ""
                    Print #1, ""
                
                    iCount = iCount + 1
                End If
            Case "Lower"
                If Not lbCompany.List(i, 2) = "" Then
                    strPole = GetPoleData(CStr(lbCompany.List(i, 0)))
                
                    Print #1, strPole
                    Print #1, ""
                    Print #1, ""
                
                    iCount = iCount + 1
                End If
            Case Else
                If Not lbCompany.List(i, 3) = "" Then
                    strPole = GetPoleData(CStr(lbCompany.List(i, 0)))
                
                    Print #1, strPole
                    Print #1, ""
                    Print #1, ""
                
                    iCount = iCount + 1
                End If
        End Select
Next_I:
    Next i
    
    Close #1
    
    MsgBox iCount & " poles in report:" & vbCr & strDWGName
End Sub

Private Sub AttForm()
    Dim strExistingName, strFileName As String
    Dim strTemp, strFormName As String
    Dim strAttach As String
    Dim vTemp, vTemp2, vLine As Variant
    Dim fName, strLocal As String
    Dim objExcel As Workbook
    Dim objDoc As Object
    Dim iRow As Integer
    
    iRow = 4
    
    vTemp = Split(ThisDrawing.Name, " ")
    strFileName = ThisDrawing.Path & "\" & vTemp(0) & " MR Report - ATT-Owner Lower.txt"
    strExistingName = ThisDrawing.Path & "\" & vTemp(0) & " ATT - Pole-Data-003_Pole_Data_Request-Part (A).xlsx"
    strLocal = "C:\Integrity\VBA\Forms\"
    
    'fName = Dir(strFileName)
    'If fName = "" Then
        'Exit Sub
    'End If
    
    Open strFileName For Input As #1
    
    'Set objExcel = CreateObject("Excel.Application")
    'objExcel.Visible = False
    
    fName = Dir(strExistingName)
    If fName = "" Then
        strTemp = ThisDrawing.Path
        If InStr(LCase(strTemp), "dropbox") > 0 Then
            vTemp2 = Split(LCase(strTemp), "dropbox")
            strFormName = vTemp2(0) & "Dropbox\UNITED COMMUNICATIONS JOB INFORMATION\5 - FORMS\ATT\ATT - Pole-Data-003_Pole_Data_Request-Part (A).xlsx"
        Else
            strFormName = strLocal & "ATT - Pole-Data-003_Pole_Data_Request-Part (A).xlsx"
        End If
        
        Set objExcel = Workbooks.Open(strFormName)
        objExcel.SaveAs (strExistingName)
        MsgBox "Created New File."
    Else
        Set objExcel = Workbooks.Open(strExistingName)
        MsgBox "Opened Existing File"
    End If
    
    objExcel.Sheets("Sheet1").Cells(1, 17).Value = Date
    objExcel.Sheets("Sheet1").Cells(2, 9).Value = vTemp(0)
    
    While Not EOF(1)
        Line Input #1, strTemp
        If strTemp = "" Then GoTo Next_line
        If Left(strTemp, 1) = "-" Then GoTo Next_line
        
        vTemp2 = Split(strTemp, vbTab)
        
        If Not vTemp2(0) = "ATT" Then
            While Not strTemp = ""
                Line Input #1, strTemp
            Wend
            GoTo Next_line
        End If
        
        objExcel.Sheets("Sheet1").Cells(iRow, 2).Value = vTemp2(UBound(vTemp2))
        
        Line Input #1, strTemp
        While Not Left(strTemp, 1) = "-"
            vTemp2 = Split(strTemp, vbTab)
            Select Case vTemp2(0)
                Case "UNITED#"
                    objExcel.Sheets("Sheet1").Cells(iRow, 3).Value = vTemp2(UBound(vTemp2))
                Case "SIZE-CLASS"
                    vLine = Split(vTemp2(1), "-")
                    If UBound(vLine) > 0 Then objExcel.Sheets("Sheet1").Cells(iRow, 5).Value = vLine(0)
                    If UBound(vLine) > 0 Then objExcel.Sheets("Sheet1").Cells(iRow, 6).Value = vLine(1)
                Case "LOCATION"
                    vLine = Split(vTemp2(1), " ")
                    If UBound(vLine) > 0 Then objExcel.Sheets("Sheet1").Cells(iRow, 4).Value = vLine(1)
                Case Else
                    If UBound(vTemp2) = 0 Then objExcel.Sheets("Sheet1").Cells(iRow, 7).Value = strTemp
            End Select
            
            Line Input #1, strTemp
        Wend
        
        strAttach = ""
        
        While Not strTemp = ""
            vLine = Split(strTemp, vbTab)
            
            If vLine(UBound(vLine)) = "NEW" Or vLine(UBound(vLine)) = "FUTURE" Then
                If strAttach = "" Then
                    strAttach = vLine(UBound(vLine) - 1)
                Else
                    strAttach = strAttach & vbCrLf & vLine(UBound(vLine) - 1)
                End If
                
                'If objExcel.Sheets("Sheet1").Cells(iRow, 10).Value = "" Then
                    'objExcel.Sheets("Sheet1").Cells(iRow, 10).Value = vLine(UBound(vLine) - 1)
                'Else
                    'objExcel.Sheets("Sheet1").Cells(iRow, 10).Value = objExcel.Sheets("Sheet1").Cells(iRow, 10).Value & vbCrLf & vLine(UBound(vLine) - 1)
                'End If
                
                If vLine(UBound(vLine)) = "FUTURE" Then
                    strAttach = strAttach & " FUTURE"
                End If
            
                objExcel.Sheets("Sheet1").Cells(iRow, 9).Value = "C"
            End If
            
            Line Input #1, strTemp
        Wend
        objExcel.Sheets("Sheet1").Cells(iRow, 10).Value = strAttach
        
        iRow = iRow + 1
        
Next_line:
    Wend
    
    'MsgBox objExcel.Sheets("Sheet1").Cells(4, 3).Value
    
    objExcel.Save
    objExcel.Close
    Close #1
    
    MsgBox "Form Completed."
End Sub

Private Sub TDSForm(strFileName As String)
    'Dim objDocument As Document
    Dim objDocument
    Dim objField As Word.FormField
    Dim strFormFile, strLine As String
    Dim strFormName As String
    Dim strTDS, strPWR, strLocation As String
    Dim strLL, strOwner, strMR, strType As String
    Dim vTemp, vLine As Variant
    Dim fName, strLocal As String
    Dim iCount, iField, iCost, iItem As Integer
    
    iCount = 0
    
    Set objDocument = CreateObject("word.application")
    strLocal = "C:\Integrity\VBA\Forms\"
    
    vTemp = Split(ThisDrawing.Name, " ")
    'strFile = "C:\Integrity\Temp\Delete This\CustomerTest\TDS Pole Form with info.docx"
    'strFormFile = "C:\Integrity\Temp\Delete This\CustomerTest\TDS Pole Form.docx"
    
    Select Case cbFormList.Value
        Case "TDS Owner Form"
            strFormFile = ThisDrawing.Path & "\" & vTemp(0) & " TDS Application for Pole Attachments (Form600P).docx"
            
            fName = Dir(strFormFile)
            If fName = "" Then
                strTemp = ThisDrawing.Path
                If InStr(LCase(strTemp), "dropbox") > 0 Then
                    vLine = Split(LCase(strTemp), "dropbox")
                    strFormName = vLine(0) & "Dropbox\UNITED COMMUNICATIONS JOB INFORMATION\VBA\Integrity\VBA\Forms\TDS Application for Pole Attachments (Form600P).docx"
                Else
                    strFormName = strLocal & "TDS Application for Pole Attachments (Form600P).docx"
                End If
                
                'MsgBox strFormName
                objDocument.Documents.Open strFormName
                objDocument.Visible = True
                objDocument.ActiveDocument.SaveAs strFormFile
            Else
                objDocument.Documents.Open strFormFile
                objDocument.Visible = True
            End If
            
            objDocument.ActiveDocument.FormFields(3).result = Date
            objDocument.ActiveDocument.FormFields(4).result = vTemp(0)
            objDocument.ActiveDocument.FormFields(18).result = "125.00"
            objDocument.ActiveDocument.FormFields(19).result = "250.00"
            objDocument.ActiveDocument.FormFields(25).result = "Tim Thompson / Director of Construction"
            objDocument.ActiveDocument.FormFields(26).result = "UNITED COMMUNICATIONS"
            objDocument.ActiveDocument.FormFields(27).result = vTemp(0)
            objDocument.ActiveDocument.FormFields(28).result = Date
            
            iField = 29
            iCost = 375
        Case "TDS MR Form"
            strFormFile = ThisDrawing.Path & "\" & vTemp(0) & " TDS Third Party MRW Request Form.docx"
            
            fName = Dir(strFormFile)
            If fName = "" Then
                strTemp = ThisDrawing.Path
                If InStr(LCase(strTemp), "dropbox") > 0 Then
                    vLine = Split(LCase(strTemp), "dropbox")
                    strFormName = vLine(0) & "Dropbox\UNITED COMMUNICATIONS JOB INFORMATION\VBA\Integrity\VBA\Forms\TDS Third Party MRW Request Form.docx"
                Else
                    strFormName = strLocal & "TDS Third Party MRW Request Form.docx"
                End If
                
                'MsgBox strFormFile
                objDocument.Documents.Open strFormName
                objDocument.Visible = True
                objDocument.ActiveDocument.SaveAs strFormFile
            Else
                objDocument.Documents.Open strFormFile
                objDocument.Visible = True
            End If
            
            objDocument.ActiveDocument.FormFields(3).result = Date
            objDocument.ActiveDocument.FormFields(4).result = vTemp(0)
            'objDocument.ActiveDocument.FormFields(10).result = "125.00"
            objDocument.ActiveDocument.FormFields(10).result = "250.00"
            'objDocument.ActiveDocument.FormFields(26).result = "UNITED COMMUNICATIONS"
            'objDocument.ActiveDocument.FormFields(27).result = vTemp(0)
            'objDocument.ActiveDocument.FormFields(28).result = Date
            
            iField = 14
            iCost = 250
    End Select
    
    'Set objDocument = Documents.Open(strFile)
    
    Open strFileName For Input As #1
    
    While Not EOF(1)
        Line Input #1, strTemp
        If strTemp = "" Then GoTo Next_line
        If Left(strTemp, 1) = "-" Then GoTo Next_line
        
        'strTDS = "UNK"
        vTemp = Split(strTemp, vbTab)
        
        If vTemp(0) = "TDS" Then
            strOwner = "TDS"
            strTDS = vTemp(UBound(vTemp))
            strPWR = "N/A"
        Else
            strOwner = vTemp(0)
            strTDS = "UNK"
            strPWR = vTemp(UBound(vTemp))
        End If
        
        strType = "OL"
        strLocation = ""
        strLL = ""
        strMR = "NO"
        
        Line Input #1, strTemp
        While Not Left(strTemp, 1) = "-"
            vTemp = Split(strTemp, vbTab)
            Select Case vTemp(0)
                Case "TDS"
                    strTDS = vTemp(UBound(vTemp))
                Case "MTE", "MTEMC", "DREMC", "DRE", "NES"
                    strPWR = vTemp(0) & ": " & vTemp(UBound(vTemp))
                Case "LOCATION"
                    strLocation = vTemp(UBound(vTemp))
                Case Else
                    If UBound(vTemp) = 0 Then
                        If InStr(strTemp, ",") > 0 Then
                            strLL = strTemp
                        End If
                    End If
            End Select
            
            Line Input #1, strTemp
        Wend
        
        While Not strTemp = ""
            If Not Left(strTemp, 1) = "-" Then
                vTemp = Split(strTemp, vbTab)
                If vTemp(UBound(vTemp)) = "NEW" Then strType = "SW"
                
                If InStr(vTemp(0), "TDS") > 0 Then
                    If InStr(vTemp(UBound(vTemp) - 1), "(") > 0 Then strMR = "YES-TDS"
                End If
            End If
            Line Input #1, strTemp
        Wend
        
        objDocument.ActiveDocument.FormFields(iField).result = strType
        iField = iField + 1
        objDocument.ActiveDocument.FormFields(iField).result = strTDS
        iField = iField + 1
        objDocument.ActiveDocument.FormFields(iField).result = strPWR
        iField = iField + 1
        objDocument.ActiveDocument.FormFields(iField).result = strLocation
        iField = iField + 1
        objDocument.ActiveDocument.FormFields(iField).result = strLL
        iField = iField + 1
        objDocument.ActiveDocument.FormFields(iField).result = strOwner
        iField = iField + 1
        objDocument.ActiveDocument.FormFields(iField).result = "UNK"
        iField = iField + 1
        objDocument.ActiveDocument.FormFields(iField).result = strMR
        iField = iField + 1
        If strType = "SW" Then
            objDocument.ActiveDocument.FormFields(iField).result = "FIBER WITH STRAND"
        Else
            objDocument.ActiveDocument.FormFields(iField).result = "FIBER OVERLASHED TO EXISTING"
        End If
        iField = iField + 1
        iCount = iCount + 1
Next_line:
    Wend
    
    Select Case cbFormList.Value
        Case "TDS Owner Form"
            If iCount > 10 Then
                iItem = (iCount - 10) * 25
                iCost = iCost + iItem
                objDocument.ActiveDocument.FormFields(20).result = iItem & ".00"
        
                If iCount > 50 Then
                    iItem = 200
                    iCost = iCost + iItem
                    objDocument.ActiveDocument.FormFields(21).result = iItem & ".00"
                End If
            End If
    
            objDocument.ActiveDocument.FormFields(22).result = iCost & ".00"
            objDocument.ActiveDocument.FormFields(10).result = iCount
        Case Else
            If iCount > 10 Then
                iItem = (iCount - 10) * 25
                iCost = iCost + iItem
                objDocument.ActiveDocument.FormFields(11).result = iItem & ".00"
        
                If iCount > 50 Then
                    iItem = 200
                    iCost = iCost + iItem
                    objDocument.ActiveDocument.FormFields(12).result = iItem & ".00"
                End If
            End If
    
            objDocument.ActiveDocument.FormFields(13).result = iCost & ".00"
    End Select
    
    objDocument.Documents.Save
    'objDocument.Save
    'objDocument.Close
    Close #1
    
    MsgBox "Form Completed."
End Sub

Private Function GreaterThan(str1 As String, str2 As String)
    Dim i1Start, i1End, i1Len As Integer
    Dim i2Start, i2End, i2Len As Integer
    Dim iShort As Integer
    
    i1Len = Len(str1)
    i2Len = Len(str2)
    
    If i1Len < i2Len Then
        iShort = i1Len
    Else
        iShort = i2Len
    End If
    
    For i = 1 To iShort
        If Not Left(str1, i) = Left(str2, i) Then GoTo Exit_Next
    Next i
Exit_Next:
    
End Function

Attribute VB_Name = "MRWorksheet"
Attribute VB_Base = "0{707506E4-86BF-49B8-8FB5-33B7344D189D}{7BC3108C-4B26-49D5-9EE6-80E45CDEBE6A}"
Attribute VB_GlobalNameSpace = False
Attribute VB_Creatable = False
Attribute VB_PredeclaredId = True
Attribute VB_Exposed = False
Attribute VB_TemplateDerived = False
Attribute VB_Customizable = False
Public objPole As AcadBlockReference
Public iChanged As Integer

Dim iListIndex As Integer
Dim iSave As Integer
Dim iMaxFt, iMaxIn As Integer
Dim strAttachmentItem As String
Dim vCoordsAttach As Variant
Dim dPosition As Double
Dim dRotate As Double
Dim dInsertPnt(0 To 2) As Double

Private Sub cbAddCLR_Click()
    Dim iListIndex As Integer
    
    lbMR.AddItem
    iListIndex = lbMR.ListCount - 1
    
    If cbAddCLR.Caption = "Update" Then
        iListIndex = lbMR.ListIndex
        lbMR.RemoveItem iListIndex
        lbMR.AddItem "", iListIndex
        
        cbAddCLR.Caption = "Add CLR"
    End If
    
    lbMR.List(iListIndex, 0) = tbMRCompany.Value
    lbMR.List(iListIndex, 1) = tbMR.Value
    lbMR.List(iListIndex, 2) = cbType.Value
    lbMR.List(iListIndex, 3) = tbSpan.Value
    lbMR.List(iListIndex, 4) = tbDist.Value
    If Not tbEF.Value = "" Then
        lbMR.List(iListIndex, 5) = tbEF.Value & "-" & tbEI.Value
    Else
        lbMR.List(iListIndex, 5) = ""
    End If
    If Not tbPF.Value = "" Then
        lbMR.List(iListIndex, 6) = tbPF.Value & "-" & tbPI.Value
    Else
        lbMR.List(iListIndex, 6) = ""
    End If
    
    tbMRCompany.Value = ""
    tbMR.Value = ""
    cbType.Value = ""
    tbSpan.Value = ""
    tbDist.Value = ""
    tbEF.Value = ""
    tbEI.Value = ""
    tbPF.Value = ""
    tbPI.Value = ""
    
    Call RemoveEmptyRows
End Sub

Private Sub cbAddNote_Click()
    If cbNote.Value = "" Then Exit Sub
    
    Dim strNote As String
    Dim vAttList As Variant
    
    Select Case cbNote.Value
        Case "Pwr replace with 5 Taller Pole"
            strNote = "NOTE-TALL"
        Case "Pwr replace with 10 Taller Pole"
            strNote = "NOTE-TALL10"
        Case "Pwr replace Defective Pole"
            strNote = "NOTE-DEF"
        Case "Pwr Raise Attachment"
            strNote = "NOTE-PRA"
        Case "Replace Note with Other"
            strNote = "NOTE-OTHER"
        Case "Use Existing Holes"
            strNote = "NOTE-UEH"
        Case "Pole Permited Previously"
            vAttList = objPole.GetAttributes
            
            strNote = "NOTE-REF=" & vAttList(1).TextString
        Case "OCALC Required"
            strNote = "OCALC"
        Case "Extra Seperation"
            strNote = "NOTE-EC"
        Case Else
            MsgBox "Empty"
            Exit Sub
    End Select
    
    'MsgBox strNote
    
    If tbNoteList.Value = "" Then
        tbNoteList.Value = strNote
    Else
        tbNoteList.Value = tbNoteList.Value & vbCr & strNote
    End If
End Sub

Private Sub cbDelete_Click()
    If lbWorkspace.ListIndex < 0 Then Exit Sub
    
    lbWorkspace.RemoveItem lbWorkspace.ListIndex
    iSave = 1
End Sub

Private Sub cbDOWN_Click()
    Dim str0, str1, str2 As String
    Dim str3, str4, str5 As String
    Dim i, i2 As Integer
    
    If lbWorkspace.ListIndex < 0 Then Exit Sub
    If lbWorkspace.ListIndex = (lbWorkspace.ListCount - 1) Then Exit Sub
    i = lbWorkspace.ListIndex
    i2 = i + 1
    
    str0 = lbWorkspace.List(i, 0)
    str1 = lbWorkspace.List(i, 1)
    str2 = lbWorkspace.List(i, 2)
    str3 = lbWorkspace.List(i, 3)
    str4 = lbWorkspace.List(i, 4)
    str5 = lbWorkspace.List(i, 5)
    
    lbWorkspace.List(i, 0) = lbWorkspace.List(i2, 0)
    lbWorkspace.List(i, 1) = lbWorkspace.List(i2, 1)
    lbWorkspace.List(i, 2) = lbWorkspace.List(i2, 2)
    lbWorkspace.List(i, 3) = lbWorkspace.List(i2, 3)
    lbWorkspace.List(i, 4) = lbWorkspace.List(i2, 4)
    lbWorkspace.List(i, 5) = lbWorkspace.List(i2, 5)
    
    lbWorkspace.List(i2, 0) = str0
    lbWorkspace.List(i2, 1) = str1
    lbWorkspace.List(i2, 2) = str2
    lbWorkspace.List(i2, 3) = str3
    lbWorkspace.List(i2, 4) = str4
    lbWorkspace.List(i2, 5) = str5
    
    lbWorkspace.ListIndex = i2
End Sub

Private Sub cbFiveFootTaller_Click()
    If lbWorkspace.ListCount < 1 Then Exit Sub
    
    Dim vLine, vItem, vHC As Variant
    Dim strLine, strHC, strType As String
    Dim iH, iIncrease As Integer
    
    If Not tbTallerPole.Value = "" Then
        iIncrease = CInt(tbTallerPole.Value)
    Else
        Exit Sub
    End If
    
    strLine = Replace(tbPoleData.Value, vbLf, "")
    vLine = Split(strLine, vbCr)
    vItem = Split(vLine(1), vbTab)
    strLine = vItem(0) & vbTab & "(" & vItem(1) & ")"
    vHC = Split(UCase(vItem(1)), "-")
    
    On Error Resume Next
    
    strType = ""
    
    If InStr(vHC(0), "C") Then
        strType = "C"
        vHC(0) = Replace(vHC(0), "C", "")
    End If
    
    If InStr(vHC(0), "S") Then
        strType = "S"
        vHC(0) = Replace(vHC(0), "S", "")
    End If
    
    iH = CInt(vHC(0)) + iIncrease
    
    If Not Err = 0 Then Exit Sub
    
    strLine = strLine & strType & iH & "-" '& vHC(1)
    
    Select Case iH
        Case Is = 35
            If vHC(1) = "?" Then
                strLine = strLine & "4"
            Else
                If CInt(vHC(1)) < 4 Then
                    strLine = strLine & vHC(1)
                Else
                    strLine = strLine & "4"
                End If
            End If
        Case Is = 40
            If vHC(1) = "?" Then
                strLine = strLine & "3"
            Else
                If CInt(vHC(1)) < 3 Then
                    strLine = strLine & vHC(1)
                Else
                    strLine = strLine & "3"
                End If
            End If
        Case Is = 45, Is = 50
            If vHC(1) = "?" Then
                strLine = strLine & "2"
            Else
                If CInt(vHC(1)) < 3 Then
                    strLine = strLine & vHC(1)
                Else
                    strLine = strLine & "2"
                End If
            End If
        Case Is > 50
            If vHC(1) = "?" Then
                strLine = strLine & "1"
            Else
                If CInt(vHC(1)) < 2 Then
                    strLine = strLine & vHC(1)
                Else
                    strLine = strLine & "1"
                End If
            End If
    End Select
    vLine(1) = strLine
    
    strLine = vLine(0)
    
    For i = 1 To UBound(vLine)
        strLine = strLine & vbCr & vLine(i)
    Next i
    
    tbPoleData.Value = strLine
    
    iIncrease = CInt(iIncrease * 0.6)
    
    For i = 0 To lbWorkspace.ListCount - 1
        Select Case lbWorkspace.List(i, 0)
            Case "PWR"
                vLine = Split(lbWorkspace.List(i, 2), "-")
                lbWorkspace.List(i, 3) = CInt(vLine(0)) + iIncrease & "-" & vLine(1)
            Case "COMM"
                lbWorkspace.List(i, 3) = lbWorkspace.List(i, 2)
        End Select
        
        'If lbWorkspace.List(i, 0) = "PWR" Then
            'vLine = Split(lbWorkspace.List(i, 2), "-")
            'lbWorkspace.List(i, 3) = CInt(vLine(0)) + iIncrease & "-" & vLine(1)
        'End If
    Next i
    
    Call SortList
    
    Select Case tbTallerPole.Value
        Case "5"
            cbNote.Value = "Pwr replace with 5 Taller Pole"
        Case "10"
            cbNote.Value = "Pwr replace with 10 Taller Pole"
    End Select
End Sub

Private Sub cbFixDown_Click()
    Dim vTemp, vAttach, vCW As Variant
    Dim strLine As String
    Dim iCurrentIn, iAttachIn As Integer
    Dim iTempFt, iTempIn As Integer
    
    iAttachIn = 1000
    
    For i = 0 To lbWorkspace.ListCount - 1
        CheckForViolations (i)
    Next i
    
    For i = 0 To lbWorkspace.ListCount - 1
        Select Case lbWorkspace.List(i, 0)
            Case "PWR"
                vTemp = Split(lbWorkspace.List(i, 4), " ")
                vAttach = Split(vTemp(1), "-")
                iCurrentIn = CInt(vAttach(0)) * 12 + CInt(vAttach(1))
                
                If iCurrentIn < iAttachIn Then iAttachIn = iCurrentIn
            Case "UTC"
                iTempFt = CInt(iAttachIn / 12 - 0.5)
                iTempIn = iAttachIn - (iTempFt * 12)
                If iTempIn > 11 Then
                    iTempIn = iTempIn - 12
                    iTempFt = iTempFt + 1
                End If
                
                lbWorkspace.List(i, 3) = iTempFt & "-" & iTempIn
                iAttachIn = iAttachIn - CInt(tbBC.Value)
            Case "COMM"
                iTempFt = CInt(iAttachIn / 12 - 0.5)
                iTempIn = iAttachIn - (iTempFt * 12)
                If iTempIn > 11 Then
                    iTempIn = iTempIn - 12
                    iTempFt = iTempFt + 1
                End If
                
                lbWorkspace.List(i, 3) = iTempFt & "-" & iTempIn
                
                If Not lbWorkspace.ListCount = i + 1 Then
                    If lbWorkspace.List(i, 1) = lbWorkspace.List(i + 1, 1) Then
                        iAttachIn = iAttachIn - CInt(tbBSC.Value)
                    Else
                        iAttachIn = iAttachIn - CInt(tbBC.Value)
                    End If
                End If
        End Select
    Next i
End Sub

Private Sub cbGetAttach_Click()
    If iSave = 1 Then
        result = MsgBox("Save changes to Pole Attachments?", vbYesNo, "Save Changes")
        If result = vbYes Then
            Call SaveAttachments
            iSave = 0
        End If
    End If
    
    Dim objEntity As AcadEntity
    Dim vReturnPnt As Variant
    
    Me.Hide
    
    On Error Resume Next
    
    Err = 0
    ThisDrawing.Utility.GetEntity objEntity, vReturnPnt, "Select Pole: "
    If Not Err = 0 Then GoTo Exit_Sub
    
    If Not TypeOf objEntity Is AcadBlockReference Then GoTo Exit_Sub
    Set objPole = objEntity
    
    If Not objPole.Name = "sPole" Then GoTo Exit_Sub
    
    Call GetPoleData
    
    Call SortList
    
Exit_Sub:
    Me.show
End Sub

Private Sub cbGetData_Click()
    Dim objEntity As AcadEntity
    Dim objBlock As AcadBlockReference
    Dim vReturnPnt As Variant
    Dim vAttList As Variant
    Dim vLine, vTemp As Variant
    Dim vItem, vMR, vAttach As Variant
    Dim iEInch, iPInch As Integer
    Dim strLine, strCO As String
    Dim strTemp As String
    Dim strPrompt As String
    Dim iSpan, iAttach As Integer
    Dim iTest, iIndex As Integer
    Dim dEF As Double
    Dim lColor As Long
    
    On Error Resume Next
    
    Me.Hide
    
    tbPrePF.Value = ""
    tbPrePI.Value = ""
    
    iSpan = 0
    iAttach = 0
    strPrompt = "Select Cable Span & Bottom Attachment:"
    
Get_Block:
    Err = 0
    ThisDrawing.Utility.GetEntity objEntity, vReturnPnt, strPrompt
    If Not Err = 0 Then GoTo Exit_Sub
    
    If Not TypeOf objEntity Is AcadBlockReference Then GoTo Exit_Sub
    Set objBlock = objEntity
    vAttList = objBlock.GetAttributes
    
    Select Case objBlock.Name
        Case "cable_span"
            If vAttList(0).TextString = "" Then GoTo Bad_Block
            iSpan = 1
            vLine = Split(vAttList(0).TextString, " ")   '<----------------------------
            strTemp = vLine(0)
            strLine = vLine(1)
    
            vLine = Split(strLine, "-")
            tbEF.Value = vLine(0)
            tbEI.Value = vLine(1)
            
            iTest = CInt(vLine(0)) * 12 + CInt(vLine(1))
            
            Select Case LCase(Left(strTemp, 1))
                Case "r"
                    cbType.Value = "RD"
                    If iTest < 216 Then
                        lColor = 255
                    Else
                        lColor = 0
                    End If
                Case "d"
                    cbType.Value = "DW"
                    If iTest < 204 Then
                        lColor = 255
                    Else
                        lColor = 0
                    End If
                Case "m"
                    cbType.Value = "MS"
                    If iTest < 204 Then
                        lColor = 255
                    Else
                        lColor = 0
                    End If
                Case Else
                    cbType.Value = "NA"
                    GoTo Exit_Sub
            End Select
            tbEF.ForeColor = lColor
            tbEI.ForeColor = lColor  '<---------------------------------------------------
    
            strTemp = vAttList(2).TextString
            If Right(strTemp, 1) = "'" Then
                strTemp = Left(strTemp, Len(strTemp) - 1)
                tbSpan.Value = strTemp
            Else
                tbSpan.Value = strTemp
            End If
    
            dEF = CDbl(strTemp)
            tbDist.Value = CStr(dEF / 2)
        Case "sPole"
            iAttach = 1
            
            Load SelectAttach
                
                If Not vAttList(9).TextString = "" Then
                    vItem = Split(vAttList(9).TextString, " ")
                    
                    For i = 0 To UBound(vItem)
                        SelectAttach.lbAttach.AddItem "NEUTRAL"
                        iIndex = SelectAttach.lbAttach.ListCount - 1
                        
                        If InStr(vItem(i), ")") > 0 Then
                            vItem(i) = Replace(vItem(i), "(", "")
                            vMR = Split(vItem(i), ")")
                            
                            SelectAttach.lbAttach.List(iIndex, 1) = vMR(0)
                            SelectAttach.lbAttach.List(iIndex, 2) = vMR(1)
                        Else
                            SelectAttach.lbAttach.List(iIndex, 1) = vItem(i)
                            SelectAttach.lbAttach.List(iIndex, 2) = "x"
                        End If
                    Next i
                End If
                
                If Not vAttList(10).TextString = "" Then
                    vItem = Split(vAttList(10).TextString, " ")
                    
                    For i = 0 To UBound(vItem)
                        SelectAttach.lbAttach.AddItem "TRANSFORMER"
                        iIndex = SelectAttach.lbAttach.ListCount - 1
                        
                        If InStr(vItem(i), ")") > 0 Then
                            vItem(i) = Replace(vItem(i), "(", "")
                            vMR = Split(vItem(i), ")")
                            
                            SelectAttach.lbAttach.List(iIndex, 1) = vMR(0)
                            SelectAttach.lbAttach.List(iIndex, 2) = vMR(1)
                        Else
                            SelectAttach.lbAttach.List(iIndex, 1) = vItem(i)
                            SelectAttach.lbAttach.List(iIndex, 2) = "x"
                        End If
                    Next i
                End If
                
                If Not vAttList(11).TextString = "" Then
                    vItem = Split(vAttList(11).TextString, " ")
                    
                    For i = 0 To UBound(vItem)
                        SelectAttach.lbAttach.AddItem "LOW POWER"
                        iIndex = SelectAttach.lbAttach.ListCount - 1
                        
                        If InStr(vItem(i), ")") > 0 Then
                            vItem(i) = Replace(vItem(i), "(", "")
                            vMR = Split(vItem(i), ")")
                            
                            SelectAttach.lbAttach.List(iIndex, 1) = vMR(0)
                            SelectAttach.lbAttach.List(iIndex, 2) = vMR(1)
                        Else
                            SelectAttach.lbAttach.List(iIndex, 1) = vItem(i)
                            SelectAttach.lbAttach.List(iIndex, 2) = "x"
                        End If
                    Next i
                End If
                
                If Not vAttList(12).TextString = "" Then
                    vItem = Split(vAttList(12).TextString, " ")
                    
                    For i = 0 To UBound(vItem)
                        SelectAttach.lbAttach.AddItem "ANTENNA"
                        iIndex = SelectAttach.lbAttach.ListCount - 1
                        
                        If InStr(vItem(i), ")") > 0 Then
                            vItem(i) = Replace(vItem(i), "(", "")
                            vMR = Split(vItem(i), ")")
                            
                            SelectAttach.lbAttach.List(iIndex, 1) = vMR(0)
                            SelectAttach.lbAttach.List(iIndex, 2) = vMR(1)
                        Else
                            SelectAttach.lbAttach.List(iIndex, 1) = vItem(i)
                            SelectAttach.lbAttach.List(iIndex, 2) = "x"
                        End If
                    Next i
                End If
                
                If Not vAttList(13).TextString = "" Then
                    vItem = Split(vAttList(13).TextString, " ")
                    
                    For i = 0 To UBound(vItem)
                        SelectAttach.lbAttach.AddItem "ST LT CIRCUIT"
                        iIndex = SelectAttach.lbAttach.ListCount - 1
                        
                        If InStr(vItem(i), ")") > 0 Then
                            vItem(i) = Replace(vItem(i), "(", "")
                            vMR = Split(vItem(i), ")")
                            
                            SelectAttach.lbAttach.List(iIndex, 1) = vMR(0)
                            SelectAttach.lbAttach.List(iIndex, 2) = vMR(1)
                        Else
                            SelectAttach.lbAttach.List(iIndex, 1) = vItem(i)
                            SelectAttach.lbAttach.List(iIndex, 2) = "x"
                        End If
                    Next i
                End If
                
                If Not vAttList(14).TextString = "" Then
                    vItem = Split(vAttList(14).TextString, " ")
                    
                    For i = 0 To UBound(vItem)
                        SelectAttach.lbAttach.AddItem "ST LT"
                        iIndex = SelectAttach.lbAttach.ListCount - 1
                        
                        If InStr(vItem(i), ")") > 0 Then
                            vItem(i) = Replace(vItem(i), "(", "")
                            vMR = Split(vItem(i), ")")
                            
                            SelectAttach.lbAttach.List(iIndex, 1) = vMR(0)
                            SelectAttach.lbAttach.List(iIndex, 2) = vMR(1)
                        Else
                            SelectAttach.lbAttach.List(iIndex, 1) = vItem(i)
                            SelectAttach.lbAttach.List(iIndex, 2) = "x"
                        End If
                    Next i
                End If
                
                For j = 16 To 23
                    If Not vAttList(j).TextString = "" Then
                        vMR = Split(vAttList(j).TextString, "=")
                        strCO = vMR(0)
                        vItem = Split(UCase(vMR(1)), " ")
                    
                        For i = 0 To UBound(vItem)
                            SelectAttach.lbAttach.AddItem strCO
                            iIndex = SelectAttach.lbAttach.ListCount - 1
                                                
                            vItem(i) = Replace(vItem(i), "C", "")
                            vItem(i) = Replace(vItem(i), "O", "")
                            vItem(i) = Replace(vItem(i), "X", "")
                        
                            If InStr(vItem(i), ")") > 0 Then
                                vItem(i) = Replace(vItem(i), "(", "")
                                vMR = Split(vItem(i), ")")
                            
                                SelectAttach.lbAttach.List(iIndex, 1) = vMR(0)
                                SelectAttach.lbAttach.List(iIndex, 2) = vMR(1)
                            Else
                                SelectAttach.lbAttach.List(iIndex, 1) = vItem(i)
                                SelectAttach.lbAttach.List(iIndex, 2) = "x"
                            End If
                        Next i
                    End If
                Next j
                
                SelectAttach.lbAttach.Selected(SelectAttach.lbAttach.ListCount - 1) = True
                
                SelectAttach.show
                
                iIndex = SelectAttach.lbAttach.ListIndex
                
                If Not SelectAttach.lbAttach.List(iIndex, 2) = "x" Then
                    If Not SelectAttach.lbAttach.List(iIndex, 1) = "x" Then
                        vAttach = Split(SelectAttach.lbAttach.List(iIndex, 1), "-")
                        iEInch = CInt(vAttach(0)) * 12
                        If UBound(vAttach) > 0 Then iEInch = iEInch + CInt(vAttach(1))
                            
                        vAttach = Split(SelectAttach.lbAttach.List(iIndex, 2), "-")
                        iPInch = CInt(vAttach(0)) * 12
                        If UBound(vAttach) > 0 Then iPInch = iPInch + CInt(vAttach(1))
                        
                        tbMRCompany.Value = SelectAttach.lbAttach.List(iIndex, 0)
                        tbMR.Value = iPInch - iEInch
                    End If
                Else
                    tbMRCompany.Value = SelectAttach.lbAttach.List(iIndex, 0)
                    tbMR.Value = 0
                End If
                
            Unload SelectAttach
            
            
            
        Case "pole_attach"
            iAttach = 1
            'tbPrePole.Value = vAttList(0).TextString
            tbMRCompany.Value = vAttList(2).TextString
            
            If vAttList(4).TextString = "" Then
                tbMR.Value = 0
            Else
                vTemp = Split(vAttList(4).TextString, " ")
                If UBound(vTemp) = 0 Then
                    tbMR.Value = 0
                Else
                    vTemp(1) = Replace(vTemp(1), """", "")
                    Select Case Left(vAttList(4).TextString, 1)
                        Case "L"
                            tbMR.Value = 0 - CInt(vTemp(1))
                        Case "R"
                            tbMR.Value = CInt(vTemp(1))
                    End Select
                End If
            End If
    End Select
Bad_Block:
    If iSpan = 0 Then
        If iAttach = 0 Then
            strPrompt = "Select Cable Span & Bottom Attachment:"
        Else
            strPrompt = "Select Cable Span:"
        End If
    Else
        If iAttach = 0 Then
            strPrompt = "Select Bottom Attachment:"
        Else
            strPrompt = "Nothing Needed:"
        End If
    End If
    
    GoTo Get_Block
    
Exit_Sub:
    If strPrompt = "Select Bottom Attachment:" Then
        Dim iInt As Integer
        
        iInt = lbWorkspace.ListCount - 1
        
        tbMRCompany.Value = lbWorkspace.List(iInt, 1)
        tbMR.Value = "0"
    End If
    
    cbAddCLR.SetFocus
    Me.show
End Sub

Private Sub cbMRReport_Click()
    Me.Hide
        Load MRSheets
            MRSheets.show
        Unload MRSheets
    Me.show
End Sub

Private Sub cbPlaceCLR_Click()
    Dim str1, str2 As String
    Dim dScale As Double
    Dim xDiff, yDiff As Double
    Dim obrBR As AcadBlockReference
    Dim returnPnt, returnPnt2 As Variant
    Dim varItem, vTemp As Variant
    Dim layerObj As AcadLayer
    
    On Error Resume Next
    
    If lbMR.ListIndex < 0 Then Exit Sub
    If lbMR.List(lbMR.ListIndex, 0) = "" Then Exit Sub
    
    dScale = 0.75   'CInt(cbScale.Value) / 100 * 1.333333
    dRotate = 0
    
    Err = 0
    str1 = lbMR.List(lbMR.ListIndex, 0) & " " & lbMR.List(lbMR.ListIndex, 2) & " CLR"
    
    str2 = Replace(lbMR.List(lbMR.ListIndex, 5), "-", "'") & """"
    If Not lbMR.List(lbMR.ListIndex, 6) = "" Then
        str2 = "(" & str2 & ") " & Replace(lbMR.List(lbMR.ListIndex, 6), "-", "'") & """"
    End If
    
    Me.Hide
    
    If lbMR.List(lbMR.ListIndex, 2) = "DW" Then
        Call AddDriveways
        GoTo Place_Block:
    End If
    
    returnPnt = ThisDrawing.Utility.GetPoint(, "Place Clearance: ")
    dInsertPnt(0) = returnPnt(0)
    dInsertPnt(1) = returnPnt(1)
    dInsertPnt(2) = 0#
    
    returnPnt2 = ThisDrawing.Utility.GetPoint(, "Rotation Direction: ")
    If dInsertPnt(0) > returnPnt2(0) Then
        xDiff = dInsertPnt(0) - returnPnt2(0)
        yDiff = dInsertPnt(1) - returnPnt2(1)
    Else
        xDiff = returnPnt2(0) - dInsertPnt(0)
        yDiff = returnPnt2(1) - dInsertPnt(1)
    End If
    If xDiff = 0 Then
        dRotate = 1.570796327
    Else
        dRotate = Atn(yDiff / xDiff)
    End If
    
Place_Block:
    
    Set obrBR = ThisDrawing.ModelSpace.InsertBlock(dInsertPnt, "clr", dScale, dScale, dScale, dRotate)
    obrBR.Layer = "Integrity Roads-Clearance"
    varItem = obrBR.GetAttributes
    varItem(0).TextString = str1
    varItem(1).TextString = str2
    obrBR.Update
    
    Me.show
End Sub

Private Sub cbPlaceNote_Click()
    If lbWorkspace.ListCount = 0 Then GoTo Exit_Sub
    
    Dim returnPoint As Variant
    Dim insertionPnt(0 To 2) As Double
    Dim dRevCloud(0 To 5) As Double
    Dim dNote(0 To 2) As Double
    Dim dScale As Double
    Dim dPosition As Double
    Dim objBlock As AcadBlockReference
    Dim layerObj As AcadLayer
    Dim vAttList, vELine, vPLine As Variant
    Dim iPI, iEI As Integer
    Dim iMR, iNote As Integer
    Dim strAtt0, strAtt1, strAtt2, strAtt3, strAtt4 As String
    Dim strLayer As String
    
    Dim vStr As Variant
    Dim str, str1, strCommand As String
    Dim lwpPnt(0 To 3) As Double
    Dim lineObj As AcadLWPolyline
    Dim n, counter As Integer
    
  'On Error Resume Next
    
    strAtt0 = tbPoleNumber.Value
    
    iMR = 0
    iNote = 0
    dPosition = 1#
    
    Me.Hide
    dScale = 1#     'CInt(cbScale.Value) / 100
    
    returnPoint = ThisDrawing.Utility.GetPoint(, "Select point:")
    n = 0
    For Each Item In returnPoint
        insertionPnt(n) = Item
        n = n + 1
    Next Item
    
    dRevCloud(0) = insertionPnt(0) - (4 * dScale)
    dRevCloud(1) = insertionPnt(1) + (20 * dScale)
    dRevCloud(2) = 0#
    
    str = "pole_attach_title"
    Set objBlock = ThisDrawing.ModelSpace.InsertBlock(insertionPnt, str, dScale, dScale, dScale, 0)
    objBlock.Layer = "Integrity Attachments-Existing"
    vAttList = objBlock.GetAttributes
    vAttList(0).TextString = strAtt0
    
    objBlock.Update
    
    insertionPnt(0) = insertionPnt(0) + (78 * dScale)
    insertionPnt(1) = insertionPnt(1) - (4.5 * dScale)
    
    str = "pole_attach"
    For i = 0 To (lbWorkspace.ListCount - 1)
        dPosition = dPosition + 0.01
        strAtt1 = dPosition
        strAtt2 = lbWorkspace.List(i, 1)
        iPI = 0: iEI = 0
        
        If Not lbWorkspace.List(i, 2) = "" Then
            vELine = Split(lbWorkspace.List(i, 2), "-")
            
            If UBound(vELine) = 0 Then
                iEI = CInt(vELine(0)) * 12
            Else
                iEI = CInt(vELine(0)) * 12 + CInt(vELine(1))
            End If
        End If
        
        If Not lbWorkspace.List(i, 3) = "" Then
            vPLine = Split(lbWorkspace.List(i, 3), "-")
            
            If UBound(vPLine) = 0 Then
                iPI = CInt(vPLine(0)) * 12
            Else
                iPI = CInt(vPLine(0)) * 12 + CInt(vPLine(1))
            End If
        End If
        
        
        
        If iPI = 0 Then
            strAtt3 = vELine(0) & "'" & vELine(1) & """"
            strAtt4 = ""
            strLayer = "Integrity Attachments-Existing"
            GoTo Place_Attachment
        End If
        
        If lbWorkspace.List(i, 0) = "NEW" Then
            strAtt3 = vPLine(0) & "'" & vPLine(1) & """"
            strAtt4 = "NEW"
            strLayer = "Integrity Attachments-New"
            If iNote < 1 Then iNote = 1
            GoTo Place_Attachment
        End If
        
        If iEI = 0 Then
            strAtt3 = vPLine(0) & "'" & vPLine(1) & """"
            strAtt4 = "ATTACH"
            strLayer = "Integrity Attachments-MR"
            iNote = 2
            GoTo Place_Attachment
        End If
        
        If cbCalloutType.Value = "(Existing)Proposed" Then
            strAtt3 = "(" & vELine(0) & "'" & vELine(1) & """)"
            strAtt4 = vPLine(0) & "'" & vPLine(1) & """"
            strLayer = "Integrity Attachments-MR"
            iNote = 2
            GoTo Place_Attachment
        End If
        
        strAtt3 = vPLine(0) & "'" & vPLine(1) & """"
        strLayer = "Integrity Attachments-MR"
        iNote = 2
        
        iMR = iPI - iEI
        Select Case iMR
            Case Is < 0
                strAtt4 = "LOWER " & Abs(iMR) & """"
            Case Is = 0
                strAtt4 = "TRANSFER"
            Case Is > 0
                strAtt4 = "RAISE " & Abs(iMR) & """"
        End Select
        
Place_Attachment:
        'If vAttList(2).TextString = "ATT" Or vAttList(2).TextString = "BST" Then
            'If iNote > 0 Then iNote = 2
        'End If
        
        Set objBlock = ThisDrawing.ModelSpace.InsertBlock(insertionPnt, str, dScale, dScale, dScale, 0)
        objBlock.Layer = strLayer
        
        vAttList = objBlock.GetAttributes
        vAttList(0).TextString = strAtt0
        vAttList(1).TextString = strAtt1
        vAttList(2).TextString = strAtt2
        vAttList(3).TextString = strAtt3
        vAttList(4).TextString = strAtt4
        objBlock.Update
        
        insertionPnt(1) = insertionPnt(1) - (9 * dScale)
    Next i
    
    vAttList = objPole.GetAttributes
        
    Select Case vAttList(2).TextString
        Case "ATT", "BST"
            If iNote = 1 Then iNote = 3
    End Select
               
    Select Case iNote
        Case 0
            Set layerObj = ThisDrawing.Layers.Add("Integrity Attachments-Existing")
            ThisDrawing.ActiveLayer = layerObj
            dRevCloud(3) = insertionPnt(0) + (30 * dScale)
        Case 1
            Set layerObj = ThisDrawing.Layers.Add("Integrity Attachments-New")
            ThisDrawing.ActiveLayer = layerObj
            dRevCloud(3) = insertionPnt(0) + (58 * dScale)
        Case 2
            Set layerObj = ThisDrawing.Layers.Add("Integrity Attachments-MR")
            ThisDrawing.ActiveLayer = layerObj
            dRevCloud(3) = insertionPnt(0) + (84 * dScale)
        Case 3
            Set layerObj = ThisDrawing.Layers.Add("Integrity Attachments-MR")
            ThisDrawing.ActiveLayer = layerObj
            dRevCloud(3) = insertionPnt(0) + (58 * dScale)
    End Select
    dRevCloud(4) = insertionPnt(1) + (3 * dScale)
    dRevCloud(5) = 0#
    
    strCommand = "revcloud r " & dRevCloud(0) & "," & dRevCloud(1)
    strCommand = strCommand & " " & dRevCloud(3) & "," & dRevCloud(4) & " " & vbCr
    ThisDrawing.SendCommand strCommand
    
    Set layerObj = ThisDrawing.Layers.Add("0")
    ThisDrawing.ActiveLayer = layerObj
    
    '<---------------------------------------------------------------------------------------------
Place_Info:
    
    If cbPoleDataOn.Value = False Then GoTo Place_Note
    
    str = "pole_info"
    strLayer = "Integrity Pole-Info"
    
    'counter = 4 + lbCompany.ListCount

    insertionPnt(0) = insertionPnt(0) - (74 * dScale)
    insertionPnt(1) = insertionPnt(1) - (12 * dScale)
    
    dPosition = 0#
    
    Dim vText, vLine As Variant
    Dim strText As String
    
    strText = Replace(tbPoleData.Value, vbLf, "")
    vText = Split(strText, vbCr)
    
    For w = 0 To UBound(vText)
        If vText(w) = "" Then GoTo Next_W
        vLine = Split(vText(w), vbTab)
    
        Set objBlock = ThisDrawing.ModelSpace.InsertBlock(insertionPnt, str, dScale, dScale, dScale, 0)
        objBlock.Layer = strLayer
        
        vAttList = objBlock.GetAttributes
        vAttList(0).TextString = strAtt0
        vAttList(1).TextString = dPosition
        vAttList(2).TextString = vLine(0)
        If UBound(vLine) = 1 Then vAttList(3).TextString = vLine(1)
        objBlock.Update
    
        insertionPnt(1) = insertionPnt(1) - (9 * dScale)
        dPosition = dPosition + 1
Next_W:
    Next w
    
    lwpPnt(0) = insertionPnt(0) - (4 * dScale)
    lwpPnt(1) = insertionPnt(1) + (7 * dScale)
    lwpPnt(2) = lwpPnt(0) + (100 * dScale)
    lwpPnt(3) = lwpPnt(1)
    
    Set lineObj = ThisDrawing.ModelSpace.AddLightWeightPolyline(lwpPnt)
    lineObj.Layer = strLayer
    lineObj.Update
    
Place_Note:
    
    If cbPWRNoteOn.Value = False Then GoTo Exit_Sub
    If cbNote.Value = "" Then GoTo Exit_Sub
    
    Select Case cbNote.Value
        Case "Power to replace with Taller Pole"
            str = "Notes-TallerPole5"
        Case "Power to replace Defective Pole"
            str = "Notes-DefectivePole"
        Case Else
            str = ""
    End Select
    
    If str = "" Then GoTo Exit_Sub
    
    dNote(0) = (dRevCloud(0) + dRevCloud(3)) / 2
    dNote(1) = dRevCloud(1) + 10
    dNote(2) = 0#
    
    'vLine = dNote
    Set objBlock = ThisDrawing.ModelSpace.InsertBlock(dNote, str, dScale, dScale, dScale, 0#)
    objBlock.Layer = strLayer
    objBlock.Update
    
Exit_Sub:
    Me.show
End Sub

Private Sub cbSaveData_Click()
    Call SaveAttachments
    iSave = 0
    
    If cbGetAttach.Enabled = False Then Me.Hide
End Sub

Private Sub cbSort_Click()
    Call SortList
End Sub

Private Sub cbUP_Click()
    Dim str0, str1, str2 As String
    Dim str3, str4, str5 As String
    Dim i, i2 As Integer
    
    If lbWorkspace.ListIndex < 1 Then Exit Sub
    i = lbWorkspace.ListIndex
    i2 = i - 1
    
    str0 = lbWorkspace.List(i, 0)
    str1 = lbWorkspace.List(i, 1)
    str2 = lbWorkspace.List(i, 2)
    str3 = lbWorkspace.List(i, 3)
    str4 = lbWorkspace.List(i, 4)
    str5 = lbWorkspace.List(i, 5)
    
    lbWorkspace.List(i, 0) = lbWorkspace.List(i2, 0)
    lbWorkspace.List(i, 1) = lbWorkspace.List(i2, 1)
    lbWorkspace.List(i, 2) = lbWorkspace.List(i2, 2)
    lbWorkspace.List(i, 3) = lbWorkspace.List(i2, 3)
    lbWorkspace.List(i, 4) = lbWorkspace.List(i2, 4)
    lbWorkspace.List(i, 5) = lbWorkspace.List(i2, 5)
    
    lbWorkspace.List(i2, 0) = str0
    lbWorkspace.List(i2, 1) = str1
    lbWorkspace.List(i2, 2) = str2
    lbWorkspace.List(i2, 3) = str3
    lbWorkspace.List(i2, 4) = str4
    lbWorkspace.List(i2, 5) = str5
    
    lbWorkspace.ListIndex = i2
End Sub

Private Sub cbUpdate_Click()
    If iSave = 1 Then
        result = MsgBox("Save changes to Pole Attachments?", vbYesNo, "Save Changes")
        If result = vbYes Then
            Call SaveAttachments
            iSave = 0
        End If
    End If
    
    Me.Hide
End Sub

Private Sub cbUpdateAttach_Click()
    Dim objSS3 As AcadSelectionSet
    Dim entBlock As AcadEntity
    Dim obrBlock As AcadBlockReference
    Dim obrAttach2 As AcadBlockReference
    Dim attList As Variant
    Dim vArray As Variant
    Dim str, str1 As String
    Dim strCompany, strExist As String
    Dim strProposed, strNote As String
    Dim strLayer  As String
    Dim dTest, dScale As Double
    Dim dCoords(0 To 2) As Double
    Dim insertionPnt(0 To 2) As Double
    Dim iEI, iPI, iDiff As Integer
    
    Me.Hide
    
    dTest = 2#
    dCoords(0) = 0#
    dCoords(1) = 0#
    
  On Error Resume Next
    Set objSS3 = ThisDrawing.SelectionSets.Add("objSS3")
    objSS3.SelectOnScreen
    For Each entBlock In objSS3
        If TypeOf entBlock Is AcadBlockReference Then
            Set obrBlock = entBlock
            If obrBlock.Name = "pole_attach" Then
                Select Case dCoords(1)
                    Case Is = 0, Is < obrBlock.InsertionPoint(1)
                        dCoords(0) = obrBlock.InsertionPoint(0)
                        dCoords(1) = obrBlock.InsertionPoint(1)
                        dCoords(2) = obrBlock.InsertionPoint(2)
                        
                        dScale = obrBlock.XScaleFactor
                End Select
                
                'entBlock.Delete
            End If
        End If
    Next entBlock
    
'    objSS3.Clear
    objSS3.Erase    '<--------------------------------------------------------------------------------------------------------------
    objSS3.Delete
    
    Me.Hide
    
    insertionPnt(0) = dCoords(0)
    insertionPnt(1) = dCoords(1)
    insertionPnt(2) = dCoords(2)
    
    str = "pole_attach"
    For i = 0 To (lbWorkspace.ListCount - 1)
        strCompany = lbWorkspace.List(i, 1)
        strExist = lbWorkspace.List(i, 2)
        strProposed = lbWorkspace.List(i, 3)
        
        If strExist = "" Then
            iEI = 0
        Else
            vArray = Split(strExist, "-")
            iEI = CInt(vArray(0)) * 12 + CInt(vArray(1))
        End If
        
        If strProposed = "" Then
            iPI = 0
        Else
            vArray = Split(strProposed, "-")
            iPI = CInt(vArray(0)) * 12 + CInt(vArray(1))
        End If
        
        iDiff = iPI - iEI
        
        strExist = Replace(strExist, "-", "'")
        strExist = strExist & """"
        
        strProposed = Replace(strProposed, "-", "'")
        strProposed = strProposed & """"
        
        Select Case iDiff
            Case Is = 0
                strNote = "TRANSFER"
                str1 = strProposed
                strLayer = "Integrity Attachments-MR"
            Case Is > 0
                If iEI > 0 Then
                    strNote = "RAISE " & Abs(iDiff) & """"
                    str1 = strProposed
                    strLayer = "Integrity Attachments-MR"
                Else
                    strNote = "NEW"
                    str1 = strProposed
                    strLayer = "Integrity Attachments-New"
                End If
            Case Is < 0
                If iPI > 0 Then
                    strNote = "LOWER " & Abs(iDiff) & """"
                    str1 = strProposed
                    strLayer = "Integrity Attachments-MR"
                Else
                    strNote = ""
                    str1 = strExist
                    strLayer = "Integrity Attachments-Existing"
                End If
        End Select
        
        'MsgBox tbUnitedPole.Value & vbCr & dPosition + (i / 100) & vbCr & strCompany & vbCr & str1 & vbCr & strNote
        
        Set obrAttach2 = ThisDrawing.ModelSpace.InsertBlock(insertionPnt, str, dScale, dScale, dScale, 0)
        obrAttach2.Layer = strLayer
        
        attList = obrAttach2.GetAttributes
        attList(0).TextString = tbUnitedPole.Value
        attList(1).TextString = dPosition + (i / 100)
        attList(2).TextString = strCompany
        attList(3).TextString = str1
        attList(4).TextString = strNote
        obrAttach2.Update
        
        insertionPnt(1) = insertionPnt(1) - (9 * dScale)
    Next i
    
    cbUpdateAttach.Enabled = False
    
    lbWorkspace.Clear
    
    If Not Err = 0 Then MsgBox "Error: " & Err.Number & vbCr & Err.Description
    
    Me.show
End Sub

Private Sub cbUpdateCLR_Click()
    If lbMR.ListIndex < 0 Then Exit Sub
    
    Dim objEntity As AcadEntity
    Dim objCLR As AcadBlockReference
    Dim vAttList, vReturnPnt As Variant
    Dim iIndex As Integer
    
    iIndex = lbMR.ListIndex
    
    Me.Hide
    
    Err = 0
    ThisDrawing.Utility.GetEntity objEntity, vReturnPnt, "Select Cable Span: "
    If Not Err = 0 Then GoTo Exit_Sub
    
    If Not TypeOf objEntity Is AcadBlockReference Then GoTo Exit_Sub
    Set objCLR = objEntity
    vAttList = objCLR.GetAttributes
    
    If lbMR.List(iIndex, 6) = "" Then
        vAttList(0).TextString = lbMR.List(iIndex, 5)
    Else
        vAttList(0).TextString = "(" & lbMR.List(iIndex, 5) & ")" & lbMR.List(iIndex, 6)
    End If
    
    objCLR.Update
Exit_Sub:
    
End Sub

Private Sub cbUpdateLine_Click()
    Dim vAttach As Variant
    Dim strNote, strTemp As String
    Dim iCurrentIn, iLowIn, iUpperIn As Integer
    Dim iNewFt, iNewIn, iDiff As Integer
    Dim iTempFt, iTempIn As Integer
    
    If Not tbExisting.Value = "" Then
        vAttach = Split(tbExisting.Value, "-")
        If UBound(vAttach) = 0 Then tbExisting.Value = tbExisting.Value & "-0"
    End If
    
    If Not tbProposed.Value = "" Then
        vAttach = Split(tbProposed.Value, "-")
        If UBound(vAttach) = 0 Then tbExisting.Value = tbExisting.Value & "-0"
    End If
    
    lbWorkspace.List(iListIndex, 0) = tbType.Value
    lbWorkspace.List(iListIndex, 1) = tbCompany.Value
    lbWorkspace.List(iListIndex, 2) = tbExisting.Value
    lbWorkspace.List(iListIndex, 3) = tbProposed.Value
    lbWorkspace.List(iListIndex, 4) = tbNotes.Value
    
    CheckForViolations (iListIndex)
    
    tbType.Value = ""
    tbCompany.Value = ""
    tbExisting.Value = ""
    tbProposed.Value = ""
    tbNotes.Value = ""
    
    cbUpdateLine.Enabled = False
    
    If iListIndex = (lbWorkspace.ListCount - 1) Then Call CheckRoadCLR
    iSave = 1
End Sub

Private Sub L24_Click()
    If L24.Caption = "xx-xx" Then Exit Sub
    
    If cbUpdateLine.Enabled = True Then
        If tbType.Value = "NEW" Then tbProposed.Value = L24.Caption
        cbUpdateLine.SetFocus
        Exit Sub
    End If
    
    Dim iIndex As Integer
    
    lbWorkspace.AddItem "NEW"
    iIndex = lbWorkspace.ListCount - 1
    lbWorkspace.List(iIndex, 1) = "NEW 6M"
    lbWorkspace.List(iIndex, 3) = L24.Caption
    
    Call SortList
    iSave = 1
End Sub

Private Sub Label83_Click()
    Dim vFirstPnt, vSecondPnt As Variant
    Dim dX, dY, dZ As Double
    
    Me.Hide
    
    vFirstPnt = ThisDrawing.Utility.GetPoint(, "Select First Point: ")
    vSecondPnt = ThisDrawing.Utility.GetPoint(, "Select Second Point: ")
    
    dX = vSecondPnt(0) - vFirstPnt(0)
    dY = vSecondPnt(1) - vFirstPnt(1)
    
    dZ = Sqr(dX * dX + dY * dY)
    tbDist.Value = CInt(dZ)
    
    Me.show
End Sub

Private Sub lbMR_DblClick(ByVal Cancel As MSForms.ReturnBoolean)
    On Error GoTo Exit_Sub
    
    Dim i As Integer
    Dim vTemp As Variant
    
    i = lbMR.ListIndex
    
    tbMRCompany.Value = lbMR.List(i, 0)
    tbMR.Value = lbMR.List(i, 1)
    cbType.Value = lbMR.List(i, 2)
    tbSpan.Value = lbMR.List(i, 3)
    tbDist.Value = lbMR.List(i, 4)
    
    If Not lbMR.List(i, 5) = "" Then
        vTemp = Split(lbMR.List(i, 5), "-")
        tbEF.Value = vTemp(0)
        If UBound(vTemp) > 0 Then tbEI.Value = vTemp(1)
    End If
    
    If Not lbMR.List(i, 6) = "" Then
        vTemp = Split(lbMR.List(i, 6), "-")
        tbPF.Value = vTemp(0)
        If UBound(vTemp) > 0 Then tbPI.Value = vTemp(1)
    End If
    cbAddCLR.Caption = "Update"
    
Exit_Sub:
End Sub

Private Sub lbMR_KeyDown(ByVal KeyCode As MSForms.ReturnInteger, ByVal Shift As Integer)
    Select Case KeyCode
        Case vbKeyDelete
            lbMR.RemoveItem lbMR.ListIndex
    End Select
End Sub

Private Sub lbWorkspace_DblClick(ByVal Cancel As MSForms.ReturnBoolean)
    iListIndex = lbWorkspace.ListIndex
    
    tbType.Value = lbWorkspace.List(iListIndex, 0)
    tbCompany.Value = lbWorkspace.List(iListIndex, 1)
    tbExisting.Value = lbWorkspace.List(iListIndex, 2)
    tbProposed.Value = lbWorkspace.List(iListIndex, 3)
    tbNotes.Value = lbWorkspace.List(iListIndex, 4)
    
    cbUpdateLine.Enabled = True
    tbType.Enabled = False
    tbCompany.Enabled = False
    tbExisting.Enabled = False
    tbNotes.Enabled = False
    
    tbProposed.SetFocus
    tbProposed.SelStart = 0
    tbProposed.SelLength = Len(tbProposed.Value)
End Sub

Private Sub Lcomm1_Click()
    If Lcomm1.Caption = "xx-xx" Then Exit Sub
    
    If cbUpdateLine.Enabled = True Then
        If tbType.Value = "NEW" Then tbProposed.Value = Lcomm1.Caption
        cbUpdateLine.SetFocus
        Exit Sub
    End If
    
    Dim iIndex As Integer
    
    lbWorkspace.AddItem "NEW"
    iIndex = lbWorkspace.ListCount - 1
    lbWorkspace.List(iIndex, 1) = "NEW 6M"
    lbWorkspace.List(iIndex, 3) = Lcomm1.Caption
    
    Call SortList
    iSave = 1
End Sub

Private Sub Lcomm2_Click()
    If Lcomm2.Caption = "xx-xx" Then Exit Sub
    
    If cbUpdateLine.Enabled = True Then
        If tbType.Value = "NEW" Then tbProposed.Value = Lcomm2.Caption
        cbUpdateLine.SetFocus
        Exit Sub
    End If
    
    Dim iIndex As Integer
    
    lbWorkspace.AddItem "NEW"
    iIndex = lbWorkspace.ListCount - 1
    lbWorkspace.List(iIndex, 1) = "NEW 6M"
    lbWorkspace.List(iIndex, 3) = Lcomm2.Caption
    
    Call SortList
    iSave = 1
End Sub

Private Sub LMaxHeight_Click()
    If LMaxHeight.Caption = "xx-xx" Then Exit Sub
    
    If cbUpdateLine.Enabled = True Then
        If tbType.Value = "NEW" Then tbProposed.Value = LMaxHeight.Caption
        cbUpdateLine.SetFocus
        Exit Sub
    End If
    
    Dim iIndex As Integer
    
    lbWorkspace.AddItem "NEW"
    iIndex = lbWorkspace.ListCount - 1
    lbWorkspace.List(iIndex, 1) = "NEW 6M"
    lbWorkspace.List(iIndex, 3) = LMaxHeight.Caption
    
    Call SortList
    iSave = 1
End Sub

Private Sub lUnlock_Click()
    tbType.Enabled = True
    tbCompany.Enabled = True
    tbExisting.Enabled = True
    tbNotes.Enabled = True

End Sub

Private Sub tbBC_Change()
    If tbBC.Value = "" Then Exit Sub
    
    For i = 0 To lbWorkspace.ListCount - 1
        'If lbWorkspace.List(i, 0) = "COMM" Then
            CheckForViolations (i)
        'End If
    Next i
End Sub

Private Sub tbBSC_Change()
    If tbBSC.Value = "" Then Exit Sub
    
    For i = 0 To lbWorkspace.ListCount - 1
        'If lbWorkspace.List(i, 0) = "COMM" Then
            CheckForViolations (i)
        'End If
    Next i
End Sub

Private Sub tbCompany_DblClick(ByVal Cancel As MSForms.ReturnBoolean)
    tbExisting.Enabled = True
End Sub

Private Sub tbLL_MouseDown(ByVal Button As Integer, ByVal Shift As Integer, ByVal X As Single, ByVal Y As Single)
    tbLL.SelStart = 0
    tbLL.SelLength = Len(tbLL.Value)
End Sub

Private Sub tbProposed_DblClick(ByVal Cancel As MSForms.ReturnBoolean)
    tbNotes.Enabled = True
End Sub

Private Sub tbSP_Change()
    If tbSP.Value = "" Then Exit Sub
    
    For i = 0 To lbWorkspace.ListCount - 1
        'If lbWorkspace.List(i, 0) = "PWR" Then
            CheckForViolations (i)
        'End If
    Next i
End Sub

Private Sub tbSS_Change()
    If tbSS.Value = "" Then Exit Sub
    
    For i = 0 To lbWorkspace.ListCount - 1
        'If lbWorkspace.List(i, 0) = "PWR" Then
            CheckForViolations (i)
        'End If
    Next i
End Sub

Private Sub tbST_Change()
    If tbST.Value = "" Then Exit Sub
    
    For i = 0 To lbWorkspace.ListCount - 1
        'If lbWorkspace.List(i, 0) = "PWR" Then
            CheckForViolations (i)
        'End If
    Next i
End Sub

Private Sub UserForm_Initialize()
    cbUP.Caption = Chr(225)
    cbDOWN.Caption = Chr(226)
    
    cbNote.AddItem ""
    cbNote.AddItem "Pwr replace with 5 Taller Pole"
    cbNote.AddItem "Pwr replace with 10 Taller Pole"
    cbNote.AddItem "Pwr replace Defective Pole"
    cbNote.AddItem "Pwr Raise Attachment"
    cbNote.AddItem "Extra Seperation"
    cbNote.AddItem "Use Existing Holes"
    cbNote.AddItem "Pole Permited Previously"
    cbNote.AddItem "OCALC Required"
    cbNote.AddItem "Replace Note with Other"
    'cbNote.AddItem "Power to replace with Thicker Pole"
    'cbNote.AddItem "Power to replace with Like Pole"
    'cbNote.AddItem "pole permitted"
    'cbNote.AddItem "replace pole"
    'cbNote.AddItem "assumes completion"
    'cbNote.AddItem "same bolt"
    'cbNote.AddItem "future same bolt"
    'cbNote.AddItem "dist stops"
    'cbNote.AddItem "fdh ground"
    'cbNote.AddItem "fdh ground wire"
    'cbNote.AddItem "additional seperation"
    'cbNote.AddItem "cant lower replace pole"
    'cbNote.AddItem "cant lower determine"
    'cbNote.Value = ""
    
    cbType.AddItem ""
    cbType.AddItem "RD"
    cbType.AddItem "DW"
    cbType.AddItem "MS"
    
    cbAlign.AddItem "Align"
    cbAlign.AddItem "Leader"
    cbAlign.Value = "Align"
    
    cbCalloutType.AddItem "(Existing)Proposed"
    cbCalloutType.AddItem "Proposed  MR-Note"
    cbCalloutType.Value = "Proposed  MR-Note"
    
    tbType.AddItem "PWR"
    tbType.AddItem "NEW"
    tbType.AddItem "COMM"
    
    lbWorkspace.Clear
    lbWorkspace.ColumnCount = 6
    lbWorkspace.ColumnWidths = "48;72;48;48;96;72"
    
    lbMR.Clear
    lbMR.ColumnCount = 7
    lbMR.ColumnWidths = "48;34;48;48;48;48;48"
    
    If Not lbWorkspace.ListCount = 0 Then
        For i = 0 To lbWorkspace.ListCount - 1
            CheckForViolations (i)
        Next i
    End If
    
    iListIndex = 0
    iSave = 0
    iChanged = 0
End Sub

Private Sub CheckForViolations(iIndex As Integer)
    Dim vAttach, vTemp, vLine As Variant
    Dim iCurrentFt, iCurrentIn As Integer
    Dim iLowFt, iLowIn As Integer
    Dim iUpperFt, iUpperIn As Integer
    Dim iNewFt, iNewIn As Integer
    Dim iDiff As Integer
    Dim strType, strCompany, strNote As String
    
    strType = lbWorkspace.List(iIndex, 0)
    strCompany = lbWorkspace.List(iIndex, 1)
    
    If Not lbWorkspace.List(iIndex, 3) = "" Then
        vAttach = Split(lbWorkspace.List(iIndex, 3), "-")
    Else
        vAttach = Split(lbWorkspace.List(iIndex, 2), "-")
    End If
            
    iCurrentIn = CInt(vAttach(0)) * 12 + CInt(vAttach(1))
            
    Select Case strType
        Case "PWR"
            Select Case strCompany
                Case "LOW POWER", "NEUTRAL", "ST LT CIR"
                    iLowIn = iCurrentIn - CInt(tbSP.Value)
                Case "TRANSFORMER"
                    iLowIn = iCurrentIn - CInt(tbST.Value)
                Case "ST LT"
                    iLowIn = iCurrentIn - CInt(tbSS.Value)
            End Select
            
            iNewFt = CInt(iLowIn / 12 - 0.5)
            iNewIn = iLowIn - (iNewFt * 12)
            If iNewIn > 11 Then
                iNewIn = iNewIn - 12
                iNewFt = iNewFt + 1
            End If
            
            strNote = "MAX: " & iNewFt & "-" & iNewIn
            lbWorkspace.List(iIndex, 4) = strNote
            
            For c = iIndex To lbWorkspace.ListCount - 1
                If lbWorkspace.List(c, 0) = "NEW" Then
                    If Not lbWorkspace.List(c, 3) = "" Then
                        vAttach = Split(lbWorkspace.List(c, 3), "-")
                    Else
                        vAttach = Split(lbWorkspace.List(c, 2), "-")
                    End If
                    iUpperIn = CInt(vAttach(0)) * 12 + CInt(vAttach(1))

                    If iLowIn - iUpperIn < 0 Then
                        lbWorkspace.List(c, 5) = "PWR"
                    Else
                        lbWorkspace.List(c, 5) = ""
                    End If
                End If
            Next c
        Case "NEW"
            lbWorkspace.List(iIndex, 5) = ""
            For g = 0 To iIndex + 1
                If g = iIndex Then GoTo Next_G
                If g > lbWorkspace.ListCount - 1 Then GoTo Next_G
                
                lbWorkspace.List(g, 3) = Replace(lbWorkspace.List(g, 3), " ", "")
                If Not lbWorkspace.List(g, 3) = "" Then
                    vAttach = Split(lbWorkspace.List(g, 3), "-")
                Else
                    vAttach = Split(lbWorkspace.List(g, 2), "-")
                End If
                'vAttach = Split(lbWorkspace.List(g, 4), " ")
                'vTemp = Split(vAttach(1), "-")
                'iUpperIn = CInt(vTemp(0)) * 12
                'If UBound(vTemp) > 0 Then iUpperIn = iUpperIn + CInt(vTemp(1))
                iUpperIn = CInt(vAttach(0)) * 12
                If UBound(vAttach) > 0 Then iUpperIn = iUpperIn + CInt(vAttach(1))
                
                If lbWorkspace.List(g, 0) = "PWR" Then
                    If iUpperIn - iCurrentIn < 0 Then
                        lbWorkspace.List(iIndex, 5) = "PWR"
                    End If
                Else
                    If iUpperIn - iCurrentIn > 0 Then
                        lbWorkspace.List(iIndex, 5) = lbWorkspace.List(iIndex, 5) & "  COMM"
                    End If
                End If
Next_G:
            Next g
        Case "COMM"
            If Not lbWorkspace.List(iIndex - 1, 3) = "" Then
                vAttach = Split(lbWorkspace.List(iIndex - 1, 3), "-")
            Else
                vAttach = Split(lbWorkspace.List(iIndex - 1, 2), "-")
            End If
            
            '<---------------------------------------------------------------Upper Attachment
            iUpperIn = CInt(vAttach(0)) * 12 + CInt(vAttach(1))
            iDiff = iUpperIn - iCurrentIn
            
            strNote = "SEP: " & Abs(iDiff)
            Select Case lbWorkspace.List(iIndex - 1, 1)
                Case tbCompany.Value
                    If iDiff < CInt(tbBSC.Value) Then
                        lbWorkspace.List(iIndex, 5) = "SEPERATION"
                    Else
                        lbWorkspace.List(iIndex, 5) = ""
                    End If
                Case "UTC NEW"
                    iTempIn = iCurrentIn + CInt(tbBC.Value)
                    iTempFt = CInt(iTempIn / 12 - 0.5)
                    iTempIn = iTempIn - (iTempFt * 12)
                    If iTempIn > 11 Then
                        iTempFt = iTempFt + 1
                        iTempIn = iTempIn - 12
                    End If

                    If iDiff < CInt(tbBC.Value) Then
                        lbWorkspace.List(iIndex, 5) = "SEPERATION"
                    Else
                        lbWorkspace.List(iIndex, 5) = ""
                    End If

                    strNote = "MIN: " & iTempFt & "-" & iTempIn
                Case Else
                    If iDiff < CInt(tbBC.Value) Then
                        lbWorkspace.List(iIndex, 5) = "SEPERATION"
                    Else
                        lbWorkspace.List(iIndex, 5) = ""
                    End If
            End Select
            
            lbWorkspace.List(iIndex, 5) = strNote
            
            '<---------------------------------------------------------------Lower Attachment
            If iIndex = lbWorkspace.ListCount - 1 Then GoTo Skip_Lower
            If Not lbWorkspace.List(iIndex + 1, 3) = "" Then
                vAttach = Split(lbWorkspace.List(iIndex + 1, 3), "-")
            Else
                vAttach = Split(lbWorkspace.List(iIndex + 1, 2), "-")
            End If
            
            iLowIn = CInt(vAttach(0)) * 12 + CInt(vAttach(1))
            iDiff = iCurrentIn - iLowIn
            
            strNote = "SEP: " & Abs(iDiff)
            
            If tbCompany.Value = lbWorkspace.List(iIndex + 1, 1) Then
                If iDiff < CInt(tbBSC.Value) Then
                    lbWorkspace.List(iIndex + 1, 5) = "SEPERATION"
                Else
                    lbWorkspace.List(iIndex + 1, 5) = ""
                End If
            Else
                If iDiff < CInt(tbBC.Value) Then
                    lbWorkspace.List(iIndex + 1, 5) = "SEPERATION"
                Else
                    lbWorkspace.List(iIndex + 1, 5) = ""
                End If
            End If
            lbWorkspace.List(iIndex + 1, 5) = strNote
            
Skip_Lower:
            'strTemp = lbWorkspace.List(iIndex - 1, 2) '= tbExisting.Value
    End Select
End Sub

Public Sub SortList()
    Dim strArrayList(), strArraySorted(), strData() As String
    Dim strListItem() As String     '<---------------------------------------------Sort
    Dim attArray, attItem, vTemp As Variant
    Dim vNotes As Variant
    Dim str1, str2 As String
    Dim i, iDWGNum, test1, place1, temp1 As Integer
    Dim iOCALC As Integer
    Dim strTemp As String
    Dim iFeet, iInch As Integer
    Dim tempFt, tempIn As Integer
    Dim iMaxIn, iMinIn, iTInch As Integer
    Dim iMaxFt, iMinFt As Integer
    Dim iCD As Integer
    
  'On Error Resume Next
    
    test1 = 0
    iOCALC = 0
    iCD = 0
    'ReDim strArrayList(0 To lbAttachments.ListCount)
    If lbWorkspace.ListCount < 1 Then Exit Sub
    ReDim strData(0 To lbWorkspace.ListCount - 1)
    ReDim strListItem(0 To lbWorkspace.ListCount - 1)
    ReDim strArraySorted(0 To lbWorkspace.ListCount - 1)
    
    For i = 0 To UBound(strListItem)
        strListItem(i) = i
    Next i
    
    For i = 0 To UBound(strData)
        If Not lbWorkspace.List(i, 3) = "" Then
            vTemp = Split(lbWorkspace.List(i, 3), "-")
            iInch = CInt(vTemp(0)) * 12 + CInt(vTemp(1))
        Else
            vTemp = Split(lbWorkspace.List(i, 2), "-")
            iInch = CInt(vTemp(0)) * 12 + CInt(vTemp(1))
        End If
        
        strData(i) = iInch
    Next i
    
    test1 = UBound(strData) - 1

    For i = UBound(strData) To (LBound(strData) + 1) Step -1
        For j = LBound(strData) To (i - 1)
            If CInt(strData(j)) < CInt(strData(j + 1)) Then
                temp1 = strData(j + 1)
                strData(j + 1) = strData(j)
                strData(j) = temp1
                
                strTemp = strListItem(j + 1)
                strListItem(j + 1) = strListItem(j)
                strListItem(j) = strTemp
            End If
        Next j
    Next i
    
    For i = LBound(strListItem) To UBound(strListItem)
        strArraySorted(i) = lbWorkspace.List(strListItem(i), 0) & vbTab & lbWorkspace.List(strListItem(i), 1) & vbTab
        strArraySorted(i) = strArraySorted(i) & lbWorkspace.List(strListItem(i), 2) & vbTab & lbWorkspace.List(strListItem(i), 3) & vbTab
        strArraySorted(i) = strArraySorted(i) & lbWorkspace.List(strListItem(i), 4) & vbTab & lbWorkspace.List(strListItem(i), 5) & vbTab
    Next i
    
    iMaxIn = 840
    iMinIn = 0
    
    lbWorkspace.Clear
    For i = LBound(strListItem) To UBound(strListItem)
        lbWorkspace.AddItem
        attItem = Split(strArraySorted(i), vbTab)
        lbWorkspace.List(i, 0) = attItem(0)
        lbWorkspace.List(i, 1) = attItem(1)
        lbWorkspace.List(i, 2) = attItem(2)
        lbWorkspace.List(i, 3) = attItem(3)
        lbWorkspace.List(i, 4) = attItem(4)
        lbWorkspace.List(i, 5) = attItem(5)
        
        If attItem(3) = "" Then
            vTemp = Split(attItem(2), "-")
            tempFt = CInt(vTemp(0))
            tempIn = CInt(vTemp(1))
        Else
            vTemp = Split(attItem(3), "-")
            tempFt = CInt(vTemp(0))
            tempIn = CInt(vTemp(1))
        End If
        
        Select Case attItem(1)
            Case "NEUTRAL"
                If tempIn < 4 Then
                    tempIn = tempIn + 12
                    tempFt = tempFt - 1
                End If
                tempFt = tempFt - 3
                tempIn = tempIn - 4
                iTInch = tempFt * 12 + tempIn
            
                If iTInch < iMaxIn Then
                    iMaxIn = iTInch
                End If
                
                lbWorkspace.List(i, 5) = "MAX: " & tempFt & "-" & tempIn
            Case "LOW POWER", "ST LT CIRCUIT"
                If tempIn < 4 Then
                    tempIn = tempIn + 12
                    tempFt = tempFt - 1
                End If
                tempFt = tempFt - 3
                tempIn = tempIn - 4
                iTInch = tempFt * 12 + tempIn
            
                If iTInch < iMaxIn Then
                    iMaxIn = iTInch
                End If
                
                lbWorkspace.List(i, 5) = "MAX: " & tempFt & "-" & tempIn
            Case "TRANSFORMER"
                If tempIn < 6 Then
                    tempIn = tempIn + 12
                    tempFt = tempFt - 1
                End If
                tempFt = tempFt - 2
                tempIn = tempIn - 6
                iTInch = tempFt * 12 + tempIn
            
                If iTInch < iMaxIn Then
                    iMaxIn = iTInch
                End If
                
                lbWorkspace.List(i, 5) = "MAX: " & tempFt & "-" & tempIn
            Case "ST LT"
                tempFt = tempFt - 1
                iTInch = tempFt * 12 + tempIn
            
                If iTInch < iMaxIn Then
                    iMaxIn = iTInch
                End If
                
                lbWorkspace.List(i, 5) = "MAX: " & tempFt & "-" & tempIn
            Case "NEW 6M"
                iOCALC = iOCALC + 1
            Case Else
                iTInch = tempFt * 12 + tempIn
                If iTInch > iMinIn Then iMinIn = iTInch
                
                iOCALC = iOCALC + 1
                If InStr(lbWorkspace.List(i, 1), "C-WIRE") > 0 Then
                    iOCALC = iOCALC - 1
                    iCD = 1
                End If
                If InStr(lbWorkspace.List(i, 1), "DROP") > 0 Then
                    iOCALC = iOCALC - 1
                    iCD = 1
                End If
        End Select
    Next i
    
    If iMaxIn < 288 Then L24.Enabled = False
    If iMaxIn < (iMinIn + 12) Then Lcomm1.Enabled = False
    If iMaxIn < (iMinIn + 24) Then Lcomm2.Enabled = False
    
    iMaxFt = Int(iMaxIn / 12)
    iMaxIn = iMaxIn - (iMaxFt * 12)
    
    LMaxHeight.Caption = iMaxFt & "-" & iMaxIn
    
    iMinFt = Int(iMinIn / 12)
    iMinIn = iMinIn - (iMinFt * 12)
    iMinFt = iMinFt + 1
    
    Lcomm1.Caption = iMinFt & "-" & iMinIn
    
    iMinFt = iMinFt + 1
    
    Lcomm2.Caption = iMinFt & "-" & iMinIn
    
    iOCALC = iOCALC + iCD
    
    If iOCALC > 3 Then
        vNotes = Split(tbPoleData.Value, vbCr)
        vTemp = Split(Replace(vNotes(1), vbLf, ""), vbTab)
        
        Select Case vTemp(0)
            Case "MTE", "MTEMC", "DRE", "DREMC", "SWPS"
                If InStr(tbNoteList.Value, "OCALC") < 1 Then
                    If tbNoteList.Value = "" Then
                        tbNoteList.Value = "OCALC"
                    Else
                        tbNoteList.Value = tbNoteList.Value & vbCr & "OCALC"
                    End If
                End If
        End Select
    End If
End Sub

Private Sub CheckRoadCLR()
    Dim vLine, vHeight, vTemp As Variant
    Dim strLine As String
    Dim strPoleAtt, strTestAtt As String
    Dim dSpan, dDist, dMR As Double
    Dim iPoleFeet, iPoleInch, iPoleMR As Integer
    Dim iCLRFeet, iCLRInch, iCLRMR As Integer
    Dim iTestFeet, iTestInch, iTestMR As Integer
    Dim iTest As Integer
    Dim lColor As Long
    Dim strCompany, strExist As String
    Dim strNote As String
    Dim vList As Variant
    Dim iEI, iPI, iDiff As Integer
    
    On Error Resume Next
    
    strCompany = lbWorkspace.List(lbWorkspace.ListCount - 1, 1)
    strExist = lbWorkspace.List(lbWorkspace.ListCount - 1, 2)
    strProposed = lbWorkspace.List(lbWorkspace.ListCount - 1, 3)
    
    If strExist = "" Then Exit Sub
    If strProposed = "" Then
        If lbMR.ListCount > 0 Then
            For i = 0 To lbMR.ListCount - 1
                lbMR.List(i, 6) = ""
            Next i
        End If
        Exit Sub
    End If
    
    vList = Split(strExist, "-")
    iEI = CInt(vList(0)) * 12 + CInt(vList(1))
    
    vList = Split(strProposed, "-")
    iPI = CInt(vList(0)) * 12 + CInt(vList(1))
    
    iPoleMR = iPI - iEI
    
    For i = 0 To lbMR.ListCount - 1
        iTestMR = lbMR.List(i, 1)
        
        vLine = Split(lbMR.List(i, 5), "-")
        iCLRFeet = CInt(vLine(0))
        iCLRInch = iCLRFeet * 12 + CInt(vLine(1))
    
        iTest = iTestMR - iPoleMR
    
        dSpan = CDbl(lbMR.List(i, 3))
        dDist = CDbl(lbMR.List(i, 4))
        dMR = dDist / dSpan
    
        iCLRInch = iCLRInch + iPoleMR + Round(iTest * dMR)
        iCLRFeet = 0
    
        Do While iCLRInch > 12
            iCLRInch = iCLRInch - 12
            iCLRFeet = iCLRFeet + 1
        Loop
    
        Do While iCLRInch < 0
            iCLRInch = iCLRInch + 12
            iCLRFeet = iCLRFeet - 1
        Loop
    
        lbMR.List(i, 6) = iCLRFeet & "-" & iCLRInch
    Next i
End Sub

Private Sub PlaceCLR()
    Dim str1, str2 As String
    Dim dScale As Double
    Dim xDiff, yDiff As Double
    Dim obrBR As AcadBlockReference
    Dim returnPnt, returnPnt2 As Variant
    Dim varItem, vTemp As Variant
    Dim layerObj As AcadLayer
    
    dScale = CInt(cbScale.Value) / 100 * 1.333333
    dRotate = 0
    
    vTemp = Split(tbPreAttach.Value, vbTab)
    
    
    str1 = vTemp(0) & " " & cbPreType.Value & " CLR"
    str2 = tbPreEF.Value & "'"
    If Not tbPreEI.Value = "" Then str2 = str2 & tbPreEI.Value & """"
    If Not tbPrePF.Value = "" Then
        str2 = "(" & str2 & ") " & tbPrePF.Value & "'"
        If Not tbPrePI.Value = "" Then str2 = str2 & tbPrePI.Value & """"
    End If
    
    Me.Hide
    
    If cbType.Value = "DW" Then
        Call AddDriveways
        GoTo Place_Block:
    End If
    
    returnPnt = ThisDrawing.Utility.GetPoint(, "Place Clearance: ")
    dInsertPnt(0) = returnPnt(0)
    dInsertPnt(1) = returnPnt(1)
    dInsertPnt(2) = 0#
    
    returnPnt2 = ThisDrawing.Utility.GetPoint(, "Rotation Direction: ")
    If dInsertPnt(0) > returnPnt2(0) Then
        xDiff = dInsertPnt(0) - returnPnt2(0)
        yDiff = dInsertPnt(1) - returnPnt2(1)
    Else
        xDiff = returnPnt2(0) - dInsertPnt(0)
        yDiff = returnPnt2(1) - dInsertPnt(1)
    End If
    If xDiff = 0 Then
        dRotate = 1.570796327
    Else
        dRotate = Atn(yDiff / xDiff)
    End If
    
Place_Block:
    
    Set obrBR = ThisDrawing.ModelSpace.InsertBlock(dInsertPnt, "clr", dScale, dScale, dScale, dRotate)
    obrBR.Layer = "Integrity Roads-Clearance"
    varItem = obrBR.GetAttributes
    varItem(0).TextString = str1
    varItem(1).TextString = str2
    obrBR.Update
    
    Me.show
Exit_Sub:
End Sub

Private Sub AddDriveways()
    Dim lineObj As AcadLWPolyline
    Dim insertPnt(0 To 2), leaderPnt(0 To 3) As Double
    Dim dScale As Double
    Dim returnPnt, returnPnt2, returnPnt3 As Variant
    Dim vEOPL As Variant
    Dim xDist, yDist, zDist, dRatio, dRatio2 As Double
    Dim dOffset As Double
    Dim iDirection As Integer 'L=-1 R=1
    
    'Me.hide
   On Error Resume Next
   
    dScale = 0.75
    'If Not Err = 0 Then dScale = 1
    
    returnPnt2 = ThisDrawing.Utility.GetPoint(, vbCr & "Start line: ")
    returnPnt = ThisDrawing.Utility.GetPoint(returnPnt2, vbCr & "End Line: ")
    'returnPnt3 = returnPnt
    
    xDist = returnPnt(0) - returnPnt2(0)
    yDist = returnPnt(1) - returnPnt2(1)
    zDist = Sqr((xDist * xDist) + (yDist * yDist))
    dRatio = (133 * dScale) / zDist
    dRatio2 = (100 * dScale) / zDist
    If xDist = 0 Then
        dRotate = 1.570796327
    Else
        dRotate = Atn(yDist / xDist)
    End If
'MsgBox dRotate
    
    leaderPnt(0) = returnPnt(0) - dRatio * xDist
    leaderPnt(1) = returnPnt(1) - dRatio * yDist
    leaderPnt(2) = returnPnt(0)
    leaderPnt(3) = returnPnt(1)
    dInsertPnt(0) = returnPnt(0) - dRatio2 * xDist
    dInsertPnt(1) = returnPnt(1) - dRatio2 * yDist
    dInsertPnt(2) = 0#
    
    Select Case xDist
        Case Is < 0
            iDirection = -1
            'dRotate = dRotate * (-1)
        Case Else
            iDirection = 1
    End Select
    
        
    Set lineObj = ThisDrawing.ModelSpace.AddLightWeightPolyline(leaderPnt)
    lineObj.Layer = "Integrity Roads-Clearance"
    
    vEOPL = lineObj.Offset(21.3333 * dScale * iDirection)
    lineObj.Update
End Sub

Private Sub RemoveEmptyRows()
    For i = lbMR.ListCount - 1 To 0 Step -1
        If lbMR.List(i, 0) = "" Then lbMR.RemoveItem i
    Next i
End Sub

Private Sub SaveAttachments()
    'If lbWorkspace.ListCount < 1 Then Exit Sub
    
    Dim strComm(8) As String
    Dim strComm1, strComm2, strComm3, strComm4 As String
    Dim strComm5, strComm6, strComm7, strComm8 As String
    Dim strLine, strExtra, strCO, strLetter As String
    Dim vAttList, vLine, vItem As Variant
    
    For i = 0 To 8
        strComm(i) = ""
    Next i
    
    strComm1 = "": strComm2 = "": strComm3 = "": strComm4 = ""
    strComm5 = "": strComm6 = "": strComm7 = "": strComm8 = ""
    
    vAttList = objPole.GetAttributes
    
    For i = 9 To 23
        vAttList(i).TextString = ""
    Next i
    
    For i = 0 To lbWorkspace.ListCount - 1
        Select Case lbWorkspace.List(i, 0)
            Case "PWR"
                Select Case lbWorkspace.List(i, 1)
                    Case "NEUTRAL"
                        strLine = lbWorkspace.List(i, 2)
                        If Not lbWorkspace.List(i, 3) = "" Then strLine = "(" & strLine & ")" & lbWorkspace.List(i, 3)
                        
                        If vAttList(9).TextString = "" Then
                            vAttList(9).TextString = strLine
                        Else
                            vAttList(9).TextString = vAttList(9).TextString & " " & strLine
                        End If
                    Case "TRANSFORMER"
                        strLine = lbWorkspace.List(i, 2)
                        If Not lbWorkspace.List(i, 3) = "" Then strLine = "(" & strLine & ")" & lbWorkspace.List(i, 3)
                        
                        If vAttList(10).TextString = "" Then
                            vAttList(10).TextString = strLine
                        Else
                            vAttList(10).TextString = vAttList(10).TextString & " " & strLine
                        End If
                    Case "LOW POWER"
                        strLine = lbWorkspace.List(i, 2)
                        If Not lbWorkspace.List(i, 3) = "" Then strLine = "(" & strLine & ")" & lbWorkspace.List(i, 3)
                        
                        If vAttList(11).TextString = "" Then
                            vAttList(11).TextString = strLine
                        Else
                            vAttList(11).TextString = vAttList(10).TextString & " " & strLine
                        End If
                    Case "ANTENNA"
                        strLine = lbWorkspace.List(i, 2)
                        If Not lbWorkspace.List(i, 3) = "" Then strLine = "(" & strLine & ")" & lbWorkspace.List(i, 3)
                        
                        If vAttList(12).TextString = "" Then
                            vAttList(12).TextString = strLine
                        Else
                            vAttList(12).TextString = vAttList(10).TextString & " " & strLine
                        End If
                    Case "ST LT CIRCUIT"
                        strLine = lbWorkspace.List(i, 2)
                        If Not lbWorkspace.List(i, 3) = "" Then strLine = "(" & strLine & ")" & lbWorkspace.List(i, 3)
                        
                        If vAttList(13).TextString = "" Then
                            vAttList(13).TextString = strLine
                        Else
                            vAttList(13).TextString = vAttList(10).TextString & " " & strLine
                        End If
                    Case "ST LT"
                        strLine = lbWorkspace.List(i, 2)
                        If Not lbWorkspace.List(i, 3) = "" Then strLine = "(" & strLine & ")" & lbWorkspace.List(i, 3)
                        
                        If vAttList(14).TextString = "" Then
                            vAttList(14).TextString = strLine
                        Else
                            vAttList(14).TextString = vAttList(10).TextString & " " & strLine
                        End If
                End Select
            Case "NEW"
                If vAttList(15).TextString = "" Then
                    vAttList(15).TextString = lbWorkspace.List(i, 3)
                Else
                    vAttList(15).TextString = vAttList(15).TextString & " " & lbWorkspace.List(i, 3)
                End If
                
                If lbWorkspace.List(i, 4) = "MTE TAG" Then vAttList(15).TextString = vAttList(15).TextString & "T"
                If lbWorkspace.List(i, 1) = "NEW OHG" Then vAttList(15).TextString = vAttList(15).TextString & "O"
                If lbWorkspace.List(i, 4) = "FUTURE" Then vAttList(15).TextString = vAttList(15).TextString & "F"
            Case "COMM"
                strCO = lbWorkspace.List(i, 1)
                If InStr(strCO, "C-WIRE") > 0 Then
                    strExtra = "c"
                    strCO = Replace(strCO, " C-WIRE", "")
                End If
                
                If InStr(strCO, "DROP") > 0 Then
                    strExtra = "d"
                    strCO = Replace(strCO, " DROP", "")
                End If
                
                If lbWorkspace.List(i, 1) = "EXTEND" Then
                    If strExtra = "" Then
                        strExtra = "e"
                    Else
                        strExtra = strExtra & "e"
                    End If
                End If
                
                If InStr(strCO, "OHG") > 0 Then
                    If strExtra = "" Then
                        strExtra = "o"
                    Else
                        strExtra = strExtra & "o"
                    End If
                    strCO = Replace(strCO, " OHG", "")
                End If
                
                If InStr(strCO, "LASH TO ") > 0 Then
                    If strExtra = "" Then
                        strExtra = "v"
                    Else
                        strExtra = strExtra & "v"
                    End If
                    strCO = Replace(strCO, "LASH TO ", "")
                End If
                
                If InStr(strCO, " TAP") > 0 Then
                    If strExtra = "" Then
                        strExtra = "p"
                    Else
                        strExtra = strExtra & "p"
                    End If
                    strCO = Replace(strCO, " TAP", "")
                End If
                
                If InStr(strCO, " SS") > 0 Then
                    If strExtra = "" Then
                        strExtra = "s"
                    Else
                        strExtra = strExtra & "s"
                    End If
                    strCO = Replace(strCO, " SS", "")
                End If
                
                If InStr(strCO, " TAG") > 0 Then
                    If strExtra = "" Then
                        strExtra = "t"
                    Else
                        strExtra = strExtra & "t"
                    End If
                    strCO = Replace(strCO, " TAG", "")
                End If
                
                If Not lbWorkspace.List(i, 2) = "" Then
                    strLine = lbWorkspace.List(i, 2)
                    
                    If Not lbWorkspace.List(i, 3) = "" Then
                        strLine = "(" & strLine & ")" & lbWorkspace.List(i, 3) & strExtra
                    Else
                        strLine = strLine & strExtra
                    End If
                    
                    strExtra = ""
                Else
                    strLine = lbWorkspace.List(i, 3) & strExtra & "x"
                    strExtra = ""
                End If
                
                For j = 1 To 8
                    vLine = Split(strComm(j), "=")
                    If strComm(j) = "" Then
                        strComm(j) = strCO & "=" & strLine
                        GoTo Found_strComm
                    End If
                    
                    If vLine(0) = strCO Then
                        strComm(j) = strComm(j) & " " & strLine
                        GoTo Found_strComm
                    End If
                Next j
                
                MsgBox "Comms full"
                Exit Sub
Found_strComm:
        End Select
    Next i
    
    For i = 1 To 8
        vAttList(15 + i).TextString = strComm(i)
    Next i
    
    If cbPoleDataOn.Value = False Then GoTo Add_Notes
    
    vAttList(2).TextString = ""
    vAttList(3).TextString = ""
    vAttList(4).TextString = ""
    vAttList(5).TextString = ""
    
    strLine = Replace(tbPoleData.Value, vbLf, "")
    vLine = Split(strLine, vbCr)
    
    vItem = Split(vLine(1), vbTab)
    strCO = vItem(0)
    vAttList(2).TextString = strCO
    vAttList(5).TextString = vItem(1)
    
    vItem = Split(vLine(2), vbTab)
    vAttList(3).TextString = vItem(1)
    
    For i = 3 To UBound(vLine)
        vItem = Split(vLine(i), vbTab)
        
        If UBound(vItem) = 0 Then GoTo Next_I
        
        If vItem(0) = strCO Then
            If vAttList(4).TextString = "" Then
                vAttList(4).TextString = vItem(1)
            Else
                vAttList(4).TextString = vAttList(4).TextString & " " & vItem(1)
            End If
        Else
            If vAttList(4).TextString = "" Then
                vAttList(4).TextString = vItem(0) & "=" & vItem(1)
            Else
                vAttList(4).TextString = vAttList(4).TextString & " " & vItem(0) & "=" & vItem(1)
            End If
        End If
Next_I:
    Next i
    
Add_Notes:
    
    If tbNoteList.Value = "" Then
        vAttList(24).TextString = ""
    Else
        strLine = Replace(tbNoteList.Value, vbLf, "")
        strLine = Replace(strLine, vbCr, ";")
        
        vAttList(24).TextString = strLine
    End If
    
Exit_Sub:
    objPole.Update
    
    iChanged = 1
End Sub

Public Sub GetPoleData()
    Dim vAttList As Variant
    Dim vAll, vLine, vCount As Variant
    Dim strLine, strCO, strTemp As String
    Dim iIndex As Integer
        
    vAttList = objPole.GetAttributes
    
    tbPoleNumber.Value = vAttList(0).TextString
    
    lbWorkspace.Clear
    lbMR.Clear
    tbPoleData.Value = ""
    
    cbNote.Value = ""
    
    If vAttList(1).TextString = "DEFECTIVE" Then cbNote.Value = "Power to replace Defective Pole"
    If vAttList(1).TextString = "REPLACE" Then cbNote.Value = "Power to replace Defective Pole"
    
    '<----------------------------------------------------------------------Pole Data
    
    strLine = vAttList(0).TextString
    strLine = strLine & vbCr & vAttList(2).TextString & vbTab & vAttList(5).TextString
    strLine = strLine & vbCr & vAttList(2).TextString & vbTab & vAttList(3).TextString
    
    If InStr(vAttList(5).TextString, ")") > 0 Then
        strTemp = Replace(vAttList(5).TextString, "(", "")
        strTemp = Replace(strTemp, "S", "")
        strTemp = Replace(strTemp, "C", "")
        strTemp = Replace(strTemp, "H", "")
        vAll = Split(strTemp, ")")
        
        vLine = Split(vAll(0), "-")
        'If InStr(vLine(0), "S") > 0 Then vLine(0) = Replace(vLine(0), "S", "")
        'If InStr(vLine(0), "C") > 0 Then vLine(0) = Replace(vLine(0), "C", "")
        'If InStr(vLine(0), "H") > 0 Then vLine(0) = Replace(vLine(0), "H", "")
        
        vCount = Split(vAll(1), "-")
        'If InStr(vCount(0), "S") > 0 Then vCount(0) = Replace(vCount(0), "S", "")
        'If InStr(vCount(0), "C") > 0 Then vCount(0) = Replace(vCount(0), "C", "")
        'If InStr(vCount(0), "H") > 0 Then vCount(0) = Replace(vCount(0), "H", "")
        
        'MsgBox vCount(0) & " , " & vLine(0) & vbCr & vCount(1) & " , " & vLine(1)
        
        If CInt(vCount(0)) > CInt(vLine(0)) Then
            cbNote.Value = "Power to replace with Taller Pole"
        Else
            If CInt(vCount(1)) < CInt(vLine(1)) Then
                cbNote.Value = "Power to replace with Thicker Pole"
            Else
                cbNote.Value = "Power to replace with Like Pole"
            End If
        End If
    End If
    
    If Not vAttList(4).TextString = "" Then
        vAll = Split(vAttList(4).TextString, " ")
        For i = 0 To UBound(vAll)
            If InStr(vAll(i), "=") > 0 Then
                vLine = Split(vAll(i), "=")
                
                strLine = strLine & vbCr & vLine(0) & vbTab & vLine(1)
            Else
                strLine = strLine & vbCr & vAttList(2).TextString & vbTab & vAll(i)
            End If
        Next i
    End If
    
    If Not vAttList(8).TextString = "" Then
        Select Case vAttList(8).TextString
            Case "M"
                vAttList(8).TextString = "MGNV"
            Case "T"
                vAttList(8).TextString = "TGB"
            Case "B"
                vAttList(8).TextString = "BROKEN GRD"
        End Select
        
        strLine = strLine & vbCr & vAttList(8).TextString
    End If
    
    tbPoleData.Value = strLine
    
    tbLL.Value = vAttList(7).TextString
    
    '<----------------------------------------------------------------------Power
    
    If Not vAttList(9).TextString = "" Then
        lbWorkspace.AddItem "PWR"
        iIndex = lbWorkspace.ListCount - 1
        lbWorkspace.List(iIndex, 1) = "NEUTRAL"
        
        strLine = vAttList(9).TextString
        If InStr(strLine, ")") > 0 Then
            vLine = Split(strLine, ")")
            
            lbWorkspace.List(iIndex, 2) = Replace(vLine(0), "(", "")
            lbWorkspace.List(iIndex, 3) = vLine(1)
        Else
            If InStr(strLine, ">") > 0 Then
                vLine = Split(strLine, ">")
                vCount = Split(vLine(1), "-")
                vCount(0) = CInt(vCount(0)) + 1
                
                strLine = ""
                If Not vLine(0) = "" Then strLine = vLine(0)
                strLine = strLine & vCount(0)
                If UBound(vCount) > 0 Then strLine = strLine & "-" & vCount(1)
            End If
            
            lbWorkspace.List(iIndex, 2) = strLine
        End If
    End If
    
    If Not vAttList(10).TextString = "" Then
        lbWorkspace.AddItem "PWR"
        iIndex = lbWorkspace.ListCount - 1
        lbWorkspace.List(iIndex, 1) = "TRANSFORMER"
        
        strLine = vAttList(10).TextString
        If InStr(strLine, ")") > 0 Then
            vLine = Split(strLine, ")")
            
            lbWorkspace.List(iIndex, 2) = Replace(vLine(0), "(", "")
            lbWorkspace.List(iIndex, 3) = vLine(1)
        Else
            If InStr(strLine, ">") > 0 Then
                vLine = Split(strLine, ">")
                vCount = Split(vLine(1), "-")
                vCount(0) = CInt(vCount(0)) + 1
                
                strLine = ""
                If Not vLine(0) = "" Then strLine = vLine(0)
                strLine = strLine & vCount(0)
                If UBound(vCount) > 0 Then strLine = strLine & "-" & vCount(1)
            End If
            
            lbWorkspace.List(iIndex, 2) = strLine
        End If
    End If
    
    If Not vAttList(11).TextString = "" Then
        lbWorkspace.AddItem "PWR"
        iIndex = lbWorkspace.ListCount - 1
        lbWorkspace.List(iIndex, 1) = "LOW POWER"
        
        strLine = vAttList(11).TextString
        If InStr(strLine, ")") > 0 Then
            vLine = Split(strLine, ")")
            
            lbWorkspace.List(iIndex, 2) = Replace(vLine(0), "(", "")
            lbWorkspace.List(iIndex, 3) = vLine(1)
        Else
            If InStr(strLine, ">") > 0 Then
                vLine = Split(strLine, ">")
                vCount = Split(vLine(1), "-")
                vCount(0) = CInt(vCount(0)) + 1
                
                strLine = ""
                If Not vLine(0) = "" Then strLine = vLine(0)
                strLine = strLine & vCount(0)
                If UBound(vCount) > 0 Then strLine = strLine & "-" & vCount(1)
            End If
            
            lbWorkspace.List(iIndex, 2) = strLine
        End If
    End If
    
    If Not vAttList(12).TextString = "" Then
        lbWorkspace.AddItem "PWR"
        iIndex = lbWorkspace.ListCount - 1
        lbWorkspace.List(iIndex, 1) = "ANTENNA"
        
        strLine = vAttList(12).TextString
        If InStr(strLine, ")") > 0 Then
            vLine = Split(strLine, ")")
            
            lbWorkspace.List(iIndex, 2) = Replace(vLine(0), "(", "")
            lbWorkspace.List(iIndex, 3) = vLine(1)
        Else
            If InStr(strLine, ">") > 0 Then
                vLine = Split(strLine, ">")
                vCount = Split(vLine(1), "-")
                vCount(0) = CInt(vCount(0)) + 1
                
                strLine = ""
                If Not vLine(0) = "" Then strLine = vLine(0)
                strLine = strLine & vCount(0)
                If UBound(vCount) > 0 Then strLine = strLine & "-" & vCount(1)
            End If
            
            lbWorkspace.List(iIndex, 2) = strLine
        End If
    End If
    
    If Not vAttList(13).TextString = "" Then
        strLine = vAttList(13).TextString
        vAll = Split(strLine, " ")
        For i = 0 To UBound(vAll)
            lbWorkspace.AddItem "PWR"
            iIndex = lbWorkspace.ListCount - 1
            lbWorkspace.List(iIndex, 1) = "ST LT CIRCUIT"
            
            If InStr(vAll(i), ")") > 0 Then
                vLine = Split(vAll(i), ")")
            
                lbWorkspace.List(iIndex, 2) = Replace(vLine(0), "(", "")
                lbWorkspace.List(iIndex, 3) = vLine(1)
            Else
            If InStr(strLine, ">") > 0 Then
                vLine = Split(strLine, ">")
                vCount = Split(vLine(1), "-")
                vCount(0) = CInt(vCount(0)) + 1
                
                strLine = ""
                If Not vLine(0) = "" Then strLine = vLine(0)
                strLine = strLine & vCount(0)
                If UBound(vCount) > 0 Then strLine = strLine & "-" & vCount(1)
            End If
            
                lbWorkspace.List(iIndex, 2) = vAll(i)
            End If
        Next i
    End If
    
    If Not vAttList(14).TextString = "" Then
        strLine = vAttList(14).TextString
        vAll = Split(strLine, " ")
        For i = 0 To UBound(vAll)
            lbWorkspace.AddItem "PWR"
            iIndex = lbWorkspace.ListCount - 1
            lbWorkspace.List(iIndex, 1) = "ST LT"
        
            If InStr(vAll(i), ")") > 0 Then
                vLine = Split(vAll(i), ")")
            
                lbWorkspace.List(iIndex, 2) = Replace(vLine(0), "(", "")
                lbWorkspace.List(iIndex, 3) = vLine(1)
            Else
                If InStr(strLine, ">") > 0 Then
                    vLine = Split(strLine, ">")
                    vCount = Split(vLine(1), "-")
                    vCount(0) = CInt(vCount(0)) + 1
                    
                    strLine = ""
                    If Not vLine(0) = "" Then strLine = vLine(0)
                    strLine = strLine & vCount(0)
                    If UBound(vCount) > 0 Then strLine = strLine & "-" & vCount(1)
                End If
                
                lbWorkspace.List(iIndex, 2) = vAll(i)
            End If
        Next i
    End If
    
    '<----------------------------------------------------------------------New Attachment
    
    If Not vAttList(15).TextString = "" Then
        strLine = UCase(vAttList(15).TextString)
        vAll = Split(strLine, " ")
        For i = 0 To UBound(vAll)
            lbWorkspace.AddItem "NEW"
            iIndex = lbWorkspace.ListCount - 1
            lbWorkspace.List(iIndex, 1) = "NEW 6M"
            
            If InStr(vAll(i), "O") > 0 Then
                vAll(i) = Replace(vAll(i), "O", "")
                lbWorkspace.List(iIndex, 4) = "NEW OHG"
            End If
            
            If InStr(vAll(i), "P") > 0 Then
                lbWorkspace.List(iIndex, 1) = lbWorkspace.List(iIndex, 1) & " TAP"
                vAll(i) = Replace(vAll(i), "P", "")
            End If
            
            If InStr(vAll(i), "T") > 0 Then
                vAll(i) = Replace(vAll(i), "T", "")
                lbWorkspace.List(iIndex, 4) = "MTE TAG"
            End If
            
            If InStr(vAll(i), "F") > 0 Then
                vAll(i) = Replace(vAll(i), "F", "")
                lbWorkspace.List(iIndex, 4) = "FUTURE"
            End If
            
            lbWorkspace.List(iIndex, 3) = vAll(i)
        Next i
    End If
    
    '<----------------------------------------------------------------------Communications
    
    For n = 16 To 23
        If Not vAttList(n).TextString = "" Then
            strLine = UCase(vAttList(n).TextString)
            vLine = Split(strLine, "=")
            strCO = vLine(0)
        
            vAll = Split(vLine(1), " ")
            For i = 0 To UBound(vAll)
                lbWorkspace.AddItem "COMM"
                iIndex = lbWorkspace.ListCount - 1
        
                lbWorkspace.List(iIndex, 1) = strCO
        
                If InStr(vAll(i), "C") > 0 Then
                    lbWorkspace.List(iIndex, 1) = lbWorkspace.List(iIndex, 1) & " C-WIRE"
                    vAll(i) = Replace(vAll(i), "C", "")
                End If
        
                If InStr(vAll(i), "D") > 0 Then
                    lbWorkspace.List(iIndex, 1) = lbWorkspace.List(iIndex, 1) & " DROP"
                    vAll(i) = Replace(vAll(i), "D", "")
                End If
            
                If InStr(vAll(i), "E") > 0 Then
                    lbWorkspace.List(iIndex, 4) = "EXTEND"
                    vAll(i) = Replace(vAll(i), "E", "")
                End If
            
                If InStr(vAll(i), "O") > 0 Then
                    lbWorkspace.List(iIndex, 1) = lbWorkspace.List(iIndex, 1) & " OHG"
                    vAll(i) = Replace(vAll(i), "O", "")
                End If
            
                If InStr(vAll(i), "P") > 0 Then
                    lbWorkspace.List(iIndex, 1) = lbWorkspace.List(iIndex, 1) & " TAP"
                    vAll(i) = Replace(vAll(i), "P", "")
                End If
        
                If InStr(vAll(i), "S") > 0 Then
                    lbWorkspace.List(iIndex, 1) = lbWorkspace.List(iIndex, 1) & " SS"
                    vAll(i) = Replace(vAll(i), "S", "")
                End If
            
                If InStr(vAll(i), "T") > 0 Then
                    lbWorkspace.List(iIndex, 1) = lbWorkspace.List(iIndex, 1) & " TAG"
                    vAll(i) = Replace(vAll(i), "T", "")
                End If
            
                If InStr(vAll(i), "V") > 0 Then
                    lbWorkspace.List(iIndex, 1) = "LASH TO " & lbWorkspace.List(iIndex, 1)
                    vAll(i) = Replace(vAll(i), "V", "")
                End If
            
                If InStr(vAll(i), "X") > 0 Then
                    lbWorkspace.List(iIndex, 4) = "ATTACH"
                    vAll(i) = Replace(vAll(i), "X", "")
                End If
            
                If InStr(vAll(i), ")") > 0 Then
                    vLine = Split(vAll(i), ")")
            
                    lbWorkspace.List(iIndex, 2) = Replace(vLine(0), "(", "")
                    lbWorkspace.List(iIndex, 3) = vLine(1)
                Else
                    If lbWorkspace.List(iIndex, 4) = "ATTACH" Then
                        lbWorkspace.List(iIndex, 3) = vAll(i)
                    Else
                        lbWorkspace.List(iIndex, 2) = vAll(i)
                    End If
                End If
            Next i
        End If
    Next n
    
    tbNoteList.Value = ""
    
    If Not vAttList(24).TextString = "" Then
        vLine = Split(vAttList(24).TextString, ";")
        strLine = vLine(0)
        If UBound(vLine) > 0 Then
            For i = 1 To UBound(vLine)
                If Not vLine(i) = "" Then strLine = strLine & vbCr & vLine(i)
            Next i
        End If
    
        tbNoteList.Value = strLine
    End If
    
    If InStr(tbNoteList.Value, "NOTE-DEF") < 1 Then
        If vAttList(1).TextString = "DEFECTIVE" Then tbNoteList.Value = tbNoteList.Value & vbCr & "NOTE-DEF"
        If vAttList(1).TextString = "REPLACE" Then tbNoteList.Value = tbNoteList.Value & vbCr & "NOTE-DEF"
    End If
    
Exit_Sub:
End Sub

Attribute VB_Name = "MainForm"
Attribute VB_Base = "0{8B6D67C8-E7A7-46FC-B2D0-7EC6EB94D655}{82011EBC-35D1-4947-B4F4-1570B54C7709}"
Attribute VB_GlobalNameSpace = False
Attribute VB_Creatable = False
Attribute VB_PredeclaredId = True
Attribute VB_Exposed = False
Attribute VB_TemplateDerived = False
Attribute VB_Customizable = False
Private Sub AddCLR_Click()
    Me.Hide
        Load AddClearances
        AddClearances.show
        Unload AddClearances
    Me.show
End Sub

Private Sub btn_LotUpdate_Click()
    Me.Hide
        Load LotUpdate
        LotUpdate.show
        Unload LotUpdate
    Me.show
End Sub

Private Sub cbAAPlaceCable_Click()
    Me.Hide
        Load aaPlaceCable
        aaPlaceCable.show
        Unload aaPlaceCable
    Me.show
End Sub

Private Sub cbAAPlaceDrop_Click()
    Me.Hide
        Load aaPlaceDrops
        aaPlaceDrops.show
        Unload aaPlaceDrops
    Me.show
End Sub

Private Sub cbAddAdresses_Click()
    'If lbList.ListCount < 1 Then Exit Sub
    
    Dim filterType, filterValue As Variant
    Dim grpCode(0) As Integer
    Dim grpValue(0) As Variant
    Dim objSS As AcadSelectionSet
    Dim objBlock As AcadBlockReference
    Dim vLine, vItem, vCount As Variant
    Dim vPnt1, vPnt2 As Variant
    Dim dPnt1(0 To 2) As Double
    Dim dPnt2(0 To 2) As Double
    Dim strText, strExistingName, strLine As String
    Dim iCount As Integer
    
    grpCode(0) = 2
    grpValue(0) = "Customer,SG"
    filterType = grpCode
    filterValue = grpValue
    
    On Error Resume Next
    
    Err = 0
    Set objSS = ThisDrawing.SelectionSets.Add("objSS")
    If Not Err = 0 Then
        Set objSS = ThisDrawing.SelectionSets.Item("objSS")
        objSS.Clear
    End If
    
    Me.Hide
    
    vPnt1 = ThisDrawing.Utility.GetPoint(, "Get BL Corner: ")
    vPnt2 = ThisDrawing.Utility.GetCorner(vPnt1, vbCr & "Get UR Corner: ")
    
    dPnt1(0) = vPnt1(0)
    dPnt1(1) = vPnt1(1)
    dPnt1(2) = vPnt1(2)
    
    dPnt2(0) = vPnt2(0)
    dPnt2(1) = vPnt2(1)
    dPnt2(2) = vPnt2(2)
    
    objSS.Select acSelectionSetWindow, dPnt1, dPnt2, filterType, filterValue
    
    vTemp = Split(ThisDrawing.Name, " ")
    strExistingName = ThisDrawing.Path & "\" & vTemp(0) & " SERVED ADDRESSES.csv"
    
    Open strExistingName For Output As #1
    
    Print #1, "House #,Street Name,TN83F N,TN83F E,Type"
    
    For Each objBlock In objSS
        vAttList = objBlock.GetAttributes
        
        Select Case objBlock.Name
            Case "SG"
                If vAttList(2).TextString = "" Then GoTo Next_objBlock
                
                strLine = "SmartGrid," & vAttList(1).TextString & "," & objBlock.InsertionPoint(1)
                strLine = strLine & "," & objBlock.InsertionPoint(0) & ",SmartGrid"
                Print #1, strLine
            Case Else
                If vAttList(4).TextString = "" Then GoTo Next_objBlock
                
                strLine = vAttList(1).TextString & "," & vAttList(2).TextString & "," & objBlock.InsertionPoint(1)
                strLine = strLine & "," & objBlock.InsertionPoint(0) & "," & vAttList(0).TextString
                Print #1, strLine
        End Select
        
Next_objBlock:
    Next objBlock
    
Clear_objSS:
    objSS.Clear
    objSS.Delete
    
    Close #1
    MsgBox "Done"
    Me.show
End Sub

Private Sub cbAddBldgs_Click()
    Me.Hide
        Load AddBLDGForm
        AddBLDGForm.show
        Unload AddBLDGForm
    Me.show
End Sub

Private Sub cbAddExistingGuys_Click()
    Dim filterType, filterValue As Variant
    Dim grpCode(0) As Integer
    Dim grpValue(0) As Variant
    Dim objSS As AcadSelectionSet
    Dim objBlock As AcadBlockReference
    Dim objAnchor As AcadBlockReference
    Dim vCoords As Variant
    Dim dRotate, dCoords(2) As Double
    
    On Error Resume Next
    
    grpCode(0) = 2
    grpValue(0) = "ExGuyOR,ExGuyOL"
    filterType = grpCode
    filterValue = grpValue
    
    Set objSS = ThisDrawing.SelectionSets.Add("objSS")
    If Not Err = 0 Then
        Set objSS = ThisDrawing.SelectionSets.Item("objSS")
        objSS.Clear
    End If
    
    objSS.Select acSelectionSetAll, , , filterType, filterValue
    
    For Each objBlock In objSS
        dRotate = objBlock.Rotation
        vCoords = objBlock.InsertionPoint
        
        Select Case objBlock.Name
            Case "ExGuyOR"
                dRotate = dRotate - (3.14159265359 / 2)
            Case "ExGuyOL"
                dRotate = dRotate + (3.14159265359 / 2)
        End Select
        
        dCoords(0) = vCoords(0) + (15 * Cos(dRotate))
        dCoords(1) = vCoords(1) + (15 * Sin(dRotate))
        dCoords(2) = 0#
        
        Set objAnchor = ThisDrawing.ModelSpace.InsertBlock(dCoords, "Existing_Guys", 1#, 1#, 1#, objBlock.Rotation)
        objAnchor.Layer = "Integrity Existing-Guys"
        objAnchor.Update
    Next objBlock
    
Exit_Sub:
    objSS.Clear
    objSS.Delete

End Sub

Private Sub cbAddF1_Click()
    Me.Hide
        Load CombineF1F2
        CombineF1F2.show
        Unload CombineF1F2
    Me.show
End Sub

Private Sub cbAddOHG_Click()
    Dim entPole As AcadObject
    Dim obrGP As AcadBlockReference
    Dim obrTemp As AcadBlockReference
    Dim attItem, attList, basePnt As Variant
    Dim lwpObj As AcadLWPolyline
    Dim lwpCoords(0 To 3) As Double
    Dim strFromPole, strToPole As String
    Dim vCoords As Variant
    Dim dFromCoords(0 To 2), dToCoords(0 To 2) As Double
    Dim dInsertionPnt(0 To 2) As Double
    Dim dTemp, Pi  As Double
    Dim dX, dY, dRotate, dScale, dDistance As Double
    Dim strBlock, strRUS, strTemp As String
    Dim layerObj As AcadLayer
    
    Me.Hide
  On Error Resume Next
    Pi = 3.14159265359
  
   dScale = CDbl(MainForm.cbScale.Value) / 100
   If Err <> 0 Then dScale = 1#
  
    ThisDrawing.Utility.GetEntity entPole, basePnt, "From Pole: "
    If TypeOf entPole Is AcadBlockReference Then
        Set obrGP = entPole
    Else
        MsgBox "Not a valid pole."
        Exit Sub
    End If
    
    dFromCoords(0) = obrGP.InsertionPoint(0)
    dFromCoords(1) = obrGP.InsertionPoint(1)
    dFromCoords(2) = 0#
    
    ThisDrawing.Utility.GetEntity entPole, basePnt, "To Pole: "
    If TypeOf entPole Is AcadBlockReference Then
        Set obrGP = entPole
    Else
        MsgBox "Not a valid pole."
        Exit Sub
    End If
    
    dToCoords(0) = obrGP.InsertionPoint(0)
    dToCoords(1) = obrGP.InsertionPoint(1)
    dToCoords(2) = 0#
    
    dInsertionPnt(0) = (dFromCoords(0) + dToCoords(0)) / 2
    dInsertionPnt(1) = (dFromCoords(1) + dToCoords(1)) / 2
    dInsertionPnt(2) = 0#
    
    Select Case (dToCoords(0) - dFromCoords(0))
        Case Is < 0
            dX = (dFromCoords(0) - dToCoords(0))
            dY = (dFromCoords(1) - dToCoords(1))
            dRotate = Atn(dY / dX) + Pi
            strBlock = "ohgL"
        Case Is > 0
            dX = (dToCoords(0) - dFromCoords(0))
            dY = (dToCoords(1) - dFromCoords(1))
            dRotate = Atn(dY / dX)
            strBlock = "ohgR"
        Case Else
            dRotate = 0
            strBlock = "ohgR"
    End Select
    
    dDistance = Sqr((dX * dX) + (dY * dY))
    dDistance = Round(dDistance)
    
    Set layerObj = ThisDrawing.Layers.Add("Integrity Guys")
    ThisDrawing.ActiveLayer = layerObj
    
    Set obrTemp = ThisDrawing.ModelSpace.InsertBlock(dInsertionPnt, strBlock, dScale, dScale, dScale, dRotate)

    attList = obrTemp.GetAttributes
    
    attList(0).TextString = dDistance & "'"
    attList(1).TextString = "PE2-3G"
    
    lwpCoords(0) = dFromCoords(0)
    lwpCoords(1) = dFromCoords(1)
    lwpCoords(2) = dToCoords(0)
    lwpCoords(3) = dToCoords(1)
    
    Set lwpObj = ThisDrawing.ModelSpace.AddLightWeightPolyline(lwpCoords)
    lwpObj.Update
    
    ThisDrawing.Utility.GetEntity entPole, basePnt, vbCr & "Select block to add units:"
    
    Set obrTemp = entPole
    
    If obrTemp.Name = "sPole" Then
        attList = obrTemp.GetAttributes
            
        If attList(27).TextString = "" Then
            attList(27).TextString = "+PE2-3G=" & dDistance & "'"
        Else
            attList(27).TextString = attList(27).TextString & ";;+PE2-3G=" & dDistance & "'"
        End If
        
        obrTemp.Update
    End If
    
    Me.show
End Sub

Private Sub cbAddSheets_Click()
    'Dim layerObj As AcadLayer
  'On Error Resume Next
    'Set layerObj = ThisDrawing.Layers.Add("Integrity Sheets")
    'ThisDrawing.ActiveLayer = layerObj
    
    Dim entPole As AcadObject
    Dim obrGSS As AcadBlockReference
    Dim obrSSInfo As AcadBlockReference
    Dim obrSSDWG1 As AcadBlockReference
    Dim attItem, attItem1, basePnt, returnPnt As Variant
    Dim vEmail As Variant
    Dim insertPnt(0 To 2) As Double
    Dim dScale As Double
    Dim iDWGNum, iNextNum As Long
    Dim str, str2 As String
    
    Me.Hide
  On Error Resume Next
  
    iNextNum = 1
    
While Err = 0
    ThisDrawing.Utility.GetEntity entPole, basePnt, "Select Staking Sheet: "
    If TypeOf entPole Is AcadBlockReference Then
        Set obrGSS = entPole
    Else
        GoTo Exit_Sub
        'Me.show
        'Exit Sub
    End If
    
    If Not Err = 0 Then GoTo Exit_Sub
    If Not obrGSS.Name = "SS-11x17" Then GoTo Exit_Sub
    
    obrGSS.Layer = "Integrity Sheets"
    attItem = obrGSS.GetAttributes
    iDWGNum = ThisDrawing.Utility.GetInteger(vbCr & "Enter Drawing Number(" & iNextNum & "): ")
    If Err < 0 Then iDWGNum = iNextNum
    iNextNum = iDWGNum + 1
    
    Select Case iDWGNum
        Case Is < 10
            attItem(0).TextString = "DWG 00" & iDWGNum
        Case Is > 99
            attItem(0).TextString = "DWG " & iDWGNum
        Case Else
            attItem(0).TextString = "DWG 0" & iDWGNum
    End Select
    
    obrGSS.Update
    dScale = obrGSS.XScaleFactor
    
    lbSheets.AddItem iDWGNum & vbTab & dScale & vbTab & obrGSS.Name & vbTab & obrGSS.InsertionPoint(0) & vbTab & obrGSS.InsertionPoint(1)
  
    insertPnt(0) = obrGSS.InsertionPoint(0) + 20 * dScale
    insertPnt(1) = obrGSS.InsertionPoint(1) + 20 * dScale
    insertPnt(2) = obrGSS.InsertionPoint(2)
    
    Set obrSSInfo = ThisDrawing.ModelSpace.InsertBlock(insertPnt, "ss info", dScale, dScale, dScale, 0#)
    obrSSInfo.Layer = "Integrity Sheets"
    
    attItem = obrSSInfo.GetAttributes
    attItem(0).TextString = tbProject.Value
    attItem(1).TextString = tbWO.Value
    attItem(2).TextString = cbExchange.Value
    attItem(3).TextString = tbRST.Value
    attItem(4).TextString = cbCounty.Value
    attItem(5).TextString = tbCity.Value
    attItem(6).TextString = iDWGNum
    attItem(7).TextString = tbTotalDWG.Value
    obrSSInfo.Update
    
    If iDWGNum = 1 Then
        insertPnt(0) = obrGSS.InsertionPoint(0) + 20 * dScale
        insertPnt(1) = obrGSS.InsertionPoint(1) + 280 * dScale
        insertPnt(2) = obrGSS.InsertionPoint(2)
    
        Set obrSSDWG1 = ThisDrawing.ModelSpace.InsertBlock(insertPnt, "ss dwg1", dScale, dScale, dScale, 0#)
        obrSSDWG1.Layer = "Integrity Sheets"
    
        attItem1 = obrSSDWG1.GetAttributes
        
        vEmail = Split(cbDesigner.Value, " ")
        str2 = LCase(vEmail(0)) & "." & LCase(vEmail(1)) & "@integrity-us.com"
        str = cbDesigner.Value & "\P" & str2 & "\P" & tbPhoneNumber.Value & "\P"
        'Select Case cbDesigner.Value
        '    Case "Dylan Spears"
        '        str = "Dylan Spears\Pdylan.spears@integrity-us.com\P" & tbPhoneNumber.Value & "\P"
        '    Case "Jeremy Pafford"
        '        str = "Jeremy Pafford\Pjeremy.pafford@integrity-us.com\P(931)698-1992\P"
        '    Case "Ronn Elliott"
        '        str = "Ronn Elliott\Pronn.elliott@integrity-us.com\P(615)419-5421\P"
        '    Case "Rich Taylor"
        '        str = "Rich Taylor\Prich.taylor@integrity-us.com\P(615)785-2032\P"
        '    Case "Ronn Elliott"
        '        str = "Jason Pafford\Pjason.pafford@integrity-us.com\P(931)209-3269\P"
        'End Select
        str = str & "730 Middle Tennessee Blvd - Suite 6\PMurfreesboro, TN 37130"
        attItem1(0).TextString = str
        obrSSDWG1.Update
    End If
    Err = 0
Wend
    layerObj.Delete
    
Exit_Sub:
    Set layerObj = ThisDrawing.Layers.Add("0")
    ThisDrawing.ActiveLayer = layerObj
    Me.show
End Sub

Private Sub cbAddTerminals_Click()
    Me.Hide
    Load DesignTermForm
    DesignTermForm.show
    Unload DesignTermForm
    Me.show
End Sub

Private Sub cbAddTextToPoles_Click()
    Me.Hide
        Load AddTextToPoles
        AddTextToPoles.show
        Unload AddTextToPoles
    Me.show
End Sub

Private Sub cbAddUnits_Click()
    Me.Hide
        Load AddRemoveUnits
        AddRemoveUnits.show
        Unload AddRemoveUnits
    Me.show
End Sub

Private Sub cbAllPeds_Click()
    Dim amap As AcadMap
    Dim ODRcs As ODRecords
    Dim tbl As ODTable
    Dim tbls As ODTables
    Dim SSobj2 As AcadSelectionSet
    Dim entBlock As AcadEntity
    Dim returnObj As AcadPoint
    Dim tempPnt As AcadPoint
    Dim basePnt, insertPnt As Variant
    Dim boolVal As Boolean
    Dim objBR As AcadBlockReference
    Dim blckAtt, varStr As Variant
    Dim str1, str2, str3 As String
    Dim layerObj As AcadLayer
    
    Dim filterType, filterValue As Variant
    Dim grpCode(0) As Integer
    Dim grpValue(0) As Variant
    
  On Error Resume Next
    
    Set amap = ThisDrawing.Application.GetInterfaceObject("AutoCADMap.Application")
    
    Set tbls = amap.Projects(ThisDrawing).ODTables
    If tbls.count > 0 Then
        For Each tbl In tbls
            If tbl.Name = "UGStructure" Then GoTo Exit_For
        Next
    End If
Exit_For:
    'MsgBox tbl.Name
    Set ODRcs = tbl.GetODRecords
    Me.Hide
    
    grpCode(0) = 8
    grpValue(0) = "UGStructure"
    filterType = grpCode
    filterValue = grpValue
    
    Set SSobj2 = ThisDrawing.SelectionSets.Add("SSobj2")
    SSobj2.Select acSelectionSetAll, , , filterType, filterValue
    
    MsgBox SSobj2.count
    
    For Each returnObj In SSobj2
        insertPnt = returnObj.Coordinates
        boolVal = ODRcs.Init(returnObj, True, False)
        
        tbLine4.Value = ODRcs.Record.Item(33).Value
        tbLine10.Value = ODRcs.Record.Item(34).Value
    
        Set returnObj = Nothing
    
        Set layerObj = ThisDrawing.Layers.Add("Integrity PEDs")
        ThisDrawing.ActiveLayer = layerObj
    
        Set objBR = ThisDrawing.ModelSpace.InsertBlock(insertPnt, "PED", 1#, 1#, 1#, 0#)
        blckAtt = objBR.GetAttributes
   
        'blckAtt(1).TextString = tbLine4.Value
        'blckAtt(2).TextString = tbLine10.Value
        blckAtt(2).TextString = tbLine4.Value & ", " & tbLine10.Value
        objBR.Update
    Next returnObj
    
Exit_Sub:
    Set layerObj = ThisDrawing.Layers.Add("0")
    ThisDrawing.ActiveLayer = layerObj
    Me.show
    SSobj2.Clear
    SSobj2.Delete
End Sub

Private Sub cbAllPoles_Click()
    Dim amap As AcadMap
    Dim ODRcs As ODRecords
    Dim ODRc As ODRecord
    Dim tbl As ODTable
    Dim tbls As ODTables
    Dim SSobj2 As AcadSelectionSet
    Dim entBlock As AcadEntity
    Dim returnObj As AcadPoint
    Dim tempPnt As AcadPoint
    Dim basePnt, insertPnt As Variant
    Dim boolVal As Boolean
    Dim objBR As AcadBlockReference
    Dim blckAtt, varStr As Variant
    Dim str1, str2, str3 As String
    Dim strHC As String
    Dim layerObj As AcadLayer
    
    Dim filterType, filterValue As Variant
    Dim grpCode(0) As Integer
    Dim grpValue(0) As Variant
    
  'On Error Resume Next
    
    Set amap = ThisDrawing.Application.GetInterfaceObject("AutoCADMap.Application")
    
    Set tbls = amap.Projects(ThisDrawing).ODTables
    If tbls.count > 0 Then
        For Each tbl In tbls
            If tbl.Name = "OH_StructureLL" Then GoTo Exit_For
        Next
    End If
Exit_For:

    Set ODRcs = tbl.GetODRecords
    Me.Hide
    
    grpCode(0) = 8
    grpValue(0) = "OH_StructureLL"
    filterType = grpCode
    filterValue = grpValue
    
    Set SSobj2 = ThisDrawing.SelectionSets.Add("SSobj2")
    SSobj2.Select acSelectionSetAll, , , filterType, filterValue
    
    MsgBox SSobj2.count
    
    For Each returnObj In SSobj2
        insertPnt = returnObj.Coordinates
        boolVal = ODRcs.Init(returnObj, True, False)
        Set ODRc = ODRcs.Record
        
        'tbLine4.Value = ODRc.item(11).Value & " - " & ODRc.item(20).Value
        'If ODRc.item(9).Value = "W" Then
            'strHC = ODRc.item(12).Value & "-" & ODRc.item(11).Value
        'Else
            'strHC = ODRc.item(12).Value & "-" & ODRc.item(11).Value
        'End If
        strHC = ODRc.Item(12).Value & "-" & ODRc.Item(11).Value
    
        Set returnObj = Nothing
    
        If ODRc.Item(6).Value = "MTEMC" Then
            Set layerObj = ThisDrawing.Layers.Add("Integrity Poles-Power")
            ThisDrawing.ActiveLayer = layerObj
        Else
            Set layerObj = ThisDrawing.Layers.Add("Integrity Poles-Other")
            ThisDrawing.ActiveLayer = layerObj
        End If
    
        Set objBR = ThisDrawing.ModelSpace.InsertBlock(insertPnt, "iPole", 1#, 1#, 1#, 0#)
        blckAtt = objBR.GetAttributes
   
        blckAtt(0).TextString = "POLE"
        blckAtt(1).TextString = "INCOMPLETE"
        blckAtt(2).TextString = ODRc.Item(6).Value
        blckAtt(5).TextString = strHC
        blckAtt(6).TextString = ODRc.Item(15).Value
        blckAtt(7).TextString = ODRc.Item(18).Value & ", " & ODRc.Item(19).Value
        objBR.Update
    Next returnObj
    
Exit_Sub:
    Set layerObj = ThisDrawing.Layers.Add("0")
    ThisDrawing.ActiveLayer = layerObj
    Me.show
    SSobj2.Clear
    SSobj2.Delete
End Sub

Private Sub cbAllSubs_Click()
    Dim amap As AcadMap
    Dim ODRcs As ODRecords
    Dim ODRc As ODRecord
    Dim tbl As ODTable
    Dim tbls As ODTables
    Dim SSobj2 As AcadSelectionSet
    Dim entBlock As AcadEntity
    Dim returnObj As AcadPoint
    Dim tempPnt As AcadPoint
    Dim basePnt, insertPnt As Variant
    Dim boolVal As Boolean
    Dim objBR As AcadBlockReference
    Dim blckAtt, varStr As Variant
    Dim str1, str2, str3 As String
    Dim strPlaced As String
    Dim layerObj As AcadLayer
    Dim strAddress, strType As String
    
    Dim filterType, filterValue As Variant
    Dim grpCode(0) As Integer
    Dim grpValue(0) As Variant
    
  On Error Resume Next
    
    Set amap = ThisDrawing.Application.GetInterfaceObject("AutoCADMap.Application")
    
    Set tbls = amap.Projects(ThisDrawing).ODTables
    If tbls.count > 0 Then
        For Each tbl In tbls
            If tbl.Name = "CustomerPoints" Then GoTo Exit_For
        Next
    End If
Exit_For:
    Set ODRcs = tbl.GetODRecords
    Me.Hide
    
    grpCode(0) = 8
    grpValue(0) = "CustomerPoints"
    filterType = grpCode
    filterValue = grpValue
    
    Set SSobj2 = ThisDrawing.SelectionSets.Add("SSobj2")
    SSobj2.Select acSelectionSetAll, , , filterType, filterValue
    
    MsgBox SSobj2.count
    
    For Each returnObj In SSobj2
        insertPnt = returnObj.Coordinates
        boolVal = ODRcs.Init(returnObj, True, False)
        Set ODRc = ODRcs.Record
        strAddress = ODRc.Item(3).Value
        strType = ODRc.Item(9).Value
        Set returnObj = Nothing
        
        If ODRc.Item(5).Value = "PLACED" Then GoTo Next_Object
        
        If InStr(UCase$(strType), "SCHOOL") > 0 Then strPlaced = "SCH"
        If InStr(UCase$(strType), "CHURCH") > 0 Then strPlaced = "CHU"
        
        If InStr(UCase$(strType), "APT") > 0 Then strPlaced = "MDU"
        If InStr(UCase$(strType), "UNIT") > 0 Then strPlaced = "MDU"
        
        If InStr(UCase$(strType), "LOT") > 0 Then strPlaced = "LOT"
        
        If InStr(UCase$(strType), "BARN") > 0 Then strPlaced = "EXT"
        If InStr(UCase$(strType), "SHOP") > 0 Then strPlaced = "EXT"
        If InStr(UCase$(strType), "GARAGE") > 0 Then strPlaced = "EXT"
        If InStr(UCase$(strType), "MOP") > 0 Then strPlaced = "EXT"
        If InStr(UCase$(strType), "PUMP") > 0 Then strPlaced = "EXT"
        If InStr(UCase$(strType), "ENTERANCE") > 0 Then strPlaced = "EXT"
        If InStr(UCase$(strType), "GATE") > 0 Then strPlaced = "EXT"
        If InStr(UCase$(strType), "LIGHTS") > 0 Then strPlaced = "EXT"
        If InStr(UCase$(strType), "REMOTE") > 0 Then strPlaced = "EXT"
        
        If InStr(UCase$(strType), "TRL") > 0 Then strPlaced = "TRL"
        If InStr(UCase$(strType), "TRAILER") > 0 Then strPlaced = "TRL"
        If InStr(UCase$(strType), "DOUBLEWIDE") > 0 Then strPlaced = "TRL"
        
        If InStr(UCase$(strType), "RES") > 0 Then strPlaced = "RES"
        If InStr(UCase$(strType), "HOUSE") > 0 Then strPlaced = "RES"
        If InStr(UCase$(strType), "HSE") > 0 Then strPlaced = "RES"
        
        If InStr(UCase$(strType), "NON RES") > 0 Then strPlaced = "NONRES"
        
        If InStr(UCase$(strType), "BUS") > 0 Then strPlaced = "BUS"
        If InStr(UCase$(strType), "COMM") > 0 Then strPlaced = "BUS"
    
        'Set layerObj = ThisDrawing.Layers.Add("Integrity Building")
        'ThisDrawing.ActiveLayer = layerObj
    
        Select Case strPlaced
            Case "RES"
                Set layerObj = ThisDrawing.Layers.Add("Integrity Building-RES")
                ThisDrawing.ActiveLayer = layerObj
                Set objBR = ThisDrawing.ModelSpace.InsertBlock(insertPnt, "RES", 1#, 1#, 1#, 0#)
                blckAtt = objBR.GetAttributes
            Case "MDU"
                Set layerObj = ThisDrawing.Layers.Add("Integrity Building-MDU")
                ThisDrawing.ActiveLayer = layerObj
                Set objBR = ThisDrawing.ModelSpace.InsertBlock(insertPnt, "MDU", 1#, 1#, 1#, 0#)
                blckAtt = objBR.GetAttributes
            Case "LOT"
                Set layerObj = ThisDrawing.Layers.Add("Integrity Building-LOT")
                ThisDrawing.ActiveLayer = layerObj
                Set objBR = ThisDrawing.ModelSpace.InsertBlock(insertPnt, "LOT", 1#, 1#, 1#, 0#)
                blckAtt = objBR.GetAttributes
            Case "TRL"
                Set layerObj = ThisDrawing.Layers.Add("Integrity Building-TRLR")
                ThisDrawing.ActiveLayer = layerObj
                Set objBR = ThisDrawing.ModelSpace.InsertBlock(insertPnt, "TRLR", 1#, 1#, 1#, 0#)
                blckAtt = objBR.GetAttributes
            Case "SCH"
                Set layerObj = ThisDrawing.Layers.Add("Integrity Building-SCHOOL")
                ThisDrawing.ActiveLayer = layerObj
                Set objBR = ThisDrawing.ModelSpace.InsertBlock(insertPnt, "SCHOOL", 1#, 1#, 1#, 0#)
                blckAtt = objBR.GetAttributes
            Case "CHU"
                Set layerObj = ThisDrawing.Layers.Add("Integrity Building-CHURCH")
                ThisDrawing.ActiveLayer = layerObj
                Set objBR = ThisDrawing.ModelSpace.InsertBlock(insertPnt, "CHURCH", 1#, 1#, 1#, 0#)
                blckAtt = objBR.GetAttributes
            Case "BUS"
                Set layerObj = ThisDrawing.Layers.Add("Integrity Building-BUS")
                ThisDrawing.ActiveLayer = layerObj
                Set objBR = ThisDrawing.ModelSpace.InsertBlock(insertPnt, "BUSINESS", 1#, 1#, 1#, 0#)
                blckAtt = objBR.GetAttributes
            Case "EXT"
                Set layerObj = ThisDrawing.Layers.Add("Integrity Building-EXT")
                ThisDrawing.ActiveLayer = layerObj
                Set objBR = ThisDrawing.ModelSpace.InsertBlock(insertPnt, "EXTENTION", 1#, 1#, 1#, 0#)
                blckAtt = objBR.GetAttributes
            Case Else
                Set layerObj = ThisDrawing.Layers.Add("Integrity Building-Misc")
                ThisDrawing.ActiveLayer = layerObj
                Set objBR = ThisDrawing.ModelSpace.InsertBlock(insertPnt, "NONRES", 1#, 1#, 1#, 0#)
                blckAtt = objBR.GetAttributes
        End Select
    
        varStr = Split(strAddress, " ")
        str1 = varStr(0)
        str2 = ""
        For i = 1 To UBound(varStr)
            str2 = str2 & varStr(i) & " "
        Next i
        str2 = Left(str2, Len(str2) - 1)
    
        blckAtt(0).TextString = str1
        blckAtt(1).TextString = str2
        blckAtt(2).TextString = strType
        objBR.Update
        
        strPlaced = ""
        ODRc.Item(5).Value = "PLACED"
        boolVal = ODRcs.Update(ODRc)
Next_Object:
    Next returnObj
    
Exit_Sub:
    Set layerObj = ThisDrawing.Layers.Add("0")
    ThisDrawing.ActiveLayer = layerObj
    Me.show
    SSobj2.Clear
    SSobj2.Delete
End Sub

Private Sub cbAnchorGuys_Click()
    Dim startPnt(0 To 2), midPnt(0 To 2), endPnt(0 To 2) As Double
    Dim firstAng, endAng, defAng, rotateAng, ancAng, pull, tempPull As Double
    Dim X(0 To 2), Y(0 To 2), Z(0 To 2) As Double
    Dim dScale As Double
    Dim objBlock As AcadBlockReference
    Dim objBlock2 As AcadBlockReference
    Dim objTemp As AcadBlockReference
    Dim returnPoint, vAttList, insertPnt As Variant
    Dim n, result, iDirection As Integer  'iDirection 0=L 1=R
    Dim str, str2 As String
    'Dim layerObj As AcadLayer
    Dim strPull, strResult As String
    Dim vPoleCoords As Variant
    Dim objEntity As AcadEntity
    'Dim obrGP As AcadBlockReference
    Dim attItem, basePnt As Variant
    Dim Pi As Double
    
    Pi = 3.14159265359
    Me.Hide
On Error Resume Next

Place_Anchor:
    
    Err = 0
    ThisDrawing.Utility.GetEntity objEntity, basePnt, "Select Pole: "
    If Not Err = 0 Then GoTo Exit_Sub
    
    If TypeOf objEntity Is AcadBlockReference Then
        Set objBlock = objEntity
    Else
        'MsgBox "Not a valid pole."
        Me.show
        Exit Sub
    End If
    vPoleCoords = objBlock.InsertionPoint
    
    X(0) = vPoleCoords(0)
    Y(0) = vPoleCoords(1)
    
    ThisDrawing.Utility.GetEntity objEntity, basePnt, "Get Backspan Pole: "
    If Not Err = 0 Then GoTo Exit_Sub
    
    If TypeOf objEntity Is AcadBlockReference Then
        Set objBlock2 = objEntity
    Else
        'MsgBox "Not a valid pole."
        Me.show
        Exit Sub
    End If
    vPoleCoords = objBlock2.InsertionPoint
    
    X(1) = vPoleCoords(0)
    Y(1) = vPoleCoords(1)
    
    ThisDrawing.Utility.GetEntity objEntity, basePnt, "Get Frontspan Pole: "
    If Not Err = 0 Then GoTo Exit_Sub
    
    If TypeOf objEntity Is AcadBlockReference Then
        Set objBlock2 = objEntity
    Else
        'MsgBox "Not a valid pole."
        Me.show
        Exit Sub
    End If
    vPoleCoords = objBlock2.InsertionPoint
    
    
    X(2) = vPoleCoords(0)
    Y(2) = vPoleCoords(1)
    
    If (X(1) - X(0)) = 0 Then
        If (Y(1) - Y(0)) < 0 Then
            firstAng = 3 * Pi / 2
        Else
            firstAng = Pi / 2
        End If
    Else
        firstAng = Math.Atn((Y(1) - Y(0)) / (X(1) - X(0)))
        If (X(1) - X(0)) < 0 Then
            firstAng = Pi + firstAng
        ElseIf (Y(1) - Y(0)) < 0 Then
            firstAng = 2 * Pi + firstAng
        End If
    End If
    
    If (X(2) - X(0)) = 0 Then
        If (Y(2) - Y(0)) < 0 Then
            firstAng = 3 * Pi / 2
        Else
            firstAng = Pi / 2
        End If
    Else
        endAng = Math.Atn((Y(2) - Y(0)) / (X(2) - X(0)))
        If (X(2) - X(0)) < 0 Then
            endAng = Pi + endAng
        ElseIf (Y(2) - Y(0)) < 0 Then
            endAng = 2 * Pi + endAng
        End If
    End If
    
    rotateAng = (endAng + firstAng) / 2
    If Math.Abs(endAng - firstAng) < Pi Then
        rotateAng = rotateAng - Pi
    End If
        
    If rotateAng < 0 Then rotateAng = rotateAng + (2 * Pi)
    If rotateAng > (2 * Pi) Then rotateAng = rotateAng - (2 * Pi)
    
    defAng = firstAng + Pi - endAng
    pull = Math.Round(Math.Abs(100 * Math.Sin(defAng / 2)))
    
    If pull >= 50 Then  '<------------------------------------- Get strPull
        strPull = "DE"
    Else
        strPull = pull
    End If
    
    If (rotateAng > (Pi / 2)) And (rotateAng <= (3 * Pi / 2)) Then
        iDirection = 0
    Else
        iDirection = 1
    End If
    
    insertPnt = ThisDrawing.Utility.GetPoint(, "Place Guy:")
    
    dScale = 1#
    'dScale = CDbl(MainForm.cbScale.Value) / 100
    
    If iDirection = 0 Then
        str = "ExGuyOL"
    Else
        str = "ExGuyOR"
    End If
    
    'Set layerObj = ThisDrawing.Layers.Add("Integrity Guys")
    'ThisDrawing.ActiveLayer = layerObj
    
    Err = 0
    
    Set objTemp = ThisDrawing.ModelSpace.InsertBlock(insertPnt, str, dScale, dScale, dScale, rotateAng)
    objTemp.Layer = "Integrity Proposed"
    vAttList = objTemp.GetAttributes
   
    vAttList(1).TextString = " "
    vAttList(2).TextString = "PE1-3G"
    objTemp.Update
    If Not Err = 0 Then MsgBox "error" & vbCr & Err.Description

    If iDirection = 0 Then
        str = "ExAncOL"
    Else
        str = "ExAncOR"
    End If

    Set objTemp = ThisDrawing.ModelSpace.InsertBlock(insertPnt, str, dScale, dScale, dScale, rotateAng)
    objTemp.Layer = "Integrity Proposed"
    vAttList = objTemp.GetAttributes
    
    vAttList(0).TextString = "PF1-5A"
    'If strPull = "DE" Then
        'vAttList(1).TextString = "P= DE"
    'Else
        vAttList(1).TextString = "P= " & strPull
    'End If
    objTemp.Update
    
    vAttList = objBlock.GetAttributes
    
    If vAttList(27).TextString = "" Then
        vAttList(27).TextString = "PE1-3G=1;;PF1-5A=1;;PM11=1"
    Else
        vAttList(27).TextString = vAttList(27).TextString & ";;+PE1-3G=1;;+PF1-5A=1;;+PM11=1"
    End If
    
    objBlock.Update
    
    GoTo Place_Anchor
    
Exit_Sub:
    Me.show
End Sub

Private Sub cbAttachAlias_Click()
    Me.Hide
        Load AttachmentAlias
            AttachmentAlias.show
        Unload AttachmentAlias
    Me.show
End Sub

Private Sub cbAVCounts_Click()
    Me.Hide
        Load CountsForm
            CountsForm.show
        Unload CountsForm
    Me.show
End Sub

Private Sub cbBackspanCounts_Click()
    Me.Hide
        Load CountsBackspan
            CountsBackspan.show
        Unload CountsBackspan
    Me.show
End Sub

Private Sub cbBlockAtt_Click()
    Me.Hide
        Load ChangeAttData
        ChangeAttData.show
        Unload ChangeAttData
    Me.show
End Sub

Private Sub cbBore_Click()
    Me.Hide
        Load BuriedPlantForm
        BuriedPlantForm.show
        Unload BuriedPlantForm
    Me.show
End Sub

Private Sub cbCableCO_Click()
    Me.Hide
        Load CableCalloutForm
            CableCalloutForm.show
        Unload CableCalloutForm
    Me.show
End Sub

Private Sub cbCalcMR_Click()
    Me.Hide
    Load MRWorksheet
    MRWorksheet.show
    Unload MRWorksheet
    Me.show
End Sub

Private Sub cbCleanup_Click()
    Me.Hide
    Load CleanupForm
    CleanupForm.show
    Unload CleanupForm
    Me.show
End Sub

Private Sub cbClosureLocations_Click()
    Me.Hide
        Load ClosureLocations
        ClosureLocations.show
        Unload ClosureLocations
    Me.show
End Sub

Private Sub cbConvertBlocksBlock_Click()
    Me.Hide
        Load ConvertChangeBlocks
        ConvertChangeBlocks.show
        Unload ConvertChangeBlocks
    Me.show
End Sub

Private Sub cbConvertCustomer_Click()
    Me.Hide
        Load ConvertCustomers
            ConvertCustomers.show
        Unload ConvertCustomers
    Me.show
End Sub

Private Sub cbConvertGPS_Click()
    Me.Hide
        Load ConvertGPS
        ConvertGPS.show
        Unload ConvertGPS
    Me.show
End Sub

Private Sub cbConvertLayers_Click()
    Me.Hide
        Load ConvertBlockLayers
        ConvertBlockLayers.show
        Unload ConvertBlockLayers
    Me.show
End Sub

Private Sub cbConvertMisc_Click()
    Me.Hide
        Load ConvertBlocks
        ConvertBlocks.show
        Unload ConvertBlocks
    Me.show
End Sub

Private Sub cbConvertNES_Click()
    Me.Hide
        Load CreateNESPoles
        CreateNESPoles.show
        Unload CreateNESPoles
    Me.show
End Sub

Private Sub cbConvertText_Click()
    Me.Hide
        Load ConvertBlockText
        ConvertBlockText.show
        Unload ConvertBlockText
    Me.show
End Sub

Private Sub cbCounts_Click()
    Me.Hide
    Load DesignCountForm
    DesignCountForm.show
    Unload DesignCountForm
    Me.show
End Sub

Private Sub cbCustomers_Click()
'    Dim SSobj2 As AcadSelectionSet
'    Dim objBLDG As AcadBlockReference
'    Dim objNewBLDG As AcadBlockReference
'    Dim attList, attNewList As Variant
'    Dim filterType, filterValue As Variant
'    Dim grpCode(0) As Integer
'    Dim grpValue(0) As Variant
'    Dim entBlock As AcadEntity
'    Dim iCount As Integer
'    Dim str1, str2, strBlock, strLayer As String
'    Dim strTemp As String
'    Dim dInsertPnt(0 To 2) As Double
'    Dim dScale As Double
'
'    Me.hide
'    iCount = 0
'
'  On Error Resume Next
'
'    strTemp = "Integrity Building-BUS"
'    'strTemp = "Integrity Building, Integrity Building-RES, Integrity Building-BUS, Integrity Building-MDU, "
'    'strTemp = strTemp & "Integrity Building-TRL, Integrity Building-SCH, Integrity Building-CHU"
'
'    grpCode(0) = 8
'    grpValue(0) = strTemp
'    'grpCode(1) = 8
'    'grpValue(1) = "Integrity Building-RES"
'    filterType = grpCode
'    filterValue = grpValue
'
'    Set SSobj2 = ThisDrawing.SelectionSets.Add("SSobj2")
'    SSobj2.Select acSelectionSetAll, , , filterType, filterValue
'
'    MsgBox SSobj2.count
'
'    For Each entBlock In SSobj2
'        If Not entBlock.ObjectName = "AcDbBlockReference" Then GoTo Next_entBlock
'        Set objBLDG = entBlock
'        attList = objBLDG.GetAttributes
'        If Not UBound(attList) = 2 Then GoTo Next_entBlock
'
'        str1 = Left(attList(2).TextString, 3)
'        If str1 = "" Then GoTo Next_entBlock
'
'        str2 = UCase(attList(2).TextString)
'        If Len(str2) > 3 Then str2 = Right(str2, Len(str2) - 3)
'        If Len(str2) = 0 Then str2 = " "
'        If Left(str2, 1) = " " Then str2 = Right(str2, Len(str2) - 1)
'
'        Select Case str1
'            Case "res"
'                If objBLDG.Name = "RES" Then GoTo Next_entBlock
'                strBlock = "RES"
'                strLayer = "Integrity Building-RES"
'            Case "bus"
'                If objBLDG.Name = "BUSINESS" Then GoTo Next_entBlock
'                strBlock = "BUSINESS"
'                strLayer = "Integrity Building-BUS"
'            Case "trl"
'                If objBLDG.Name = "TRLR" Then GoTo Next_entBlock
'                strBlock = "TRLR"
'                strLayer = "Integrity Building-TRL"
'            Case "mdu"
'                If objBLDG.Name = "MDU" Then GoTo Next_entBlock
'                strBlock = "MDU"
'                strLayer = "Integrity Building-MDU"
'            Case "ext"
'                If objBLDG.Name = "EXTENTION" Then GoTo Next_entBlock
'                strBlock = "EXTENTION"
'                strLayer = "Integrity Building Misc"
'            Case "sch"
'                If objBLDG.Name = "SCHOOL" Then GoTo Next_entBlock
'                strBlock = "SCHOOL"
'                strLayer = "Integrity Building-SCH"
'            Case "chu"
'                MsgBox "CHURCH" & vbCr & str1 & vbCr & str2
'                If objBLDG.Name = "CHURCH" Then GoTo Next_entBlock
'                strBlock = "CHURCH"
'                strLayer = "Integrity Building-CHU"
'            Case Else
'                GoTo Next_entBlock
'        End Select
'
'        'str2 = "Old Block: " & objBLDG.Name & vbCr & "Data: " & attList(2).TextString & vbCr
'        'str2 = str2 & "New Block: " & strBlock
'        'MsgBox str2
'
'        'str2 = UCase(attList(2).TextString)
'        'str2 = Right(str2, Len(str2) - 3)
'
'        dInsertPnt(0) = objBLDG.InsertionPoint(0)
'        dInsertPnt(1) = objBLDG.InsertionPoint(1)
'        dInsertPnt(2) = 0#
'
'        dScale = objBLDG.XScaleFactor
'
'        Set objNewBLDG = ThisDrawing.ModelSpace.InsertBlock(dInsertPnt, strBlock, dScale, dScale, dScale, 0#)
'        objNewBLDG.Layer = strLayer
'        attNewList = objNewBLDG.GetAttributes
'
'        attNewList(0).TextString = attList(0).TextString
'        attNewList(1).TextString = attList(1).TextString
'        attNewList(2).TextString = str2
'
'        objNewBLDG.Update
'        objBLDG.Delete
'        iCount = iCount + 1
'Next_entBlock:
'    Next entBlock
'
'    SSobj2.Clear
'    SSobj2.Delete
'
'    MsgBox "Converted Buildings: " & iCount
'
'    Me.show
End Sub

Private Sub cbCreateKML_Click()
    Me.Hide
        Load CreateKML
            CreateKML.show
        Unload CreateKML
    Me.show
End Sub

Private Sub cbCreateProject_Click()
    Me.Hide
        Load ProjectCreate
            ProjectCreate.show
        Unload ProjectCreate
    Me.Hide
End Sub

Private Sub cbCreateVHLEForms_Click()
    Me.Hide
        Load CreateVHLEForms
            CreateVHLEForms.show
        Unload CreateVHLEForms
    Me.show
End Sub

Private Sub cbCustomerReport_Click()
    Me.Hide
        Load CustomerLocationReport
            CustomerLocationReport.show
        Unload CustomerLocationReport
    Me.show
End Sub

Private Sub cbDBKF_Click()
    Me.Hide
        Load dbLoss
            dbLoss.show
        Unload dbLoss
    Me.show
End Sub

Private Sub cbDeleteDrop_Click()
    Me.Hide
        Call DeleteDropCallouts
    Me.show
End Sub

Private Sub cbDropCallouts_Click()
    Me.Hide
        Call DropCallout
    Me.show
End Sub

Private Sub cbExchange_Change()
    Select Case cbExchange.Value
        Case "Belfast"
            cbCounty.Value = "Marshall"
            tbCity.Value = "Belfast"
        Case "Bell Buckle"
            cbCounty.Value = "Bedford"
            tbCity.Value = "Bell Buckle"
        Case "Chapel Hill"
            cbCounty.Value = "Marshall"
            tbCity.Value = "Chapel Hill"
        Case "Chapel Hill-CLEC"
            cbCounty.Value = "Marshall"
            tbCity.Value = " "
        Case "College Grove"
            cbCounty.Value = "Williamson"
            tbCity.Value = "College Grove"
        Case "College Grove-CLEC"
            cbCounty.Value = "Williamson"
            tbCity.Value = " "
        Case "Flat Creek"
            cbCounty.Value = "Bedford"
            tbCity.Value = "Flat Creek"
        Case "Fosterville"
            cbCounty.Value = "Rutherford"
            tbCity.Value = "Fosterville"
        Case "Franklin-CLEC"
            cbCounty.Value = "Williamson"
            tbCity.Value = "Franklin"
        Case "Lebanon-CLEC"
            cbCounty.Value = "Wilson"
            tbCity.Value = "Lebanon"
        Case "Murfreesboro-CLEC"
            cbCounty.Value = "Rutherford"
            tbCity.Value = "Murfreesboro"
        Case "Nolensville"
            cbCounty.Value = "Williamson"
            tbCity.Value = "Nolensville"
        Case "Nolensville-CLEC"
            cbCounty.Value = "Williamson"
            tbCity.Value = "Nolensville"
        Case "Shelbyville-CLEC"
            cbCounty.Value = "Bedford"
            tbCity.Value = "Shelbyville"
        Case "Smyrna-CLEC"
            cbCounty.Value = "Rutherford"
            tbCity.Value = "Smyrna"
        Case "Triune"
            cbCounty.Value = "Williamson"
            tbCity.Value = "Triune"
        Case "Unionville"
            cbCounty.Value = "Bedford"
            tbCity.Value = "Unionville"
    End Select
End Sub

Private Sub cbExtraHeights_Click()
    Me.Hide
        Load ExtraHeightForm
        ExtraHeightForm.show
        Unload ExtraHeightForm
    Me.show
End Sub

Private Sub cbFeedCounts_Click()
    Me.Hide
    Load FeedCounts
    FeedCounts.show
    Unload FeedCounts
    Me.show
End Sub

Private Sub cbFixSubs_Click()
    Me.Hide
    Load DesignReplaceSubs
    DesignReplaceSubs.show
    Unload DesignReplaceSubs
    Me.show
End Sub

Private Sub cbGetData_Click()
    Me.Hide
        Load GetDataByPoly
        GetDataByPoly.show
        Unload GetDataByPoly
    Me.show
End Sub

Private Sub cbGetLengths_Click()
    Me.Hide
        Load GetCableLengths
        GetCableLengths.show
        Unload GetCableLengths
    Me.show
End Sub

Private Sub cbGetSpansReel_Click()
    Me.Hide
        Load GetSpansReel
        GetSpansReel.show
        Unload GetSpansReel
    Me.show
End Sub

Private Sub cbHousing_Click()
    Me.Hide
        Load PlaceBuriedData
        PlaceBuriedData.show
        Unload PlaceBuriedData
    Me.show
End Sub

Private Sub cbLoadBlocks_Click()
    Me.Hide
        Load LoadBlocks
        LoadBlocks.show
        Unload LoadBlocks
    Me.show
End Sub

Private Sub cbMaptrim_Click()
    Dim objSSM1 As AcadSelectionSet
    Dim objEntity As AcadEntity
    Dim objEntTemp As AcadEntity
    Dim objRemove(0) As AcadEntity
    Dim objLWP As AcadLWPolyline
    Dim objLWPBorder As AcadLWPolyline
    Dim objSSBlock As AcadBlockReference
    Dim objLayer As AcadLayer
    'Dim strLayer As String
    Dim strCommand As String
    Dim strHandle As String
    Dim strRemove As String
    Dim vReturnPnt As Variant
    Dim vCoords As Variant
    Dim dLL(0 To 2) As Double
    Dim dUR(0 To 2) As Double
    Dim dFrom(0 To 2) As Double
    Dim dTo(0 To 2) As Double
    Dim dDiff(0 To 1) As Double
    Dim dScale As Double
    
  On Error Resume Next
    'Select boundary & find drawing number
    
    Me.Hide
    
    Err = 0
    Set objSSM1 = ThisDrawing.SelectionSets.Add("objSSM1")
    If Not Err = 0 Then
        Set objSSM1 = ThisDrawing.SelectionSets.Item("objSSM1")
        Err = 0
    End If
    
  While Err = 0
    
    ThisDrawing.Utility.GetEntity objEntity, vReturnPnt, "Select Trim Border: "
    If Not objEntity.ObjectName = "AcDbPolyline" Then
        Me.show
        Exit Sub
    End If
    
    Set objLWP = objEntity
    vCoords = objLWP.Coordinates
    
    dLL(0) = vCoords(0)
    dLL(1) = vCoords(1)
    dUR(0) = vCoords(0)
    dUR(1) = vCoords(1)
    
    For i = 2 To UBound(vCoords)
        If vCoords(i) < dLL(0) Then
            dLL(0) = vCoords(i)
        Else
            If vCoords(i) > dUR(0) Then
                dUR(0) = vCoords(i)
            End If
        End If
        
        i = i + 1
        
        If vCoords(i) < dLL(1) Then
            dLL(1) = vCoords(i)
        Else
            If vCoords(i) > dUR(1) Then
                dUR(1) = vCoords(i)
            End If
        End If
    Next i
    
    dFrom(0) = (dLL(0) + dUR(0)) / 2
    dFrom(1) = (dLL(1) + dUR(1)) / 2
    
    'Get coordinates to DWG Sheet and draw LWP (Save strHandle)
    
    ThisDrawing.Utility.GetEntity objEntity, vReturnPnt, "Select DWG Border: "
    If TypeOf objEntity Is AcadBlockReference Then
        Set objSSBlock = objEntity
    Else
        MsgBox "Not a valid entity."
        Exit Sub
    End If
    
    dScale = objSSBlock.XScaleFactor
    strRemove = objSSBlock.Layer
    
    dTo(0) = objSSBlock.InsertionPoint(0) + (825 * dScale)
    dTo(1) = objSSBlock.InsertionPoint(1) + (525 * dScale)
    dTo(2) = 0#
    
    dDiff(0) = dTo(0) - dFrom(0)
    dDiff(1) = dTo(1) - dFrom(1)
    
    Set objLWPBorder = ThisDrawing.ModelSpace.AddLightWeightPolyline(vCoords)
    objLWPBorder.Closed = True
    objLWPBorder.Layer = objLWP.Layer
    objLWPBorder.Move dFrom, dTo
    objLWPBorder.Update
    strHandle = objLWPBorder.Handle
    
    'Get objects crossing within dimensions of DWG and copy to DWG
    
    objSSM1.Select acSelectionSetCrossing, dLL, dUR
    
    If objSSM1.count = 0 Then GoTo Exit_Sub
    
    strCommand = "COPY" & vbCr & "P" & vbCr & vbCr
    strCommand = strCommand & dFrom(0) & "," & dFrom(1) & ",0" & vbCr
    strCommand = strCommand & dTo(0) & "," & dTo(1) & ",0" & vbCr & vbCr
    
    ThisDrawing.SetVariable "CMDDIA", 0
    ThisDrawing.SendCommand strCommand
    
    objSSM1.Clear
    
    Set objLayer = ThisDrawing.Layers(strRemove)
    objLayer.Lock = True
    
    dLL(0) = dLL(0) + dDiff(0)
    dLL(1) = dLL(1) + dDiff(1)
    dUR(0) = dUR(0) + dDiff(0)
    dUR(1) = dUR(1) + dDiff(1)
    
    'Set objSSM1 = ThisDrawing.SelectionSets.Add("objSSM1")
    objSSM1.Select acSelectionSetCrossing, dLL, dUR
        
    For Each objEntTemp In objSSM1
        If objEntTemp.Layer = strRemove Then
            'MsgBox "Found an entity" & vbCr & objEntTemp.ObjectName
            Set objRemove(0) = objEntTemp
            objSSM1.RemoveItems objRemove
        End If
    Next objEntTemp
    
    strCommand = "_MAPTRIM" & vbCr & "S" & vbCr & "(handent """ & strHandle & """)" & vbCr
    strCommand = strCommand & "N" & vbCr & "Y" & vbCr & "P" & vbCr & vbCr & "O" & vbCr
    strCommand = strCommand & "Y" & vbCr & "Y" & vbCr & "R" & vbCr & "Y" & vbCr

    ThisDrawing.SendCommand strCommand
    
    objSSM1.Clear
    
    objLayer.Lock = False
  Wend
    
Exit_Sub:
    objSSM1.Delete
    
    ThisDrawing.SetVariable "CMDDIA", 1
    Me.show
End Sub

Private Sub cbMatchlines_Click()
    Me.Hide
    Call Module1.AddMatchlines
    Me.show
    Exit Sub
End Sub

Private Sub cbMissingCallouts_Click()
    Me.Hide
        Load FindMissingCallouts
            FindMissingCallouts.show
        Unload FindMissingCallouts
    Me.show
End Sub

Private Sub cbMRReport_Click()
    Me.Hide
        Load MRSheets
            MRSheets.show
        Unload MRSheets
    Me.show
End Sub

Private Sub cbOldMenu_Click()
    Me.Hide
        Load MainForm2
        MainForm2.show
        Unload MainForm2
    Me.show
End Sub

Private Sub cbMRReview_Click()
    Me.Hide
    Load MRReview
    MRReview.show
    Unload MRReview
    Me.show
End Sub

Private Sub cbODInquiry_Click()
    Me.Hide
        Load ObjectDataInquiry
        ObjectDataInquiry.show
        Unload ObjectDataInquiry
    Me.show
End Sub

Private Sub cbOpenDWG_Click()
    Me.Hide
        Load ProjectOpen
        ProjectOpen.show
        Unload ProjectOpen
    Me.show
End Sub

Private Sub cbPedForm_Click()
    Me.Hide
        Load PedForm
        PedForm.show
        Unload PedForm
    Me.show
End Sub

Private Sub cbPlaceBuriedCbl_Click()
    Dim amap As AcadMap
    Dim ODRcs As ODRecords
    Dim tbl As ODTable
    Dim tbls As ODTables
    Dim boolVal As Boolean
    Dim entPole As AcadObject
    Dim objLWP As AcadLWPolyline
    Dim objLine As AcadLine
    Dim obrDrop As AcadBlockReference
    Dim attItem, basePnt As Variant
    Dim strType, strLength, strTemp As String
    Dim dRotate, dScale, Pi As Double
    Dim dTest As Double
    Dim dInsertPnt(0 To 2) As Double
    Dim dStartPnt(0 To 2) As Double
    Dim dEndPnt(0 To 2) As Double
    Dim dDiff(0 To 1) As Double
    Dim vStartPnt, vEndPnt As Variant
    Dim vCoords, vAttList, vList As Variant
    Dim layerObj As AcadLayer
    Dim strCableSize As String
    
    Me.Hide
  On Error Resume Next
    Set layerObj = ThisDrawing.Layers.Add("Integrity Cable-Buried Text")
    ThisDrawing.ActiveLayer = layerObj
    
    strCableSize = ThisDrawing.Utility.GetString(1, "Cable Size (Space between Cables): ")
    vList = Split(strCableSize, " ")
    strCableSize = ""
    For iTemp = LBound(vList) To UBound(vList)
        strCableSize = strCableSize & vList(iTemp) & "F "
    Next iTemp
  
    Pi = 3.14159265359
    'dScale = 1
    
    Set amap = ThisDrawing.Application.GetInterfaceObject("AutoCADMap.Application")
    
    Set tbls = amap.Projects(ThisDrawing).ODTables
    
get_Drop:

    dScale = 1#  'cbScale.Value / 100
    strLength = ""
    
    Err = 0
    ThisDrawing.Utility.GetEntity entPole, basePnt, "Select Buried Cable: "
    If Not Err = 0 Then GoTo Exit_Sub
    
    Select Case entPole.ObjectName
        Case "AcDbLine"
            Set objLine = entPole
            strTemp = CInt(objLine.Length)
            vStartPnt = objLine.StartPoint
            vEndPnt = objLine.EndPoint
            
            Err = 0
            If tbls.count > 0 Then
                For Each tbl In tbls
                    If tbl.Name = "UGPrimary" Then GoTo Exit_For2
                Next
            End If
Exit_For2:
            
            Set ODRcs = tbl.GetODRecords
            boolVal = ODRcs.Init(entPole, True, False)
             
            strLength = ODRcs.Record.Item(35).Value
            'MsgBox Len(strLength) & vbCr & Err
            If Len(strLength) < 1 Then
                strLength = strTemp
            End If
            
        Case "AcDbPolyline"
            Set objLWP = entPole
            strTemp = CStr(CInt(objLWP.Length))
            'MsgBox strTemp
            vCoords = objLWP.Coordinates
            dStartPnt(0) = vCoords(0)
            dStartPnt(1) = vCoords(1)
            dStartPnt(2) = 0#
            dEndPnt(0) = vCoords(2)
            dEndPnt(1) = vCoords(3)
            dEndPnt(2) = 0#
            
            dDiff(0) = dEndPnt(0) - dStartPnt(0)
            dDiff(1) = dEndPnt(1) - dStartPnt(1)
            dTemp = Sqr(dDiff(0) * dDiff(0) + dDiff(1) * dDiff(1))
            
            If UBound(vCoords) > 3 Then
                For i = 5 To UBound(vCoords) Step 2
                    dDiff(0) = vCoords(i - 1) - vCoords(i - 3)
                    dDiff(1) = vCoords(i) - vCoords(i - 2)
                    If dTemp < Sqr(dDiff(0) * dDiff(0) + dDiff(1) * dDiff(1)) Then
                        dStartPnt(0) = vCoords(i - 3)
                        dStartPnt(1) = vCoords(i - 2)
                        dEndPnt(0) = vCoords(i - 1)
                        dEndPnt(1) = vCoords(i)
                        dTemp = Sqr(dDiff(0) * dDiff(0) + dDiff(1) * dDiff(1))
                    End If
                Next i
            End If
            
            Err = 0
            If tbls.count > 0 Then
                For Each tbl In tbls
                    If tbl.Name = "UGPrimary" Then GoTo exit_for4
                Next
            End If
exit_for4:
            
            Set ODRcs = tbl.GetODRecords
            boolVal = ODRcs.Init(entPole, True, False)
               
            strLength = ODRcs.Record.Item(35).Value
            'MsgBox Len(strLength) & vbCr & Err
            If Len(strLength) < 1 Then
                strLength = strTemp
            End If
            
            vStartPnt = dStartPnt
            vEndPnt = dEndPnt
        Case Else
            Set layerObj = ThisDrawing.Layers.Add("0")
            ThisDrawing.ActiveLayer = layerObj
            Me.show
            Exit Sub
    End Select
    
    dInsertPnt(0) = (vStartPnt(0) + vEndPnt(0)) / 2
    dInsertPnt(1) = (vStartPnt(1) + vEndPnt(1)) / 2
    dInsertPnt(2) = 0#
    
    dDiff(0) = vEndPnt(0) - vStartPnt(0)
    dDiff(1) = vEndPnt(1) - vStartPnt(1)
    
    If dDiff(0) = 0 Then
        dRotate = 0#
    Else
        If dDiff(1) = 0 Then
            dRotate = Pi / 2
        Else
            dRotate = Atn(dDiff(1) / dDiff(0))
        End If
    End If
    
    If dRotate > (Pi / 2) And dRotate < (1.5 * Pi) Then dRotate = dRotate - Pi
    
    'ThisDrawing.ActiveLayer = layerObj
    
    Set obrDrop = ThisDrawing.ModelSpace.InsertBlock(dInsertPnt, "Cable_span", dScale, dScale, dScale, dRotate)
    vAttList = obrDrop.GetAttributes
    vAttList(1).TextString = strCableSize
    vAttList(2).TextString = strLength & "'"
    obrDrop.Update
    
    GoTo get_Drop
Exit_Sub:
    Me.show
End Sub

Private Sub cbPlaceCable_Click()
    Me.Hide
    
        Load PlaceAerialCable
        PlaceAerialCable.show
        Unload PlaceAerialCable
    
    Me.show
End Sub

Private Sub cbPlaceFromSpida_Click()
    Me.Hide
        Load PlaceSPIDAPoles
        PlaceSPIDAPoles.show
        Unload PlaceSPIDAPoles
    Me.show
End Sub

Private Sub cbPlaceOwner_Click()
    Me.Hide
            Load PoleOwnerNote
            PoleOwnerNote.show
            Unload PoleOwnerNote
    Me.show
End Sub

Private Sub cbPlacePoleData_Click()
    Me.Hide
            Load PlacePoleData
            PlacePoleData.show
            Unload PlacePoleData
    Me.show
End Sub

Private Sub cbPlanWorksheet_Click()
    Me.Hide
        Load aaPlanningWorksheet
        aaPlanningWorksheet.show
        Unload aaPlanningWorksheet
    Me.show
End Sub

Private Sub cbPoleCOMMs_Click()
    Me.Hide
        Load PoleCOMMupdate
        PoleCOMMupdate.show
        Unload PoleCOMMupdate
    Me.show
End Sub

Private Sub cbPoleData_Click()
    Me.Hide
            Load ConPoleForm
            ConPoleForm.show
            Unload ConPoleForm
    Me.show
End Sub

Private Sub cbPonVHLE_Click()
    Me.Hide
            Load PonVHLE
            PonVHLE.show
            Unload PonVHLE
    Me.show
End Sub

Private Sub cbPrintSelected_Click()
    Dim strArraySheets() As String
    Dim attTotalLine, attTotalSplit As Variant
    Dim str, str1 As String
    Dim strDWG As String
    Dim dScale As Double
    Dim dLL(0 To 1), dUR(0 To 1) As Double
    Dim strPlot(0 To 24) As String
    Dim i As Integer
    Dim strCommand As String
    Dim strPath As String
    Dim strFileName As String
    'Dim str As String
    Dim strArray As Variant
    Dim viewCoordsB(0 To 2) As Double
    Dim viewCoordsE(0 To 2) As Double
    
    strPath = ThisDrawing.Path & "\"
    
    strPlot(0) = "-plot"
    strPlot(1) = "y"
    strPlot(2) = ""
    'strPlot(3) = "Microsoft Print to PDF"
    strPlot(4) = "TABLOID"
    strPlot(5) = "i" '"i"
    strPlot(6) = "LANDSCAPE"
    strPlot(7) = "n"
    strPlot(8) = "w"
    'strPlot(9) = ""
    'strPlot(10) = ""
    'strPlot(11) = "" '"1=75"
    strPlot(12) = "c"
    strPlot(13) = "y"
    strPlot(14) = "United.ctb"
    strPlot(15) = "y"
    strPlot(16) = "a"
    strPlot(17) = "n"
    strPlot(18) = "n"
    strPlot(19) = "y"
    'strPlot(20) = ""
    strPlot(21) = ""
    strPlot(22) = ""
    strPlot(23) = ""
    strPlot(24) = ""
    
    ThisDrawing.SetVariable "FILEDIA", 0
    ThisDrawing.SetVariable "CMDDIA", 0
    
    For i = 0 To lbSheets.ListCount - 1
        If lbSheets.Selected(i) Then
            str = lbSheets.List(i)
            attTotalSplit = Split(str, vbTab)
            strDWG = attTotalSplit(0)
            dScale = CDbl(attTotalSplit(1))
            dLL(0) = CDbl(attTotalSplit(2))
            dLL(1) = CDbl(attTotalSplit(3))
            dUR(0) = dLL(0) + (1652 * dScale)
            dUR(1) = dLL(1) + (1052 * dScale)
    
            viewCoordsB(0) = dLL(0)
            viewCoordsB(1) = dLL(1)
            viewCoordsB(2) = 0#
            viewCoordsE(0) = dUR(0)
            viewCoordsE(1) = dUR(1)
            viewCoordsE(2) = 0#
    
            ThisDrawing.Application.ZoomWindow viewCoordsB, viewCoordsE
            
            strPlot(9) = (dLL(0) - (1 * dScale)) & "," & (dLL(1) - (1 * dScale))
            strPlot(10) = (dUR(0) + (1 * dScale)) & "," & (dUR(1) + (1 * dScale))
            strPlot(11) = "1=" & CStr((dScale + 0.02) * 100)
    
            strFileName = """" & strPath & "Individual Sheets\" & strDWG & ".pdf"""
            strPlot(20) = strFileName
            'MsgBox strFileName
            
            strCommand = ""
            For j = 0 To 19
                If strPlot(j) = "" Then
                    strCommand = strCommand & vbCr
                Else
                    strCommand = strCommand & strPlot(j) & vbCr
                End If
            Next j
            
            ThisDrawing.SendCommand strCommand
            
            'str1 = strDWG & vbCr & "Scale= " & dScale & vbCr
            'str1 = str1 & "LLx " & dLL(0) & vbCr & "LLy " & dLL(1) & vbCr
            'str1 = str1 & "URx " & dUR(0) & vbCr & "URy " & dUR(1)
            
            'MsgBox str1
            
            'ThisDrawing.ActiveLayout.SetWindowToPlot dLL, dUR
            'ThisDrawing.ActiveLayout.PlotType = acWindow
            'ThisDrawing.ActiveLayout.ConfigName "Microsoft Print to PDF.pc3"
            'ThisDrawing.Plot.PlotToDevice
        End If
    Next i
    
    ThisDrawing.SetVariable "FILEDIA", 1
    ThisDrawing.SetVariable "CMDDIA", 1
    
End Sub

Private Sub cbProjectStatus_Click()
    Me.Hide
            Load ProjectStatus
            ProjectStatus.show
            Unload ProjectStatus
    Me.show
End Sub

Private Sub cbPwrAttach_Click()
    Me.Hide
            Load PwrAttachment
            PwrAttachment.show
            Unload PwrAttachment
    Me.show
End Sub

Private Sub cbQuit_Click()
    Me.Hide
End Sub

Private Sub cbRdClr_Click()
    Me.Hide
            Load RdClrForm
            RdClrForm.show
            Unload RdClrForm
    Me.show
End Sub

Private Sub cbRearrageCounts_Click()
    Me.Hide
        Load RearrangeCounts
            RearrangeCounts.show
        Unload RearrangeCounts
    Me.show
End Sub

Private Sub cbRenumber_Click()
    Me.Hide
        Load RenumberPoles
            RenumberPoles.show
        Unload RenumberPoles
    Me.show
End Sub

Private Sub cbReplaceCounts_Click()
    Me.Hide
        Load ReplaceCounts
            ReplaceCounts.show
        Unload ReplaceCounts
    Me.show
End Sub

Private Sub cbReplaceUnits_Click()
    Me.Hide
        Load ReplaceUnits
            ReplaceUnits.show
        Unload ReplaceUnits
    Me.show
End Sub

Private Sub cbResizeBlocks_Click()
    Me.Hide
        Load ResizeBlocks
            ResizeBlocks.show
        Unload ResizeBlocks
    Me.show
End Sub

Private Sub cbRevCloudText_Click()
    Dim objSS As AcadSelectionSet
    Dim objEntity As AcadEntity
    Dim objText As AcadText
    Dim objMText As AcadMText
    Dim objLWP As AcadLWPolyline
    Dim vReturnPnt As Variant
    Dim vMin, vMax As Variant
    Dim strCommand, strResult As String
    Dim strLayer As String
    Dim dRotation As Double
    
    Me.Hide
    
    On Error Resume Next
    ThisDrawing.Utility.GetEntity objEntity, vReturnPnt, vbCr & "Select Text or MText:"
    Set objSS = ThisDrawing.SelectionSets.Add("temp")
    
    Select Case objEntity.ObjectName
        Case "AcDbMText"
            Set objMText = objEntity
            strLayer = objMText.Layer
            
            dRotation = objMText.Rotation
            objMText.Rotation = 0
            objMText.GetBoundingBox vMin, vMax
            vMin(0) = vMin(0) - 5
            vMin(1) = vMin(1) - 5
            vMax(0) = vMax(0) + 5
            vMax(1) = vMax(1) + 5
            
            strCommand = "revcloud r " & vMin(0) & "," & vMin(1) & " " & vMax(0) & "," & vMax(1) & " " & vbCr
            ThisDrawing.SendCommand strCommand
            
            objSS.Select acSelectionSetLast
            'objss.AddItems
            For Each objEntity In objSS
                objEntity.Rotate objMText.InsertionPoint, dRotation
                objEntity.Layer = strLayer
            Next objEntity
            
            objMText.Rotation = dRotation
            ThisDrawing.Regen acActiveViewport
        Case "AcDbText"
            Set objText = objEntity
            strLayer = objText.Layer
            
            dRotation = objText.Rotation
            objText.Rotation = 0
            objText.GetBoundingBox vMin, vMax
            vMin(0) = vMin(0) - 5
            vMin(1) = vMin(1) - 5
            vMax(0) = vMax(0) + 5
            vMax(1) = vMax(1) + 5
            
            strCommand = "revcloud r " & vMin(0) & "," & vMin(1) & " " & vMax(0) & "," & vMax(1) & " " & vbCr
            ThisDrawing.SendCommand strCommand
            
            objSS.Select acSelectionSetLast
            'objss.AddItems
            For Each objEntity In objSS
                objEntity.Rotate objText.TextAlignmentPoint, dRotation
                objEntity.Layer = strLayer
            Next objEntity
            
            objText.Rotation = dRotation
            ThisDrawing.Regen acActiveViewport
        Case Else
            MsgBox "Not text"
    End Select
    
    objSS.Clear
    objSS.Delete
    
    Me.show
End Sub

Private Sub cbRevisionNote_Click()
    Me.Hide
        Load Revision
            Revision.show
        Unload Revision
    Me.show
End Sub

Private Sub cbSave_Click()
    ThisDrawing.SendCommand "QSAVE" & vbCr
End Sub

Private Sub cbScope_Click()
    Me.Hide
            Load ScopeOfWork
            ScopeOfWork.show
            Unload ScopeOfWork
    Me.show
End Sub

Private Sub cbSendCommand_Click()
    Dim strCommand As String
    
    Me.Hide
    
    strCommand = ThisDrawing.Utility.GetString(True, "Enter AutoCAD Command or Alias: ")
    
    ThisDrawing.SendCommand strCommand & vbCr
    
    Me.show
End Sub

Private Sub cbSpidaFindPNumber_Click()
    Me.Hide
        Load SpidaAddPNumber
            SpidaAddPNumber.show
        Unload SpidaAddPNumber
    Me.show
End Sub

Private Sub cbSpidaminSearch_Click()
    Me.Hide
        Load SPIDAminSearch
            SPIDAminSearch.show
        Unload SPIDAminSearch
    Me.show
End Sub

Private Sub cbTabGeneric_Click()
    Me.Hide
        Load TabGeneric
            TabGeneric.show
        Unload TabGeneric
    Me.show
End Sub

Private Sub cbTDOT_Click()
    Me.Hide
        Load TDOT
            TDOT.show
        Unload TDOT
    Me.show
End Sub

Private Sub cbTDS_Click()
    Me.Hide
        Load TDSMainForm
            TDSMainForm.show
        Unload TDSMainForm
    Me.show
End Sub

Private Sub cbTemplates_Click()
    Me.Hide
        Load TemplateEditor
            TemplateEditor.show
        Unload TemplateEditor
    Me.show
End Sub

Private Sub cbTicket_Click()
    Me.Hide
        Load TroubleTicket
            TroubleTicket.show
        Unload TroubleTicket
    Me.show
End Sub

Private Sub cbTrim_Click()
'    Dim SSobj2 As AcadSelectionSet
'    Dim objTrim As AcadBlockReference
'    Dim attList As Variant
'    Dim filterType, filterValue As Variant
'    Dim grpCode(0) As Integer
'    Dim grpValue(0) As Variant
'    Dim entBlock As AcadEntity
'    Dim iCount As Integer
'
'    Me.hide
'    iCount = 0
'
'    grpCode(0) = 8
'    grpValue(0) = "_Annotations"
'    filterType = grpCode
'    filterValue = grpValue
'
'    Set SSobj2 = ThisDrawing.SelectionSets.Add("SSobj2")
'    SSobj2.Select acSelectionSetAll, , , filterType, filterValue
'
'    For Each entBlock In SSobj2
'        If Not entBlock.ObjectName = "AcDbBlockReference" Then GoTo Next_entBlock
'        Set objTrim = entBlock
'        If Not objTrim.Name = "__Trim" Then GoTo Next_entBlock
'
'        attList = objTrim.GetAttributes
'        attList(0).TextString = "T.T=" & attList(0).TextString & "'"
'        objTrim.Layer = "Integrity Notes"
'        objTrim.Update
'
'        iCount = iCount + 1
'Next_entBlock:
'    Next entBlock
'
'    SSobj2.Clear
'    SSobj2.Delete
'
'    MsgBox "Trim Blocks: " & iCount
'    Me.show
End Sub

Private Sub cbToCO_Click()
    Me.Hide
        Load PlaceToCO
            PlaceToCO.show
        Unload PlaceToCO
    Me.show
End Sub

Private Sub cbTrace_Click()
    Me.Hide
        Load TraceForm
            TraceForm.show
        Unload TraceForm
    Me.show
End Sub

Private Sub cbUnits_Click()
    Me.Hide
        Load UnitForm
        UnitForm.show
        Unload UnitForm
    Me.show
End Sub

Private Sub cbUnitTab_Click()
    Me.Hide
        Load TabGeneric
        TabGeneric.show
        Unload TabGeneric
    Me.show
End Sub

Private Sub cbUpdateAllSS_Click()
    Dim objSS1 As AcadSelectionSet
    Dim entBlock As AcadObject
    Dim obrTemp As AcadBlockReference
    Dim attItem2 As Variant
    Dim mode As Integer
    'Dim str As String
    Dim filterType, filterValue As Variant
    Dim grpCode(0) As Integer
    Dim grpValue(0) As Variant
    Dim str As String
    
  On Error Resume Next
    
    'str = ThisDrawing.Name
    'tbWO.Value = Left(str, 8)
    'str = Right(str, (Len(str) - 9))
    'tbProject.Value = Left(str, (Len(str) - 4))
    
    grpCode(0) = 8
    grpValue(0) = "Integrity Sheets"
    filterType = grpCode
    filterValue = grpValue
    
    Set objSS1 = ThisDrawing.SelectionSets.Add("objSS1")
    objSS1.Select acSelectionSetAll, , , filterType, filterValue
    
    For Each entBlock In objSS1
        'If TypeOf entBlock Is AcadBlockReference Then
            Set obrTemp = entBlock
        'Else
            'MsgBox "Error" & Err
            'GoTo exit_sub
        'End If
        
        If obrTemp.Name = "SS Info" Then
            attItem2 = obrTemp.GetAttributes
            attItem2(0).TextString = tbProject.Value
            attItem2(1).TextString = tbWO.Value
            attItem2(2).TextString = cbExchange.Value
            attItem2(3).TextString = tbRST.Value
            attItem2(4).TextString = cbCounty.Value
            attItem2(5).TextString = tbCity.Value
            attItem2(7).TextString = tbTotalDWG.Value
            
            obrTemp.Update
        End If
    Next entBlock
    
    Call SortLBItems
Exit_Sub:
    objSS1.Delete
End Sub

Private Sub cbUnnamedForm_Click()
    Me.Hide
        Load UnnamedForm
        UnnamedForm.show
        Unload UnnamedForm
    Me.show
End Sub

Private Sub cbUpdateAncGuy_Click()
    Me.Hide
        Call UpdateAnchors
    Me.show
End Sub

Private Sub cbValidate_Click()
    Me.Hide
        Load ValidateFielding
        ValidateFielding.show
        Unload ValidateFielding
    Me.show
End Sub

Private Sub cbValidateAttach_Click()
    Me.Hide
        Load ValidateAttachments
        ValidateAttachments.show
        Unload ValidateAttachments
    Me.show
End Sub

Private Sub cbValidateCounts_Click()
    Me.Hide
        Load ValidateCounts
        ValidateCounts.show
        Unload ValidateCounts
    Me.show
End Sub

Private Sub cbValidateCustomers_Click()
    Me.Hide
        Load ValidateCustomers
        ValidateCustomers.show
        Unload ValidateCustomers
    Me.show
End Sub

Private Sub cbValidateHO1_Click()
    Me.Hide
        Load ValidateHO1
        ValidateHO1.show
        Unload ValidateHO1
    Me.show
End Sub

Private Sub cbValidateMCL_Click()
    Me.Hide
        Load ValidateMCL
        ValidateMCL.show
        Unload ValidateMCL
    Me.show
End Sub

Private Sub cbValidateML_Click()
    Me.Hide
        Load ValidateML
        ValidateML.show
        Unload ValidateML
    Me.show
End Sub

Private Sub cbVerifyAsFielded_Click()
    Me.Hide
        'Load CheckFieldedPoles
        'CheckFieldedPoles.show
        'Unload CheckFieldedPoles
        Load ValidateAttachments
        ValidateAttachments.show
        Unload ValidateAttachments
    Me.show
End Sub

Private Sub cbVerifyAttCallouts_Click()
    Me.Hide
        Load VerifyAttachmentCallouts
            VerifyAttachmentCallouts.show
        Unload VerifyAttachmentCallouts
    Me.show
End Sub

Private Sub cbVerifyBores_Click()
    Me.Hide
        Load ValidateBores
            ValidateBores.show
        Unload ValidateBores
    Me.show
End Sub

Private Sub cbVerifyHC_Click()
    Me.Hide
    Load CheckHC
    CheckHC.show
    Unload CheckHC
    Me.show
End Sub

Private Sub cbVerifyUnits_Click()
    Me.Hide
        Load VerifyUnits
            VerifyUnits.show
        Unload VerifyUnits
    Me.show
End Sub

Private Sub cbVHLE_Click()
    Me.Hide
    Load DesignVHLE
    DesignVHLE.show
    Unload DesignVHLE
    Me.show
End Sub

Private Sub cbWorkload_Click()
    Me.Hide
        Load WorkloadForm
            WorkloadForm.show
        Unload WorkloadForm
    Me.show
End Sub

Private Sub CommandButton1_Click()
    Me.Hide
    Load OtherSubsPoles
    OtherSubsPoles.show
    Unload OtherSubsPoles
    Me.show
End Sub

Private Sub CommandButton2_Click()
    Me.Hide
    Load zMisc
    zMisc.show
    Unload zMisc
    Me.show
End Sub

Private Sub CommandButton3_Click()
    Me.Hide
        Load PlaceCountCallouts
        PlaceCountCallouts.show
        Unload PlaceCountCallouts
    Me.show
End Sub

Private Sub Label3_Click()
    Dim objObject As AcadObject
    Dim obrGP2 As AcadBlockReference
    Dim basePnt, attItem As Variant
    
    Me.Hide
  On Error Resume Next
    
    ThisDrawing.Utility.GetEntity objObject, basePnt, "Select SS Info: "
    If TypeOf objObject Is AcadBlockReference Then
        Set obrGP2 = objObject
    Else
        Me.show
        Exit Sub
    End If
    attItem = obrGP2.GetAttributes
    
    tbProject.Value = attItem(0).TextString
    tbWO.Value = attItem(1).TextString
    cbExchange.Value = attItem(2).TextString
    tbRST.Value = attItem(3).TextString
    cbCounty.Value = attItem(4).TextString
    tbCity.Value = attItem(5).TextString
    tbTotalDWG = attItem(7).TextString
    
    Me.show
End Sub

Private Sub Label5_Click()
    Dim objObject As AcadObject
    Dim obrGP2 As AcadBlockReference
    Dim basePnt, attItem As Variant
    
    Me.Hide
  On Error Resume Next
    
    ThisDrawing.Utility.GetEntity objObject, basePnt, "Select SS Info: "
    If TypeOf objObject Is AcadBlockReference Then
        Set obrGP2 = objObject
    Else
        Me.show
        Exit Sub
    End If
    attItem = obrGP2.GetAttributes
    
    cbExchange.Value = attItem(2).TextString
    tbRST.Value = attItem(3).TextString
    cbCounty.Value = attItem(4).TextString
    tbCity.Value = attItem(5).TextString
    
    Me.show
End Sub

Private Sub CommandButton4_Click()
    Me.Hide
        Load TransferToMap
        TransferToMap.show
        Unload TransferToMap
    Me.show
End Sub

Private Sub CommandButton5_Click()
    Me.Hide
        Load ReplaceF1
            ReplaceF1.show
        Unload ReplaceF1
    Me.show
End Sub

Private Sub CommandButton6_Click()
    Dim vPnt1, vPnt2 As Variant
    Dim grpCode(0) As Integer
    Dim grpValue(0) As Variant
    Dim filterType, filterValue As Variant
    Dim objSS As AcadSelectionSet
    Dim obj3DPoly As Acad3DPolyline
    Dim obj2DPoly As AcadLWPolyline
    Dim v3DCoords As Variant
    Dim iCount, i2D, iTemp As Integer
    Dim strLayer As String
    
    Me.Hide
    
    On Error Resume Next
    
    Err = 0
    vPnt1 = ThisDrawing.Utility.GetPoint(, "Get BL Corner: ")
    vPnt2 = ThisDrawing.Utility.GetCorner(vPnt1, vbCr & "Get UR Corner: ")
    If Not Err = 0 Then
        Me.show
        Exit Sub
    End If
    
    grpCode(0) = 0
    grpValue(0) = "Polyline"
    filterType = grpCode
    filterValue = grpValue
    
    Err = 0
    Set objSS = ThisDrawing.SelectionSets.Add("objSS")
    If Not Err = 0 Then
        Set objSS = ThisDrawing.SelectionSets.Item("objSS")
        objSS.Clear
    End If
    objSS.Select acSelectionSetWindow, vPnt1, vPnt2, filterType, filterValue
    
    MsgBox "3D Polyline Count = " & objSS.count
    
    For Each obj3DPoly In objSS
        strLayer = obj3DPoly.Layer
        
        v3DCoords = obj3DPoly.Coordinates
        
        iCount = (UBound(v3DCoords) + 1) * 2 / 3
        ReDim d2dcoords(iCount - 1) As Double
        
        iTemp = 0
        i2D = 0
        For i = 0 To UBound(v3DCoords)
            If iTemp = 2 Then
                iTemp = 0
            Else
                d2dcoords(i2D) = v3DCoords(i)
                iTemp = iTemp + 1
                i2D = i2D + 1
            End If
        Next i
        
        Set obj2DPoly = ThisDrawing.ModelSpace.AddLightWeightPolyline(d2dcoords)
        obj2DPoly.Layer = strLayer
        obj2DPoly.Update
        
        obj3DPoly.Layer = "Integrity Delete"
    Next obj3DPoly
    
    
    objSS.Clear
    objSS.Delete
    
    Me.show
End Sub

Private Sub ConvertSPOle_Click()
    Me.Hide
        Load ConvertToSPole
        ConvertToSPole.show
        Unload ConvertToSPole
    Me.show
End Sub

Private Sub lbSheets_DblClick(ByVal Cancel As MSForms.ReturnBoolean)
    Dim str As String
    Dim strArray As Variant
    Dim viewCoordsB(0 To 2) As Double
    Dim viewCoordsE(0 To 2) As Double
    
    Me.Hide
    
    str = lbSheets.List(lbSheets.ListIndex)
    strArray = Split(str, vbTab)
    
    viewCoordsB(0) = strArray(2)
    viewCoordsB(1) = strArray(3)
    viewCoordsB(2) = 0#
    viewCoordsE(0) = viewCoordsB(0) + 1650 * CDbl(strArray(1))
    viewCoordsE(1) = viewCoordsB(1) + 1050 * CDbl(strArray(1))
    viewCoordsE(2) = 0#
    
    ThisDrawing.Application.ZoomWindow viewCoordsB, viewCoordsE
    Me.show
End Sub

Private Sub SortLBItems()
    Dim strArrayList(), strArraySorted() As String
    Dim attArray, attItem As Variant
    Dim str1, str2, strItem As String
    Dim i, iDWGNum, test1 As Integer
    
  On Error Resume Next
    test1 = 0
    ReDim strArraySorted(0 To lbSheets.ListCount)
    
    For i = 0 To lbSheets.ListCount - 1
        str1 = lbSheets.List(i)
        attArray = Split(str1, vbTab)
        str2 = Right(attArray(0), 3)
        
        If str2 = "" Then GoTo Next_I
        If str2 = "MAP" Then
            iDWGNum = 0
        Else
            iDWGNum = CInt(str2)
        End If
        
        If iDWGNum > test1 Then test1 = iDWGNum
        
        strArraySorted(iDWGNum) = str1
Next_I:
    Next i
    
    lbSheets.Clear
    For i = 0 To test1
        lbSheets.AddItem strArraySorted(i)
    Next i
End Sub

Private Sub LDwgScale_Click()
    Dim entPole As AcadObject
    Dim basePnt As Variant
    
    Me.Hide
  On Error Resume Next
    
    ThisDrawing.Utility.GetEntity entPole, basePnt, "Left Click to Exit: "
    
    Me.show
End Sub

Private Sub UserForm_Initialize()
    
    cbScale.AddItem "50"
    cbScale.AddItem "75"
    cbScale.AddItem "100"
    
  On Error Resume Next
    
    Dim objSS1 As AcadSelectionSet
    Dim entBlock As AcadObject
    Dim obrTemp As AcadBlockReference
    Dim attItem2, vTemp As Variant
    Dim mode As Integer
    'Dim str As String
    Dim filterType, filterValue As Variant
    Dim grpCode(0) As Integer
    Dim grpValue(0) As Variant
    Dim str As String
    
    str = ThisDrawing.Name
    tbWO.Value = Left(str, 8)
    str = Right(str, (Len(str) - 9))
    tbProject.Value = Left(str, (Len(str) - 4))
    
    grpCode(0) = 8
    grpValue(0) = "Integrity Sheets"
    filterType = grpCode
    filterValue = grpValue
    
    Set objSS1 = ThisDrawing.SelectionSets.Add("objSS1")
    objSS1.Select acSelectionSetAll, , , filterType, filterValue
    
    For Each entBlock In objSS1
        'If TypeOf entBlock Is AcadBlockReference Then
            Set obrTemp = entBlock
        'Else
            'MsgBox "Error" & Err
            'GoTo exit_sub
        'End If
        
        If obrTemp.Name = "SS-11x17" Then
            attItem2 = obrTemp.GetAttributes
            vTemp = Split(attItem2(0).TextString, " ")
            'If Not (vTemp(0) = "DWG") Then GoTo Next_entBlock
            Select Case vTemp(0)
                Case "DWG"
                Case "MAP"
                Case "PMT"
                    GoTo Next_entBlock
                'Case Else
                '    GoTo Next_entBlock
            End Select
            'If Not vTemp(0) = "DWG" Then
            '    If vTemp(0) = "MAP" Or vTemp(1) = "MAP" Then
            '    GoTo Next_entBlock
            '
            'End If
                
            str = attItem2(0).TextString & vbTab & obrTemp.XScaleFactor
            str = str & vbTab & obrTemp.InsertionPoint(0) & vbTab & obrTemp.InsertionPoint(1)
            lbSheets.AddItem str
        End If
Next_entBlock:
    Next entBlock
    
    Call SortLBItems
Exit_Sub:
    objSS1.Delete
End Sub

Private Sub UpdateAnchors()
    Dim dTotal, dFeet, dInch As Double
    Dim iFeet, iInch As Integer
    Dim entPole As AcadObject
    Dim obrGP As AcadBlockReference
    Dim attItem, basePnt, vList As Variant
    Dim insertPnt As Variant
    Dim strLH, strPull As String
    Dim vList2 As Variant
    Dim strTemp, strBlockName As String
    Dim vLH As Variant
    Dim dScale, dRotate As Double
    Dim layerObj As AcadLayer
    
    'Me.hide
On Error Resume Next

update_block:
    Err = 0
    
    ThisDrawing.Utility.GetEntity entPole, basePnt, "Select Guy or Anchor: "
    If Not Err = 0 Then GoTo Exit_Sub
    
    If TypeOf entPole Is AcadBlockReference Then
        Set obrGP = entPole
    Else
        GoTo Exit_Sub
    End If
    
    attItem = obrGP.GetAttributes
    
    Select Case obrGP.Name
        Case "ExGuyOR", "ExGuyOL"
            Load ConUpdateGuy
            
            If Not attItem(2).TextString = "" Then
                vLH = Split(attItem(2).TextString, "/")
                ConUpdateGuy.tbLead.Value = vLH(0)
                ConUpdateGuy.tbHeight.Value = vLH(1)
            End If
            
            ConUpdateGuy.show
            
            attItem(2).TextString = ConUpdateGuy.tbLead.Value & "/" & ConUpdateGuy.tbHeight.Value
            attItem(3).TextString = "PE1-3G"
            
            Unload ConUpdateGuy
        Case "ExAncOR", "ExAncOL"
            attItem(0).TextString = "PF1-5A"
    End Select
    obrGP.Update

    GoTo update_block
    
Exit_Sub:
End Sub

Private Sub DropCallout()
    Dim amap As AcadMap
    Dim ODRcs As ODRecords
    Dim tbl As ODTable
    Dim tbls As ODTables
    Dim boolVal As Boolean
    Dim entPole As AcadEntity
    Dim objLWP As AcadLWPolyline
    Dim objPolyline As AcadPolyline
    Dim objLine As AcadLine
    Dim obrDrop As AcadBlockReference
    Dim objBlock As AcadBlockReference
    Dim attItem, vBasePnt As Variant
    Dim strType, strLength As String
    Dim strTemp As String
    Dim dRotate, dScale, Pi As Double
    Dim dTest, dDistScale As Double
    Dim dInsertPnt(0 To 2) As Double
    Dim dStartPnt(0 To 2) As Double
    Dim dEndPnt(0 To 2) As Double
    Dim dToText(0 To 2) As Double
    Dim dFromText(0 To 2) As Double
    Dim dDiff(0 To 2) As Double
    Dim vStartPnt, vEndPnt As Variant
    Dim vCoords, vAttList As Variant
    Dim layerObj As AcadLayer
    Dim iPosition, iLength As Integer
    
    'Me.Hide
  On Error Resume Next
  
    Pi = 3.14159265359
    
    Set amap = ThisDrawing.Application.GetInterfaceObject("AutoCADMap.Application")
    
    Set tbls = amap.Projects(ThisDrawing).ODTables
    
get_Drop:

    dScale = cbScale.Value / 100
    If dScale = 0 Then dScale = 1#
    
    Err = 0
    
    ThisDrawing.Utility.GetEntity entPole, vBasePnt, "Select Drop: "
    
    If Not Err = 0 Then GoTo Exit_Sub
    
    Select Case entPole.ObjectName
        Case "AcDbLine"
            Set objLine = entPole
            iLength = CInt(objLine.Length)
            vStartPnt = objLine.StartPoint
            vEndPnt = objLine.EndPoint
            
            dDiff(0) = vEndPnt(0) - vStartPnt(0)
            dDiff(1) = vEndPnt(1) - vStartPnt(1)
            dDiff(2) = (dDiff(0) * dDiff(0)) + (dDiff(1) * dDiff(1))
            dDiff(2) = Sqr(dDiff(2))
            
            If vBasePnt(0) > vStartPnt(0) Then
                dToText(0) = vBasePnt(0) - vStartPnt(0)
                dToText(1) = vBasePnt(1) - vStartPnt(1)
            Else
                dToText(0) = vStartPnt(0) - vBasePnt(0)
                dToText(1) = vStartPnt(1) - vBasePnt(1)
            End If
            dToText(2) = Sqr((dToText(0) * dToText(0)) + (dToText(1) * dToText(1)))
            
            dDistScale = dToText(2) / dDiff(2)
            dInsertPnt(0) = vStartPnt(0) + (dDiff(0) * dDistScale)
            dInsertPnt(1) = vStartPnt(1) + (dDiff(1) * dDistScale)
            dInsertPnt(2) = 0#
            
            If dToText(0) = 0 Then
                dRotate = Pi / 2
            Else
                dRotate = Atn(dDiff(1) / dDiff(0))
            End If
            
            iPosition = 34
            
            Select Case objLine.Layer
                Case "Integrity Drops-Aerial", "OHSecondary", "OH_Secondary", "F-DROP-A-E"
                    strType = "SEAO"
                Case Else
                    strType = "SEBO"
            End Select
            
            strLength = iLength
            
        Case "AcDbPolyline"
            Set objLWP = entPole
            iLength = CInt(objLWP.Length)
            vCoords = objLWP.Coordinates
            
            For i = 3 To UBound(vCoords) Step 2
                dDiff(0) = vCoords(i - 1) - vCoords(i - 3)
                dDiff(1) = vCoords(i) - vCoords(i - 2)
                dDiff(2) = Sqr((dDiff(0) * dDiff(0)) + (dDiff(1) * dDiff(1)))
            
                dToText(0) = vBasePnt(0) - vCoords(i - 3)
                dToText(1) = vBasePnt(1) - vCoords(i - 2)
                dToText(2) = Sqr((dToText(0) * dToText(0)) + (dToText(1) * dToText(1)))
                
                If dDiff(2) > dToText(2) Then
                    dFromText(0) = vBasePnt(0) - vCoords(i - 1)
                    dFromText(1) = vBasePnt(1) - vCoords(i)
                    dFromText(2) = Sqr((dFromText(0) * dFromText(0)) + (dFromText(1) * dFromText(1)))
                    
                    dTemp = (dFromText(2) + dToText(2)) / dDiff(2)
                    If dTemp < 1.01 Then
                        GoTo Exit_First_Next
                    End If
                End If
            Next i
Exit_First_Next:
            
            dDistScale = Abs(dToText(2) / dDiff(2))
            dInsertPnt(0) = vCoords(i - 3) + (dDiff(0) * dDistScale)
            dInsertPnt(1) = vCoords(i - 2) + (dDiff(1) * dDistScale)
            dInsertPnt(2) = 0#
            
            If dToText(0) = 0 Then
                dRotate = Pi / 2
            Else
                dRotate = Atn(dDiff(1) / dDiff(0))
            End If
            
            Select Case objLWP.Layer
                Case "Integrity Drops-Aerial", "OHSecondary", "OH_Secondary", "F-DROP-A-E"
                    strType = "SEAO"
                Case Else
                    strType = "SEBO"
            End Select
            
            strLength = iLength
            
        Case "AcDbBlockReference"
            Set objBlock = entPole
            
            Select Case objBlock.Name
                Case "Drop"
                    vAttList = objBlock.GetAttributes
                    strTemp = vAttList(0).TextString
                    If InStr(strTemp, "-") > 0 Then
                        vCoords = Split(strTemp, "-")
                        vCoords(0) = CInt(vCoords(0)) + 1
                        vAttList(0).TextString = vCoords(0) & "-" & vCoords(1)
                    Else
                        vAttList(0).TextString = "2-" & vAttList(0).TextString
                    End If
                    
                    objBlock.Update
                Case Else
                    Me.show
                    Exit Sub
            End Select
            
            GoTo get_Drop
        Case Else
            MsgBox entPole.ObjectName
            Me.show
            Exit Sub
    End Select

    Err = 0
    Set obrDrop = ThisDrawing.ModelSpace.InsertBlock(dInsertPnt, "Drop", dScale, dScale, dScale, dRotate)
    If Not Err = 0 Then MsgBox Err.desription
    If strType = "SEAO" Then
        obrDrop.Layer = "Integrity Drops-Aerial Text"
    Else
        obrDrop.Layer = "Integrity Drops-Buried Text"
    End If
    
    vAttList = obrDrop.GetAttributes
    vAttList(0).TextString = strType
    vAttList(1).TextString = strLength & "'"
    obrDrop.Update
    
    GoTo get_Drop
Exit_Sub:

End Sub

Private Sub DeleteDropCallouts()
    Me.Hide
    
    Dim result As Integer
    
    result = MsgBox("Are you sure you want to delete all drop callouts?", vbYesNo, "Delete Drop Callouts")
    If result = vbNo Then
        Me.show
    End If
    
    Dim vDwgLL, vDwgUR As Variant
    Dim filterType, filterValue As Variant
    Dim grpCode(0) As Integer
    Dim grpValue(0) As Variant
    Dim objSS As AcadSelectionSet
    Dim objBlock As AcadBlockReference
    Dim vAtt As Variant
    
    vDwgLL = ThisDrawing.Utility.GetPoint(, "Get DWG LL Corner: ")
    vDwgUR = ThisDrawing.Utility.GetCorner(vDwgLL, vbCr & "Get DWG UR Corner: ")
    
    grpCode(0) = 2
    grpValue(0) = "Drop"
    filterType = grpCode
    filterValue = grpValue
    
    Set objSS = ThisDrawing.SelectionSets.Add("objSS")
    objSS.Select acSelectionSetWindow, vDwgLL, vDwgUR, filterType, filterValue
    If objSS.count < 1 Then GoTo Exit_Sub
    
    For Each objBlock In objSS
        Select Case objBlock.Layer
            Case "Integrity Drops-Aerial Text", "Integrity Drops-Buried Text"
                objBlock.Delete
        End Select
    Next objBlock
    
Exit_Sub:
    objSS.Clear
    objSS.Delete
    
    ThisDrawing.Regen acAllViewports
    
    Me.show
End Sub

Attribute VB_Name = "MainForm2"
Attribute VB_Base = "0{049A2EBC-E88F-4E14-A446-B3617CD716F0}{6CFEAA7E-14D0-4B14-A67A-02C9E69AB24F}"
Attribute VB_GlobalNameSpace = False
Attribute VB_Creatable = False
Attribute VB_PredeclaredId = True
Attribute VB_Exposed = False
Attribute VB_TemplateDerived = False
Attribute VB_Customizable = False
'Dim strUsageReport As String

Private Sub AddCLR_Click()
    Me.Hide
        Load AddClearances
        AddClearances.show
        Unload AddClearances
    Me.show
End Sub

Private Sub cbAddBldgs_Click()
    Me.Hide
        Load AddBLDGForm
        AddBLDGForm.show
        Unload AddBLDGForm
    Me.show
End Sub

Private Sub cbAddExistingGuys_Click()
    Dim filterType, filterValue As Variant
    Dim grpCode(0) As Integer
    Dim grpValue(0) As Variant
    Dim objSS As AcadSelectionSet
    Dim objBlock As AcadBlockReference
    Dim objAnchor As AcadBlockReference
    Dim vCoords As Variant
    Dim dRotate, dCoords(2) As Double
    
    On Error Resume Next
    
    grpCode(0) = 2
    grpValue(0) = "ExGuyOR,ExGuyOL"
    filterType = grpCode
    filterValue = grpValue
    
    Set objSS = ThisDrawing.SelectionSets.Add("objSS")
    If Not Err = 0 Then
        Set objSS = ThisDrawing.SelectionSets.Item("objSS")
        objSS.Clear
    End If
    
    objSS.Select acSelectionSetAll, , , filterType, filterValue
    
    For Each objBlock In objSS
        dRotate = objBlock.Rotation
        vCoords = objBlock.InsertionPoint
        
        Select Case objBlock.Name
            Case "ExGuyOR"
                dRotate = dRotate - (3.14159265359 / 2)
            Case "ExGuyOL"
                dRotate = dRotate + (3.14159265359 / 2)
        End Select
        
        dCoords(0) = vCoords(0) + (15 * Cos(dRotate))
        dCoords(1) = vCoords(1) + (15 * Sin(dRotate))
        dCoords(2) = 0#
        
        Set objAnchor = ThisDrawing.ModelSpace.InsertBlock(dCoords, "Existing_Guys", 1#, 1#, 1#, objBlock.Rotation)
        objAnchor.Layer = "Integrity Existing-Guys"
        objAnchor.Update
    Next objBlock
    
Exit_Sub:
    objSS.Clear
    objSS.Delete

End Sub

Private Sub cbAddOHG_Click()
    Dim entPole As AcadObject
    Dim obrGP As AcadBlockReference
    Dim obrTemp As AcadBlockReference
    Dim attItem, attList, basePnt As Variant
    Dim lwpObj As AcadLWPolyline
    Dim lwpCoords(0 To 3) As Double
    Dim strFromPole, strToPole As String
    Dim vCoords As Variant
    Dim dFromCoords(0 To 2), dToCoords(0 To 2) As Double
    Dim dInsertionPnt(0 To 2) As Double
    Dim dTemp, Pi  As Double
    Dim dX, dY, dRotate, dScale, dDistance As Double
    Dim strBlock, strRUS, strTemp As String
    Dim layerObj As AcadLayer
    
    Me.Hide
  On Error Resume Next
    Pi = 3.14159265359
  
   dScale = CDbl(MainForm.cbScale.Value) / 100
   If Err <> 0 Then dScale = 1#
  
    ThisDrawing.Utility.GetEntity entPole, basePnt, "From Pole: "
    If TypeOf entPole Is AcadBlockReference Then
        Set obrGP = entPole
    Else
        MsgBox "Not a valid pole."
        Exit Sub
    End If
    
    dFromCoords(0) = obrGP.InsertionPoint(0)
    dFromCoords(1) = obrGP.InsertionPoint(1)
    dFromCoords(2) = 0#
    
    ThisDrawing.Utility.GetEntity entPole, basePnt, "To Pole: "
    If TypeOf entPole Is AcadBlockReference Then
        Set obrGP = entPole
    Else
        MsgBox "Not a valid pole."
        Exit Sub
    End If
    
    dToCoords(0) = obrGP.InsertionPoint(0)
    dToCoords(1) = obrGP.InsertionPoint(1)
    dToCoords(2) = 0#
    
    dInsertionPnt(0) = (dFromCoords(0) + dToCoords(0)) / 2
    dInsertionPnt(1) = (dFromCoords(1) + dToCoords(1)) / 2
    dInsertionPnt(2) = 0#
    
    Select Case (dToCoords(0) - dFromCoords(0))
        Case Is < 0
            dX = (dFromCoords(0) - dToCoords(0))
            dY = (dFromCoords(1) - dToCoords(1))
            dRotate = Atn(dY / dX) + Pi
            strBlock = "ohgL"
        Case Is > 0
            dX = (dToCoords(0) - dFromCoords(0))
            dY = (dToCoords(1) - dFromCoords(1))
            dRotate = Atn(dY / dX)
            strBlock = "ohgR"
        Case Else
            dRotate = 0
            strBlock = "ohgR"
    End Select
    
    dDistance = Sqr((dX * dX) + (dY * dY))
    dDistance = Round(dDistance)
    
    Set layerObj = ThisDrawing.Layers.Add("Integrity Guys")
    ThisDrawing.ActiveLayer = layerObj
    
    Set obrTemp = ThisDrawing.ModelSpace.InsertBlock(dInsertionPnt, strBlock, dScale, dScale, dScale, dRotate)

    attList = obrTemp.GetAttributes
    
    attList(0).TextString = dDistance & "'"
    attList(1).TextString = "PE2-3G"
    
    lwpCoords(0) = dFromCoords(0)
    lwpCoords(1) = dFromCoords(1)
    lwpCoords(2) = dToCoords(0)
    lwpCoords(3) = dToCoords(1)
    
    Set lwpObj = ThisDrawing.ModelSpace.AddLightWeightPolyline(lwpCoords)
    lwpObj.Update
    
    ThisDrawing.Utility.GetEntity entPole, basePnt, vbCr & "Select block to add units:"
    
    Set obrTemp = entPole
    
    If obrTemp.Name = "sPole" Then
        attList = obrTemp.GetAttributes
            
        If attList(27).TextString = "" Then
            attList(27).TextString = "+PE2-3G=" & dDistance & "'"
        Else
            attList(27).TextString = attList(27).TextString & ";;+PE2-3G=" & dDistance & "'"
        End If
        
        obrTemp.Update
    End If
    
    Me.show
End Sub

Private Sub cbAddSheets_Click()
    'Dim layerObj As AcadLayer
  'On Error Resume Next
    'Set layerObj = ThisDrawing.Layers.Add("Integrity Sheets")
    'ThisDrawing.ActiveLayer = layerObj
    
    Dim entPole As AcadObject
    Dim obrGSS As AcadBlockReference
    Dim obrSSInfo As AcadBlockReference
    Dim obrSSDWG1 As AcadBlockReference
    Dim attItem, attItem1, basePnt, returnPnt As Variant
    Dim vEmail As Variant
    Dim insertPnt(0 To 2) As Double
    Dim dScale As Double
    Dim iDWGNum, iNextNum As Long
    Dim str, str2 As String
    
    Me.Hide
  On Error Resume Next
  
    iNextNum = 1
    
While Err = 0
    ThisDrawing.Utility.GetEntity entPole, basePnt, "Select Staking Sheet: "
    If TypeOf entPole Is AcadBlockReference Then
        Set obrGSS = entPole
    Else
        GoTo Exit_Sub
        'Me.show
        'Exit Sub
    End If
    
    If Not Err = 0 Then GoTo Exit_Sub
    If Not obrGSS.Name = "SS-11x17" Then GoTo Exit_Sub
    
    obrGSS.Layer = "Integrity Sheets"
    attItem = obrGSS.GetAttributes
    iDWGNum = ThisDrawing.Utility.GetInteger(vbCr & "Enter Drawing Number(" & iNextNum & "): ")
    If Err < 0 Then iDWGNum = iNextNum
    iNextNum = iDWGNum + 1
    
    Select Case iDWGNum
        Case Is < 10
            attItem(0).TextString = "DWG 00" & iDWGNum
        Case Is > 99
            attItem(0).TextString = "DWG " & iDWGNum
        Case Else
            attItem(0).TextString = "DWG 0" & iDWGNum
    End Select
    
    obrGSS.Update
    dScale = obrGSS.XScaleFactor
    
    lbSheets.AddItem iDWGNum & vbTab & dScale & vbTab & obrGSS.Name & vbTab & obrGSS.InsertionPoint(0) & vbTab & obrGSS.InsertionPoint(1)
  
    insertPnt(0) = obrGSS.InsertionPoint(0) + 20 * dScale
    insertPnt(1) = obrGSS.InsertionPoint(1) + 20 * dScale
    insertPnt(2) = obrGSS.InsertionPoint(2)
    
    Set obrSSInfo = ThisDrawing.ModelSpace.InsertBlock(insertPnt, "ss info", dScale, dScale, dScale, 0#)
    obrSSInfo.Layer = "Integrity Sheets"
    
    attItem = obrSSInfo.GetAttributes
    attItem(0).TextString = tbProject.Value
    attItem(1).TextString = tbWO.Value
    attItem(2).TextString = cbExchange.Value
    attItem(3).TextString = tbRST.Value
    attItem(4).TextString = cbCounty.Value
    attItem(5).TextString = tbCity.Value
    attItem(6).TextString = iDWGNum
    attItem(7).TextString = tbTotalDWG.Value
    obrSSInfo.Update
    
    If iDWGNum = 1 Then
        insertPnt(0) = obrGSS.InsertionPoint(0) + 20 * dScale
        insertPnt(1) = obrGSS.InsertionPoint(1) + 280 * dScale
        insertPnt(2) = obrGSS.InsertionPoint(2)
    
        Set obrSSDWG1 = ThisDrawing.ModelSpace.InsertBlock(insertPnt, "ss dwg1", dScale, dScale, dScale, 0#)
        obrSSDWG1.Layer = "Integrity Sheets"
    
        attItem1 = obrSSDWG1.GetAttributes
        
        vEmail = Split(cbDesigner.Value, " ")
        str2 = LCase(vEmail(0)) & "." & LCase(vEmail(1)) & "@integrity-us.com"
        str = cbDesigner.Value & "\P" & str2 & "\P" & tbPhoneNumber.Value & "\P"
        'Select Case cbDesigner.Value
        '    Case "Dylan Spears"
        '        str = "Dylan Spears\Pdylan.spears@integrity-us.com\P" & tbPhoneNumber.Value & "\P"
        '    Case "Jeremy Pafford"
        '        str = "Jeremy Pafford\Pjeremy.pafford@integrity-us.com\P(931)698-1992\P"
        '    Case "Ronn Elliott"
        '        str = "Ronn Elliott\Pronn.elliott@integrity-us.com\P(615)419-5421\P"
        '    Case "Rich Taylor"
        '        str = "Rich Taylor\Prich.taylor@integrity-us.com\P(615)785-2032\P"
        '    Case "Ronn Elliott"
        '        str = "Jason Pafford\Pjason.pafford@integrity-us.com\P(931)209-3269\P"
        'End Select
        str = str & "730 Middle Tennessee Blvd - Suite 6\PMurfreesboro, TN 37130"
        attItem1(0).TextString = str
        obrSSDWG1.Update
    End If
    Err = 0
Wend
    layerObj.Delete
    
Exit_Sub:
    Set layerObj = ThisDrawing.Layers.Add("0")
    ThisDrawing.ActiveLayer = layerObj
    Me.show
End Sub

Private Sub cbAddTerminals_Click()
    Me.Hide
    Load DesignTermForm
    DesignTermForm.show
    Unload DesignTermForm
    Me.show
End Sub

Private Sub cbAddUnits_Click()
    Me.Hide
        Load AddRemoveUnits
        AddRemoveUnits.show
        Unload AddRemoveUnits
    Me.show
End Sub

Private Sub cbAnchorGuys_Click()
    Dim startPnt(0 To 2), midPnt(0 To 2), endPnt(0 To 2) As Double
    Dim firstAng, endAng, defAng, rotateAng, ancAng, pull, tempPull As Double
    Dim X(0 To 2), Y(0 To 2), Z(0 To 2) As Double
    Dim dScale As Double
    Dim objBlock As AcadBlockReference
    Dim objBlock2 As AcadBlockReference
    Dim objTemp As AcadBlockReference
    Dim returnPoint, vAttList, insertPnt As Variant
    Dim n, result, iDirection As Integer  'iDirection 0=L 1=R
    Dim str, str2 As String
    'Dim layerObj As AcadLayer
    Dim strPull, strResult As String
    Dim vPoleCoords As Variant
    Dim objEntity As AcadEntity
    'Dim obrGP As AcadBlockReference
    Dim attItem, basePnt As Variant
    Dim Pi As Double
    
    Pi = 3.14159265359
    Me.Hide
On Error Resume Next

Place_Anchor:
    
    Err = 0
    ThisDrawing.Utility.GetEntity objEntity, basePnt, "Select Pole: "
    If Not Err = 0 Then GoTo Exit_Sub
    
    If TypeOf objEntity Is AcadBlockReference Then
        Set objBlock = objEntity
    Else
        'MsgBox "Not a valid pole."
        Me.show
        Exit Sub
    End If
    vPoleCoords = objBlock.InsertionPoint
    
    X(0) = vPoleCoords(0)
    Y(0) = vPoleCoords(1)
    
    ThisDrawing.Utility.GetEntity objEntity, basePnt, "Get Backspan Pole: "
    If Not Err = 0 Then GoTo Exit_Sub
    
    If TypeOf objEntity Is AcadBlockReference Then
        Set objBlock2 = objEntity
    Else
        'MsgBox "Not a valid pole."
        Me.show
        Exit Sub
    End If
    vPoleCoords = objBlock2.InsertionPoint
    
    X(1) = vPoleCoords(0)
    Y(1) = vPoleCoords(1)
    
    ThisDrawing.Utility.GetEntity objEntity, basePnt, "Get Frontspan Pole: "
    If Not Err = 0 Then GoTo Exit_Sub
    
    If TypeOf objEntity Is AcadBlockReference Then
        Set objBlock2 = objEntity
    Else
        'MsgBox "Not a valid pole."
        Me.show
        Exit Sub
    End If
    vPoleCoords = objBlock2.InsertionPoint
    
    
    X(2) = vPoleCoords(0)
    Y(2) = vPoleCoords(1)
    
    If (X(1) - X(0)) = 0 Then
        If (Y(1) - Y(0)) < 0 Then
            firstAng = 3 * Pi / 2
        Else
            firstAng = Pi / 2
        End If
    Else
        firstAng = Math.Atn((Y(1) - Y(0)) / (X(1) - X(0)))
        If (X(1) - X(0)) < 0 Then
            firstAng = Pi + firstAng
        ElseIf (Y(1) - Y(0)) < 0 Then
            firstAng = 2 * Pi + firstAng
        End If
    End If
    
    If (X(2) - X(0)) = 0 Then
        If (Y(2) - Y(0)) < 0 Then
            firstAng = 3 * Pi / 2
        Else
            firstAng = Pi / 2
        End If
    Else
        endAng = Math.Atn((Y(2) - Y(0)) / (X(2) - X(0)))
        If (X(2) - X(0)) < 0 Then
            endAng = Pi + endAng
        ElseIf (Y(2) - Y(0)) < 0 Then
            endAng = 2 * Pi + endAng
        End If
    End If
    
    rotateAng = (endAng + firstAng) / 2
    If Math.Abs(endAng - firstAng) < Pi Then
        rotateAng = rotateAng - Pi
    End If
        
    If rotateAng < 0 Then rotateAng = rotateAng + (2 * Pi)
    If rotateAng > (2 * Pi) Then rotateAng = rotateAng - (2 * Pi)
    
    defAng = firstAng + Pi - endAng
    pull = Math.Round(Math.Abs(100 * Math.Sin(defAng / 2)))
    
    If pull >= 50 Then  '<------------------------------------- Get strPull
        strPull = "DE"
    Else
        strPull = pull
    End If
    
    If (rotateAng > (Pi / 2)) And (rotateAng <= (3 * Pi / 2)) Then
        iDirection = 0
    Else
        iDirection = 1
    End If
    
    insertPnt = ThisDrawing.Utility.GetPoint(, "Place Guy:")
    
    dScale = 1#
    'dScale = CDbl(MainForm.cbScale.Value) / 100
    
    If iDirection = 0 Then
        str = "ExGuyOL"
    Else
        str = "ExGuyOR"
    End If
    
    'Set layerObj = ThisDrawing.Layers.Add("Integrity Guys")
    'ThisDrawing.ActiveLayer = layerObj
    
    Err = 0
    
    Set objTemp = ThisDrawing.ModelSpace.InsertBlock(insertPnt, str, dScale, dScale, dScale, rotateAng)
    objTemp.Layer = "Integrity Proposed"
    vAttList = objTemp.GetAttributes
   
    vAttList(1).TextString = " "
    vAttList(2).TextString = "PE1-3G"
    objTemp.Update
    If Not Err = 0 Then MsgBox "error" & vbCr & Err.Description

    If iDirection = 0 Then
        str = "ExAncOL"
    Else
        str = "ExAncOR"
    End If

    Set objTemp = ThisDrawing.ModelSpace.InsertBlock(insertPnt, str, dScale, dScale, dScale, rotateAng)
    objTemp.Layer = "Integrity Proposed"
    vAttList = objTemp.GetAttributes
    
    vAttList(0).TextString = "PF1-5A"
    'If strPull = "DE" Then
        'vAttList(1).TextString = "P= DE"
    'Else
        vAttList(1).TextString = "P= " & strPull
    'End If
    objTemp.Update
    
    vAttList = objBlock.GetAttributes
    
    If vAttList(27).TextString = "" Then
        vAttList(27).TextString = "PE1-3G=1;;PF1-5A=1;;PM11=1"
    Else
        vAttList(27).TextString = vAttList(27).TextString & ";;+PE1-3G=1;;+PF1-5A=1;;+PM11=1"
    End If
    
    objBlock.Update
    
    GoTo Place_Anchor
    
Exit_Sub:
    Me.show
End Sub

Private Sub cbAttachAlias_Click()
    Me.Hide
        Load AttachmentAlias
            AttachmentAlias.show
        Unload AttachmentAlias
    Me.show
End Sub

Private Sub cbAVCounts_Click()
    Me.Hide
        Load CountsForm
            CountsForm.show
        Unload CountsForm
    Me.show
End Sub

Private Sub cbBlockAtt_Click()
    Me.Hide
        Load ChangeAttData
        ChangeAttData.show
        Unload ChangeAttData
    Me.show
End Sub

Private Sub cbBore_Click()
    Me.Hide
        Load BuriedPlantForm
        BuriedPlantForm.show
        Unload BuriedPlantForm
    Me.show
End Sub

Private Sub cbCableCO_Click()
    Me.Hide
        Load CableCalloutForm
            CableCalloutForm.show
        Unload CableCalloutForm
    Me.show
End Sub

Private Sub cbCalcMR_Click()
    Me.Hide
    Load MRWorksheet
    MRWorksheet.show
    Unload MRWorksheet
    Me.show
End Sub

Private Sub cbCleanup_Click()
    Me.Hide
    Load CleanupForm
    CleanupForm.show
    Unload CleanupForm
    Me.show
End Sub

Private Sub cbClosureLocations_Click()
    Me.Hide
        Load ClosureLocations
        ClosureLocations.show
        Unload ClosureLocations
    Me.show
End Sub

Private Sub cbConvertBlocksBlock_Click()
    Me.Hide
        Load ConvertChangeBlocks
        ConvertChangeBlocks.show
        Unload ConvertChangeBlocks
    Me.show
End Sub

Private Sub cbConvertCustomer_Click()
    Me.Hide
        Load ConvertCustomers
            ConvertCustomers.show
        Unload ConvertCustomers
    Me.show
End Sub

Private Sub cbConvertGPS_Click()
    Me.Hide
        Load ConvertGPS
        ConvertGPS.show
        Unload ConvertGPS
    Me.show
End Sub

Private Sub cbConvertLayers_Click()
    Me.Hide
        Load ConvertBlockLayers
        ConvertBlockLayers.show
        Unload ConvertBlockLayers
    Me.show
End Sub

Private Sub cbConvertMisc_Click()
    Me.Hide
        Load ConvertBlocks
        ConvertBlocks.show
        Unload ConvertBlocks
    Me.show
End Sub

Private Sub cbConvertNES_Click()
    Me.Hide
        Load CreateNESPoles
        CreateNESPoles.show
        Unload CreateNESPoles
    Me.show
End Sub

Private Sub cbConvertText_Click()
    Me.Hide
        Load ConvertBlockText
        ConvertBlockText.show
        Unload ConvertBlockText
    Me.show
End Sub

Private Sub cbCustomers_Click()
'    Dim SSobj2 As AcadSelectionSet
'    Dim objBLDG As AcadBlockReference
'    Dim objNewBLDG As AcadBlockReference
'    Dim attList, attNewList As Variant
'    Dim filterType, filterValue As Variant
'    Dim grpCode(0) As Integer
'    Dim grpValue(0) As Variant
'    Dim entBlock As AcadEntity
'    Dim iCount As Integer
'    Dim str1, str2, strBlock, strLayer As String
'    Dim strTemp As String
'    Dim dInsertPnt(0 To 2) As Double
'    Dim dScale As Double
'
'    Me.hide
'    iCount = 0
'
'  On Error Resume Next
'
'    strTemp = "Integrity Building-BUS"
'    'strTemp = "Integrity Building, Integrity Building-RES, Integrity Building-BUS, Integrity Building-MDU, "
'    'strTemp = strTemp & "Integrity Building-TRL, Integrity Building-SCH, Integrity Building-CHU"
'
'    grpCode(0) = 8
'    grpValue(0) = strTemp
'    'grpCode(1) = 8
'    'grpValue(1) = "Integrity Building-RES"
'    filterType = grpCode
'    filterValue = grpValue
'
'    Set SSobj2 = ThisDrawing.SelectionSets.Add("SSobj2")
'    SSobj2.Select acSelectionSetAll, , , filterType, filterValue
'
'    MsgBox SSobj2.count
'
'    For Each entBlock In SSobj2
'        If Not entBlock.ObjectName = "AcDbBlockReference" Then GoTo Next_entBlock
'        Set objBLDG = entBlock
'        attList = objBLDG.GetAttributes
'        If Not UBound(attList) = 2 Then GoTo Next_entBlock
'
'        str1 = Left(attList(2).TextString, 3)
'        If str1 = "" Then GoTo Next_entBlock
'
'        str2 = UCase(attList(2).TextString)
'        If Len(str2) > 3 Then str2 = Right(str2, Len(str2) - 3)
'        If Len(str2) = 0 Then str2 = " "
'        If Left(str2, 1) = " " Then str2 = Right(str2, Len(str2) - 1)
'
'        Select Case str1
'            Case "res"
'                If objBLDG.Name = "RES" Then GoTo Next_entBlock
'                strBlock = "RES"
'                strLayer = "Integrity Building-RES"
'            Case "bus"
'                If objBLDG.Name = "BUSINESS" Then GoTo Next_entBlock
'                strBlock = "BUSINESS"
'                strLayer = "Integrity Building-BUS"
'            Case "trl"
'                If objBLDG.Name = "TRLR" Then GoTo Next_entBlock
'                strBlock = "TRLR"
'                strLayer = "Integrity Building-TRL"
'            Case "mdu"
'                If objBLDG.Name = "MDU" Then GoTo Next_entBlock
'                strBlock = "MDU"
'                strLayer = "Integrity Building-MDU"
'            Case "ext"
'                If objBLDG.Name = "EXTENTION" Then GoTo Next_entBlock
'                strBlock = "EXTENTION"
'                strLayer = "Integrity Building Misc"
'            Case "sch"
'                If objBLDG.Name = "SCHOOL" Then GoTo Next_entBlock
'                strBlock = "SCHOOL"
'                strLayer = "Integrity Building-SCH"
'            Case "chu"
'                MsgBox "CHURCH" & vbCr & str1 & vbCr & str2
'                If objBLDG.Name = "CHURCH" Then GoTo Next_entBlock
'                strBlock = "CHURCH"
'                strLayer = "Integrity Building-CHU"
'            Case Else
'                GoTo Next_entBlock
'        End Select
'
'        'str2 = "Old Block: " & objBLDG.Name & vbCr & "Data: " & attList(2).TextString & vbCr
'        'str2 = str2 & "New Block: " & strBlock
'        'MsgBox str2
'
'        'str2 = UCase(attList(2).TextString)
'        'str2 = Right(str2, Len(str2) - 3)
'
'        dInsertPnt(0) = objBLDG.InsertionPoint(0)
'        dInsertPnt(1) = objBLDG.InsertionPoint(1)
'        dInsertPnt(2) = 0#
'
'        dScale = objBLDG.XScaleFactor
'
'        Set objNewBLDG = ThisDrawing.ModelSpace.InsertBlock(dInsertPnt, strBlock, dScale, dScale, dScale, 0#)
'        objNewBLDG.Layer = strLayer
'        attNewList = objNewBLDG.GetAttributes
'
'        attNewList(0).TextString = attList(0).TextString
'        attNewList(1).TextString = attList(1).TextString
'        attNewList(2).TextString = str2
'
'        objNewBLDG.Update
'        objBLDG.Delete
'        iCount = iCount + 1
'Next_entBlock:
'    Next entBlock
'
'    SSobj2.Clear
'    SSobj2.Delete
'
'    MsgBox "Converted Buildings: " & iCount
'
'    Me.show
End Sub

Private Sub cbDBKF_Click()
    Me.Hide
        Load dbLoss
            dbLoss.show
        Unload dbLoss
    Me.show
End Sub

Private Sub cbDeleteDrop_Click()
    Me.Hide
        Call DeleteDropCallouts
    Me.show
End Sub

Private Sub cbDropCallouts_Click()
    Me.Hide
        Call DropCallout
    Me.show
End Sub

Private Sub cbExchange_Change()
    Select Case cbExchange.Value
        Case "Belfast"
            cbCounty.Value = "Marshall"
            tbCity.Value = "Belfast"
        Case "Bell Buckle"
            cbCounty.Value = "Bedford"
            tbCity.Value = "Bell Buckle"
        Case "Chapel Hill"
            cbCounty.Value = "Marshall"
            tbCity.Value = "Chapel Hill"
        Case "Chapel Hill-CLEC"
            cbCounty.Value = "Marshall"
            tbCity.Value = " "
        Case "College Grove"
            cbCounty.Value = "Williamson"
            tbCity.Value = "College Grove"
        Case "College Grove-CLEC"
            cbCounty.Value = "Williamson"
            tbCity.Value = " "
        Case "Flat Creek"
            cbCounty.Value = "Bedford"
            tbCity.Value = "Flat Creek"
        Case "Fosterville"
            cbCounty.Value = "Rutherford"
            tbCity.Value = "Fosterville"
        Case "Franklin-CLEC"
            cbCounty.Value = "Williamson"
            tbCity.Value = "Franklin"
        Case "Lebanon-CLEC"
            cbCounty.Value = "Wilson"
            tbCity.Value = "Lebanon"
        Case "Murfreesboro-CLEC"
            cbCounty.Value = "Rutherford"
            tbCity.Value = "Murfreesboro"
        Case "Nolensville"
            cbCounty.Value = "Williamson"
            tbCity.Value = "Nolensville"
        Case "Nolensville-CLEC"
            cbCounty.Value = "Williamson"
            tbCity.Value = "Nolensville"
        Case "Shelbyville-CLEC"
            cbCounty.Value = "Bedford"
            tbCity.Value = "Shelbyville"
        Case "Smyrna-CLEC"
            cbCounty.Value = "Rutherford"
            tbCity.Value = "Smyrna"
        Case "Triune"
            cbCounty.Value = "Williamson"
            tbCity.Value = "Triune"
        Case "Unionville"
            cbCounty.Value = "Bedford"
            tbCity.Value = "Unionville"
    End Select
End Sub

Private Sub cbExtraHeights_Click()
    Me.Hide
        Load ExtraHeightForm
        ExtraHeightForm.show
        Unload ExtraHeightForm
    Me.show
End Sub

Private Sub cbGetLengths_Click()
    Me.Hide
        Load GetCableLengths
        GetCableLengths.show
        Unload GetCableLengths
    Me.show
End Sub

Private Sub cbGetSpansReel_Click()
    Me.Hide
        Load GetSpansReel
        GetSpansReel.show
        Unload GetSpansReel
    Me.show
End Sub

Private Sub cbHousing_Click()
    Me.Hide
        Load PlaceBuriedData
        PlaceBuriedData.show
        Unload PlaceBuriedData
    Me.show
End Sub

Private Sub cbLoadBlocks_Click()
    Me.Hide
        Load LoadBlocks
        LoadBlocks.show
        Unload LoadBlocks
    Me.show
End Sub

Private Sub cbMaptrim_Click()
    Dim objSSM1 As AcadSelectionSet
    Dim objEntity As AcadEntity
    Dim objEntTemp As AcadEntity
    Dim objRemove(0) As AcadEntity
    Dim objLWP As AcadLWPolyline
    Dim objLWPBorder As AcadLWPolyline
    Dim objSSBlock As AcadBlockReference
    Dim objLayer As AcadLayer
    'Dim strLayer As String
    Dim strCommand As String
    Dim strHandle As String
    Dim strRemove As String
    Dim vReturnPnt As Variant
    Dim vCoords As Variant
    Dim dLL(0 To 2) As Double
    Dim dUR(0 To 2) As Double
    Dim dFrom(0 To 2) As Double
    Dim dTo(0 To 2) As Double
    Dim dDiff(0 To 1) As Double
    Dim dScale As Double
    
  On Error Resume Next
    'Select boundary & find drawing number
    
    Me.Hide
    
    Err = 0
    Set objSSM1 = ThisDrawing.SelectionSets.Add("objSSM1")
    If Not Err = 0 Then
        Set objSSM1 = ThisDrawing.SelectionSets.Item("objSSM1")
        Err = 0
    End If
    
  While Err = 0
    
    ThisDrawing.Utility.GetEntity objEntity, vReturnPnt, "Select Trim Border: "
    If Not objEntity.ObjectName = "AcDbPolyline" Then
        Me.show
        Exit Sub
    End If
    
    Set objLWP = objEntity
    vCoords = objLWP.Coordinates
    
    dLL(0) = vCoords(0)
    dLL(1) = vCoords(1)
    dUR(0) = vCoords(0)
    dUR(1) = vCoords(1)
    
    For i = 2 To UBound(vCoords)
        If vCoords(i) < dLL(0) Then
            dLL(0) = vCoords(i)
        Else
            If vCoords(i) > dUR(0) Then
                dUR(0) = vCoords(i)
            End If
        End If
        
        i = i + 1
        
        If vCoords(i) < dLL(1) Then
            dLL(1) = vCoords(i)
        Else
            If vCoords(i) > dUR(1) Then
                dUR(1) = vCoords(i)
            End If
        End If
    Next i
    
    dFrom(0) = (dLL(0) + dUR(0)) / 2
    dFrom(1) = (dLL(1) + dUR(1)) / 2
    
    'Get coordinates to DWG Sheet and draw LWP (Save strHandle)
    
    ThisDrawing.Utility.GetEntity objEntity, vReturnPnt, "Select DWG Border: "
    If TypeOf objEntity Is AcadBlockReference Then
        Set objSSBlock = objEntity
    Else
        MsgBox "Not a valid entity."
        Exit Sub
    End If
    
    dScale = objSSBlock.XScaleFactor
    strRemove = objSSBlock.Layer
    
    dTo(0) = objSSBlock.InsertionPoint(0) + (825 * dScale)
    dTo(1) = objSSBlock.InsertionPoint(1) + (525 * dScale)
    dTo(2) = 0#
    
    dDiff(0) = dTo(0) - dFrom(0)
    dDiff(1) = dTo(1) - dFrom(1)
    
    Set objLWPBorder = ThisDrawing.ModelSpace.AddLightWeightPolyline(vCoords)
    objLWPBorder.Closed = True
    objLWPBorder.Layer = objLWP.Layer
    objLWPBorder.Move dFrom, dTo
    objLWPBorder.Update
    strHandle = objLWPBorder.Handle
    
    'Get objects crossing within dimensions of DWG and copy to DWG
    
    objSSM1.Select acSelectionSetCrossing, dLL, dUR
    
    If objSSM1.count = 0 Then GoTo Exit_Sub
    
    strCommand = "COPY" & vbCr & "P" & vbCr & vbCr
    strCommand = strCommand & dFrom(0) & "," & dFrom(1) & ",0" & vbCr
    strCommand = strCommand & dTo(0) & "," & dTo(1) & ",0" & vbCr & vbCr
    
    ThisDrawing.SetVariable "CMDDIA", 0
    ThisDrawing.SendCommand strCommand
    
    objSSM1.Clear
    
    Set objLayer = ThisDrawing.Layers(strRemove)
    objLayer.Lock = True
    
    dLL(0) = dLL(0) + dDiff(0)
    dLL(1) = dLL(1) + dDiff(1)
    dUR(0) = dUR(0) + dDiff(0)
    dUR(1) = dUR(1) + dDiff(1)
    
    'Set objSSM1 = ThisDrawing.SelectionSets.Add("objSSM1")
    objSSM1.Select acSelectionSetCrossing, dLL, dUR
        
    For Each objEntTemp In objSSM1
        If objEntTemp.Layer = strRemove Then
            'MsgBox "Found an entity" & vbCr & objEntTemp.ObjectName
            Set objRemove(0) = objEntTemp
            objSSM1.RemoveItems objRemove
        End If
    Next objEntTemp
    
    strCommand = "_MAPTRIM" & vbCr & "S" & vbCr & "(handent """ & strHandle & """)" & vbCr
    strCommand = strCommand & "N" & vbCr & "Y" & vbCr & "P" & vbCr & vbCr & "O" & vbCr
    strCommand = strCommand & "Y" & vbCr & "Y" & vbCr & "R" & vbCr & "Y" & vbCr

    ThisDrawing.SendCommand strCommand
    
    objSSM1.Clear
    
    objLayer.Lock = False
  Wend
    
Exit_Sub:
    objSSM1.Delete
    
    ThisDrawing.SetVariable "CMDDIA", 1
    Me.show
End Sub

Private Sub cbMatchlines_Click()
    Me.Hide
    Call Module1.AddMatchlines
    Me.show
    Exit Sub
End Sub

Private Sub cbMissingCallouts_Click()
    Me.Hide
        Load FindMissingCallouts
            FindMissingCallouts.show
        Unload FindMissingCallouts
    Me.show
End Sub

Private Sub cbMRReport_Click()
    Me.Hide
        Load MRSheets
            MRSheets.show
        Unload MRSheets
    Me.show
End Sub

Private Sub cbOldMenu_Click()
    Me.Hide
        Load MainForm2
        MainForm2.show
        Unload MainForm2
    Me.show
End Sub

Private Sub cbMRReview_Click()
    Me.Hide
    Load MRReview
    MRReview.show
    Unload MRReview
    Me.show
End Sub

Private Sub cbODInquiry_Click()
    Me.Hide
        Load ObjectDataInquiry
        ObjectDataInquiry.show
        Unload ObjectDataInquiry
    Me.show
End Sub

Private Sub cbPlaceBuriedCbl_Click()
    Dim amap As AcadMap
    Dim ODRcs As ODRecords
    Dim tbl As ODTable
    Dim tbls As ODTables
    Dim boolVal As Boolean
    Dim entPole As AcadObject
    Dim objLWP As AcadLWPolyline
    Dim objLine As AcadLine
    Dim obrDrop As AcadBlockReference
    Dim attItem, basePnt As Variant
    Dim strType, strLength, strTemp As String
    Dim dRotate, dScale, Pi As Double
    Dim dTest As Double
    Dim dInsertPnt(0 To 2) As Double
    Dim dStartPnt(0 To 2) As Double
    Dim dEndPnt(0 To 2) As Double
    Dim dDiff(0 To 1) As Double
    Dim vStartPnt, vEndPnt As Variant
    Dim vCoords, vAttList, vList As Variant
    Dim layerObj As AcadLayer
    Dim strCableSize As String
    
    Me.Hide
  On Error Resume Next
    Set layerObj = ThisDrawing.Layers.Add("Integrity Cable-Buried Text")
    ThisDrawing.ActiveLayer = layerObj
    
    strCableSize = ThisDrawing.Utility.GetString(1, "Cable Size (Space between Cables): ")
    vList = Split(strCableSize, " ")
    strCableSize = ""
    For iTemp = LBound(vList) To UBound(vList)
        strCableSize = strCableSize & vList(iTemp) & "F "
    Next iTemp
  
    Pi = 3.14159265359
    'dScale = 1
    
    Set amap = ThisDrawing.Application.GetInterfaceObject("AutoCADMap.Application")
    
    Set tbls = amap.Projects(ThisDrawing).ODTables
    
get_Drop:

    dScale = 1#  'cbScale.Value / 100
    strLength = ""
    
    Err = 0
    ThisDrawing.Utility.GetEntity entPole, basePnt, "Select Buried Cable: "
    If Not Err = 0 Then GoTo Exit_Sub
    
    Select Case entPole.ObjectName
        Case "AcDbLine"
            Set objLine = entPole
            strTemp = CInt(objLine.Length)
            vStartPnt = objLine.StartPoint
            vEndPnt = objLine.EndPoint
            
            Err = 0
            If tbls.count > 0 Then
                For Each tbl In tbls
                    If tbl.Name = "UGPrimary" Then GoTo Exit_For2
                Next
            End If
Exit_For2:
            
            Set ODRcs = tbl.GetODRecords
            boolVal = ODRcs.Init(entPole, True, False)
             
            strLength = ODRcs.Record.Item(35).Value
            'MsgBox Len(strLength) & vbCr & Err
            If Len(strLength) < 1 Then
                strLength = strTemp
            End If
            
        Case "AcDbPolyline"
            Set objLWP = entPole
            strTemp = CInt(objLWP.Length)
            MsgBox strTemp
            vCoords = objLWP.Coordinates
            dStartPnt(0) = vCoords(0)
            dStartPnt(1) = vCoords(1)
            dStartPnt(2) = 0#
            dEndPnt(0) = vCoords(2)
            dEndPnt(1) = vCoords(3)
            dEndPnt(2) = 0#
            
            dDiff(0) = dEndPnt(0) - dStartPnt(0)
            dDiff(1) = dEndPnt(1) - dStartPnt(1)
            dTemp = Sqr(dDiff(0) * dDiff(0) + dDiff(1) * dDiff(1))
            
            If UBound(vCoords) > 3 Then
                For i = 5 To UBound(vCoords)
                    dDiff(0) = vCoords(i - 1) - vCoords(i - 3)
                    dDiff(1) = vCoords(i) - vCoords(i - 2)
                    If dTemp < Sqr(dDiff(0) * dDiff(0) + dDiff(1) * dDiff(1)) Then
                        dStartPnt(0) = vCoords(i - 3)
                        dStartPnt(1) = vCoords(i - 2)
                        dEndPnt(0) = vCoords(i - 1)
                        dEndPnt(1) = vCoords(i)
                        dTemp = Sqr(dDiff(0) * dDiff(0) + dDiff(1) * dDiff(1))
                    End If
                Next i
            End If
            
            Err = 0
            If tbls.count > 0 Then
                For Each tbl In tbls
                    If tbl.Name = "UGPrimary" Then GoTo exit_for4
                Next
            End If
exit_for4:
            
            Set ODRcs = tbl.GetODRecords
            boolVal = ODRcs.Init(entPole, True, False)
               
            strLength = ODRcs.Record.Item(35).Value
            'MsgBox Len(strLength) & vbCr & Err
            If Len(strLength) < 1 Then
                strLength = strTemp
            End If
            
            vStartPnt = dStartPnt
            vEndPnt = dEndPnt
        Case Else
            Set layerObj = ThisDrawing.Layers.Add("0")
            ThisDrawing.ActiveLayer = layerObj
            Me.show
            Exit Sub
    End Select
    
    dInsertPnt(0) = (vStartPnt(0) + vEndPnt(0)) / 2
    dInsertPnt(1) = (vStartPnt(1) + vEndPnt(1)) / 2
    dInsertPnt(2) = 0#
    
    dDiff(0) = vEndPnt(0) - vStartPnt(0)
    dDiff(1) = vEndPnt(1) - vStartPnt(1)
    
    If dDiff(0) = 0 Then
        dRotate = 0#
    Else
        If dDiff(1) = 0 Then
            dRotate = Pi / 2
        Else
            dRotate = Atn(dDiff(1) / dDiff(0))
        End If
    End If
    
    If dRotate > (Pi / 2) And dRotate < (1.5 * Pi) Then dRotate = dRotate - Pi
    
    'ThisDrawing.ActiveLayer = layerObj
    
    Set obrDrop = ThisDrawing.ModelSpace.InsertBlock(dInsertPnt, "Cable_span", dScale, dScale, dScale, dRotate)
    vAttList = obrDrop.GetAttributes
    vAttList(1).TextString = strCableSize
    vAttList(2).TextString = strLength & "'"
    obrDrop.Update
    
    GoTo get_Drop
Exit_Sub:
    Me.show
End Sub

Private Sub cbPlaceCable_Click()
    Me.Hide
    
        Load PlaceAerialCable
        PlaceAerialCable.show
        Unload PlaceAerialCable
    
    Me.show
End Sub

Private Sub cbPlaceFromSpida_Click()
    Me.Hide
        Load PlaceSPIDAPoles
        PlaceSPIDAPoles.show
        Unload PlaceSPIDAPoles
    Me.show
End Sub

Private Sub cbPlaceOwner_Click()
    Me.Hide
            Load PoleOwnerNote
            PoleOwnerNote.show
            Unload PoleOwnerNote
    Me.show
End Sub

Private Sub cbPlacePoleData_Click()
    Me.Hide
            Load PlacePoleData
            PlacePoleData.show
            Unload PlacePoleData
    Me.show
End Sub

Private Sub cbPonVHLE_Click()
    Me.Hide
            Load PonVHLE
            PonVHLE.show
            Unload PonVHLE
    Me.show
End Sub

Private Sub cbPrintSelected_Click()
    Dim strArraySheets() As String
    Dim attTotalLine, attTotalSplit As Variant
    Dim str, str1 As String
    Dim strDWG As String
    Dim dScale As Double
    Dim dLL(0 To 1), dUR(0 To 1) As Double
    Dim strPlot(0 To 24) As String
    Dim i As Integer
    Dim strCommand As String
    Dim strPath As String
    Dim strFileName As String
    'Dim str As String
    Dim strArray As Variant
    Dim viewCoordsB(0 To 2) As Double
    Dim viewCoordsE(0 To 2) As Double
    
    strPath = ThisDrawing.Path & "\"
    
    strPlot(0) = "-plot"
    strPlot(1) = "y"
    strPlot(2) = ""
    'strPlot(3) = "Microsoft Print to PDF"
    strPlot(4) = "TABLOID"
    strPlot(5) = "i" '"i"
    strPlot(6) = "LANDSCAPE"
    strPlot(7) = "n"
    strPlot(8) = "w"
    'strPlot(9) = ""
    'strPlot(10) = ""
    'strPlot(11) = "" '"1=75"
    strPlot(12) = "c"
    strPlot(13) = "y"
    strPlot(14) = "United.ctb"
    strPlot(15) = "y"
    strPlot(16) = "a"
    strPlot(17) = "n"
    strPlot(18) = "n"
    strPlot(19) = "y"
    'strPlot(20) = ""
    strPlot(21) = ""
    strPlot(22) = ""
    strPlot(23) = ""
    strPlot(24) = ""
    
    ThisDrawing.SetVariable "FILEDIA", 0
    ThisDrawing.SetVariable "CMDDIA", 0
    
    For i = 0 To lbSheets.ListCount - 1
        If lbSheets.Selected(i) Then
            str = lbSheets.List(i)
            attTotalSplit = Split(str, vbTab)
            strDWG = attTotalSplit(0)
            dScale = CDbl(attTotalSplit(1))
            dLL(0) = CDbl(attTotalSplit(2))
            dLL(1) = CDbl(attTotalSplit(3))
            dUR(0) = dLL(0) + (1652 * dScale)
            dUR(1) = dLL(1) + (1052 * dScale)
    
            viewCoordsB(0) = dLL(0)
            viewCoordsB(1) = dLL(1)
            viewCoordsB(2) = 0#
            viewCoordsE(0) = dUR(0)
            viewCoordsE(1) = dUR(1)
            viewCoordsE(2) = 0#
    
            ThisDrawing.Application.ZoomWindow viewCoordsB, viewCoordsE
            
            strPlot(9) = (dLL(0) - (1 * dScale)) & "," & (dLL(1) - (1 * dScale))
            strPlot(10) = (dUR(0) + (1 * dScale)) & "," & (dUR(1) + (1 * dScale))
            strPlot(11) = "1=" & CStr((dScale + 0.02) * 100)
    
            strFileName = """" & strPath & "Individual Sheets\" & strDWG & ".pdf"""
            strPlot(20) = strFileName
            'MsgBox strFileName
            
            strCommand = ""
            For j = 0 To 19
                If strPlot(j) = "" Then
                    strCommand = strCommand & vbCr
                Else
                    strCommand = strCommand & strPlot(j) & vbCr
                End If
            Next j
            
            ThisDrawing.SendCommand strCommand
            
            'str1 = strDWG & vbCr & "Scale= " & dScale & vbCr
            'str1 = str1 & "LLx " & dLL(0) & vbCr & "LLy " & dLL(1) & vbCr
            'str1 = str1 & "URx " & dUR(0) & vbCr & "URy " & dUR(1)
            
            'MsgBox str1
            
            'ThisDrawing.ActiveLayout.SetWindowToPlot dLL, dUR
            'ThisDrawing.ActiveLayout.PlotType = acWindow
            'ThisDrawing.ActiveLayout.ConfigName "Microsoft Print to PDF.pc3"
            'ThisDrawing.Plot.PlotToDevice
        End If
    Next i
    
    ThisDrawing.SetVariable "FILEDIA", 1
    ThisDrawing.SetVariable "CMDDIA", 1
    
End Sub

Private Sub cbProjectStatus_Click()
    Me.Hide
            Load ProjectStatus
            ProjectStatus.show
            Unload ProjectStatus
    Me.show
End Sub

Private Sub cbQuit_Click()
    Me.Hide
End Sub

Private Sub cbRearrageCounts_Click()
    Me.Hide
        Load RearrangeCounts
            RearrangeCounts.show
        Unload RearrangeCounts
    Me.show
End Sub

Private Sub cbRenumber_Click()
    Me.Hide
        Load RenumberPoles
            RenumberPoles.show
        Unload RenumberPoles
    Me.show
End Sub

Private Sub cbReplaceCounts_Click()
    Me.Hide
        Load ReplaceCounts
            ReplaceCounts.show
        Unload ReplaceCounts
    Me.show
End Sub

Private Sub cbResizeBlocks_Click()
    Me.Hide
        Load ResizeBlocks
            ResizeBlocks.show
        Unload ResizeBlocks
    Me.show
End Sub

Private Sub cbSave_Click()
    ThisDrawing.SendCommand "QSAVE" & vbCr
End Sub

Private Sub cbScope_Click()
    Me.Hide
            Load ScopeOfWork
            ScopeOfWork.show
            Unload ScopeOfWork
    Me.show
End Sub

Private Sub cbSendCommand_Click()
    Dim strCommand As String
    
    Me.Hide
    
    strCommand = ThisDrawing.Utility.GetString(True, "Enter AutoCAD Command or Alias: ")
    
    ThisDrawing.SendCommand strCommand & vbCr
    
    Me.show
End Sub

Private Sub cbSpidaminSearch_Click()
    Me.Hide
        Load SPIDAminSearch
            SPIDAminSearch.show
        Unload SPIDAminSearch
    Me.show
End Sub

Private Sub cbTabGeneric_Click()
    Me.Hide
        Load TabGeneric
            TabGeneric.show
        Unload TabGeneric
    Me.show
End Sub

Private Sub cbTDOT_Click()
    Me.Hide
        Load TDOT
            TDOT.show
        Unload TDOT
    Me.show
End Sub

Private Sub cbTDS_Click()
    Me.Hide
        Load TDSMainForm
            TDSMainForm.show
        Unload TDSMainForm
    Me.show
End Sub

Private Sub cbTemplates_Click()
    Me.Hide
        Load TemplateEditor
            TemplateEditor.show
        Unload TemplateEditor
    Me.show
End Sub

Private Sub cbTicket_Click()
    Me.Hide
        Load TroubleTicket
            TroubleTicket.show
        Unload TroubleTicket
    Me.show
End Sub

Private Sub cbTrim_Click()
'    Dim SSobj2 As AcadSelectionSet
'    Dim objTrim As AcadBlockReference
'    Dim attList As Variant
'    Dim filterType, filterValue As Variant
'    Dim grpCode(0) As Integer
'    Dim grpValue(0) As Variant
'    Dim entBlock As AcadEntity
'    Dim iCount As Integer
'
'    Me.hide
'    iCount = 0
'
'    grpCode(0) = 8
'    grpValue(0) = "_Annotations"
'    filterType = grpCode
'    filterValue = grpValue
'
'    Set SSobj2 = ThisDrawing.SelectionSets.Add("SSobj2")
'    SSobj2.Select acSelectionSetAll, , , filterType, filterValue
'
'    For Each entBlock In SSobj2
'        If Not entBlock.ObjectName = "AcDbBlockReference" Then GoTo Next_entBlock
'        Set objTrim = entBlock
'        If Not objTrim.Name = "__Trim" Then GoTo Next_entBlock
'
'        attList = objTrim.GetAttributes
'        attList(0).TextString = "T.T=" & attList(0).TextString & "'"
'        objTrim.Layer = "Integrity Notes"
'        objTrim.Update
'
'        iCount = iCount + 1
'Next_entBlock:
'    Next entBlock
'
'    SSobj2.Clear
'    SSobj2.Delete
'
'    MsgBox "Trim Blocks: " & iCount
'    Me.show
End Sub

Private Sub cbTrace_Click()
    Me.Hide
        Load TraceForm
            TraceForm.show
        Unload TraceForm
    Me.show
End Sub

Private Sub cbUnits_Click()
    Me.Hide
        Load UnitForm
        UnitForm.show
        Unload UnitForm
    Me.show
End Sub

Private Sub cbUnitTab_Click()
    Me.Hide
        Load TabGeneric
        TabGeneric.show
        Unload TabGeneric
    Me.show
End Sub

Private Sub cbUpdateAllSS_Click()
    Dim objSS1 As AcadSelectionSet
    Dim entBlock As AcadObject
    Dim obrTemp As AcadBlockReference
    Dim attItem2 As Variant
    Dim mode As Integer
    'Dim str As String
    Dim filterType, filterValue As Variant
    Dim grpCode(0) As Integer
    Dim grpValue(0) As Variant
    Dim str As String
    
  On Error Resume Next
    
    'str = ThisDrawing.Name
    'tbWO.Value = Left(str, 8)
    'str = Right(str, (Len(str) - 9))
    'tbProject.Value = Left(str, (Len(str) - 4))
    
    grpCode(0) = 8
    grpValue(0) = "Integrity Sheets"
    filterType = grpCode
    filterValue = grpValue
    
    Set objSS1 = ThisDrawing.SelectionSets.Add("objSS1")
    objSS1.Select acSelectionSetAll, , , filterType, filterValue
    
    For Each entBlock In objSS1
        'If TypeOf entBlock Is AcadBlockReference Then
            Set obrTemp = entBlock
        'Else
            'MsgBox "Error" & Err
            'GoTo exit_sub
        'End If
        
        If obrTemp.Name = "SS Info" Then
            attItem2 = obrTemp.GetAttributes
            attItem2(0).TextString = tbProject.Value
            attItem2(1).TextString = tbWO.Value
            attItem2(2).TextString = cbExchange.Value
            attItem2(3).TextString = tbRST.Value
            attItem2(4).TextString = cbCounty.Value
            attItem2(5).TextString = tbCity.Value
            attItem2(7).TextString = tbTotalDWG.Value
            
            obrTemp.Update
        End If
    Next entBlock
    
    Call SortLBItems
Exit_Sub:
    objSS1.Delete
End Sub

Private Sub cbUnnamedForm_Click()
    Me.Hide
        Load UnnamedForm
        UnnamedForm.show
        Unload UnnamedForm
    Me.show
End Sub

Private Sub cbUpdateAncGuy_Click()
    Me.Hide
        Call UpdateAnchors
    Me.show
End Sub

Private Sub cbValidate_Click()
    Me.Hide
        Load ValidateFielding
        ValidateFielding.show
        Unload ValidateFielding
    Me.show
End Sub

Private Sub cbValidateAttach_Click()
    Me.Hide
        Load ValidateAttachments
        ValidateAttachments.show
        Unload ValidateAttachments
    Me.show
End Sub

Private Sub cbValidateCounts_Click()
    Me.Hide
        Load ValidateCounts
        ValidateCounts.show
        Unload ValidateCounts
    Me.show
End Sub

Private Sub cbValidateCustomers_Click()
    Me.Hide
        Load ValidateCustomers
        ValidateCustomers.show
        Unload ValidateCustomers
    Me.show
End Sub

Private Sub cbValidateHO1_Click()
    Me.Hide
        Load ValidateHO1
        ValidateHO1.show
        Unload ValidateHO1
    Me.show
End Sub

Private Sub cbValidateMCL_Click()
    Me.Hide
        Load ValidateMCL
        ValidateMCL.show
        Unload ValidateMCL
    Me.show
End Sub

Private Sub cbValidateML_Click()
    Me.Hide
        Load ValidateML
        ValidateML.show
        Unload ValidateML
    Me.show
End Sub

Private Sub cbVerifyAsFielded_Click()
    Me.Hide
        'Load CheckFieldedPoles
        'CheckFieldedPoles.show
        'Unload CheckFieldedPoles
        Load ValidateAttachments
        ValidateAttachments.show
        Unload ValidateAttachments
    Me.show
End Sub

Private Sub cbVerifyAttCallouts_Click()
    Me.Hide
        Load VerifyAttachmentCallouts
            VerifyAttachmentCallouts.show
        Unload VerifyAttachmentCallouts
    Me.show
End Sub

Private Sub cbVerifyUnits_Click()
    Me.Hide
        Load VerifyUnits
            VerifyUnits.show
        Unload VerifyUnits
    Me.show
End Sub

Private Sub cbVHLE_Click()
    Me.Hide
    Load DesignVHLE
    DesignVHLE.show
    Unload DesignVHLE
    Me.show
End Sub

Private Sub CommandButton1_Click()
    Me.Hide
    Load OtherSubsPoles
    OtherSubsPoles.show
    Unload OtherSubsPoles
    Me.show
End Sub

Private Sub CommandButton2_Click()
    Me.Hide
    Load zMisc
    zMisc.show
    Unload zMisc
    Me.show
End Sub

Private Sub CommandButton3_Click()
    Me.Hide
        Load PlaceCountCallouts
        PlaceCountCallouts.show
        Unload PlaceCountCallouts
    Me.show
End Sub

Private Sub Label3_Click()
    Dim objObject As AcadObject
    Dim obrGP2 As AcadBlockReference
    Dim basePnt, attItem As Variant
    
    Me.Hide
  On Error Resume Next
    
    ThisDrawing.Utility.GetEntity objObject, basePnt, "Select SS Info: "
    If TypeOf objObject Is AcadBlockReference Then
        Set obrGP2 = objObject
    Else
        Me.show
        Exit Sub
    End If
    attItem = obrGP2.GetAttributes
    
    tbProject.Value = attItem(0).TextString
    tbWO.Value = attItem(1).TextString
    cbExchange.Value = attItem(2).TextString
    tbRST.Value = attItem(3).TextString
    cbCounty.Value = attItem(4).TextString
    tbCity.Value = attItem(5).TextString
    tbTotalDWG = attItem(7).TextString
    
    Me.show
End Sub

Private Sub Label5_Click()
    Dim objObject As AcadObject
    Dim obrGP2 As AcadBlockReference
    Dim basePnt, attItem As Variant
    
    Me.Hide
  On Error Resume Next
    
    ThisDrawing.Utility.GetEntity objObject, basePnt, "Select SS Info: "
    If TypeOf objObject Is AcadBlockReference Then
        Set obrGP2 = objObject
    Else
        Me.show
        Exit Sub
    End If
    attItem = obrGP2.GetAttributes
    
    cbExchange.Value = attItem(2).TextString
    tbRST.Value = attItem(3).TextString
    cbCounty.Value = attItem(4).TextString
    tbCity.Value = attItem(5).TextString
    
    Me.show
End Sub

Private Sub CommandButton4_Click()
    Me.Hide
        Load TransferToMap
        TransferToMap.show
        Unload TransferToMap
    Me.show
End Sub

Private Sub CommandButton5_Click()
    Me.Hide
        Load ReplaceF1
            ReplaceF1.show
        Unload ReplaceF1
    Me.show
End Sub

Private Sub ConvertSPOle_Click()
    Me.Hide
        Load ConvertToSPole
        ConvertToSPole.show
        Unload ConvertToSPole
    Me.show
End Sub

Private Sub lbSheets_DblClick(ByVal Cancel As MSForms.ReturnBoolean)
    Dim str As String
    Dim strArray As Variant
    Dim viewCoordsB(0 To 2) As Double
    Dim viewCoordsE(0 To 2) As Double
    
    Me.Hide
    
    str = lbSheets.List(lbSheets.ListIndex)
    strArray = Split(str, vbTab)
    
    viewCoordsB(0) = strArray(2)
    viewCoordsB(1) = strArray(3)
    viewCoordsB(2) = 0#
    viewCoordsE(0) = viewCoordsB(0) + 1650 * CDbl(strArray(1))
    viewCoordsE(1) = viewCoordsB(1) + 1050 * CDbl(strArray(1))
    viewCoordsE(2) = 0#
    
    ThisDrawing.Application.ZoomWindow viewCoordsB, viewCoordsE
    Me.show
End Sub

Private Sub SortLBItems()
    Dim strArrayList(), strArraySorted() As String
    Dim attArray, attItem As Variant
    Dim str1, str2, strItem As String
    Dim i, iDWGNum, test1 As Integer
    
  On Error Resume Next
    test1 = 0
    ReDim strArraySorted(0 To lbSheets.ListCount)
    
    For i = 0 To lbSheets.ListCount - 1
        str1 = lbSheets.List(i)
        attArray = Split(str1, vbTab)
        str2 = Right(attArray(0), 3)
        
        If str2 = "" Then GoTo Next_I
        If str2 = "MAP" Then
            iDWGNum = 0
        Else
            iDWGNum = CInt(str2)
        End If
        
        If iDWGNum > test1 Then test1 = iDWGNum
        
        strArraySorted(iDWGNum) = str1
Next_I:
    Next i
    
    lbSheets.Clear
    For i = 0 To test1
        lbSheets.AddItem strArraySorted(i)
    Next i
End Sub

Private Sub LDwgScale_Click()
    Dim entPole As AcadObject
    Dim basePnt As Variant
    
    Me.Hide
  On Error Resume Next
    
    ThisDrawing.Utility.GetEntity entPole, basePnt, "Left Click to Exit: "
    
    Me.show
End Sub

Private Sub UserForm_Initialize()
    
    cbScale.AddItem "50"
    cbScale.AddItem "75"
    cbScale.AddItem "100"
    
    Dim objSS1 As AcadSelectionSet
    Dim entBlock As AcadObject
    Dim obrTemp As AcadBlockReference
    Dim attItem2, vTemp As Variant
    Dim mode As Integer
    'Dim str As String
    Dim filterType, filterValue As Variant
    Dim grpCode(0) As Integer
    Dim grpValue(0) As Variant
    Dim str As String
    
  On Error Resume Next
    
    str = ThisDrawing.Name
    tbWO.Value = Left(str, 8)
    str = Right(str, (Len(str) - 9))
    tbProject.Value = Left(str, (Len(str) - 4))
    
    grpCode(0) = 8
    grpValue(0) = "Integrity Sheets"
    filterType = grpCode
    filterValue = grpValue
    
    Set objSS1 = ThisDrawing.SelectionSets.Add("objSS1")
    objSS1.Select acSelectionSetAll, , , filterType, filterValue
    
    For Each entBlock In objSS1
        'If TypeOf entBlock Is AcadBlockReference Then
            Set obrTemp = entBlock
        'Else
            'MsgBox "Error" & Err
            'GoTo exit_sub
        'End If
        
        If obrTemp.Name = "SS-11x17" Then
            attItem2 = obrTemp.GetAttributes
            vTemp = Split(attItem2(0).TextString, " ")
            'If Not (vTemp(0) = "DWG") Then GoTo Next_entBlock
            Select Case vTemp(0)
                Case "DWG"
                Case "MAP"
                Case "PMT"
                    GoTo Next_entBlock
                'Case Else
                '    GoTo Next_entBlock
            End Select
            'If Not vTemp(0) = "DWG" Then
            '    If vTemp(0) = "MAP" Or vTemp(1) = "MAP" Then
            '    GoTo Next_entBlock
            '
            'End If
                
            str = attItem2(0).TextString & vbTab & obrTemp.XScaleFactor
            str = str & vbTab & obrTemp.InsertionPoint(0) & vbTab & obrTemp.InsertionPoint(1)
            lbSheets.AddItem str
        End If
Next_entBlock:
    Next entBlock
    
    Call SortLBItems
Exit_Sub:
    objSS1.Delete
End Sub

Private Sub UpdateAnchors()
    Dim dTotal, dFeet, dInch As Double
    Dim iFeet, iInch As Integer
    Dim entPole As AcadObject
    Dim obrGP As AcadBlockReference
    Dim attItem, basePnt, vList As Variant
    Dim insertPnt As Variant
    Dim strLH, strPull As String
    Dim vList2 As Variant
    Dim strTemp, strBlockName As String
    Dim vLH As Variant
    Dim dScale, dRotate As Double
    Dim layerObj As AcadLayer
    
    'Me.hide
On Error Resume Next

update_block:
    Err = 0
    
    ThisDrawing.Utility.GetEntity entPole, basePnt, "Select Guy or Anchor: "
    If Not Err = 0 Then GoTo Exit_Sub
    
    If TypeOf entPole Is AcadBlockReference Then
        Set obrGP = entPole
    Else
        GoTo Exit_Sub
    End If
    
    attItem = obrGP.GetAttributes
    
    Select Case obrGP.Name
        Case "ExGuyOR", "ExGuyOL"
            Load ConUpdateGuy
            
            If Not attItem(2).TextString = "" Then
                vLH = Split(attItem(2).TextString, "/")
                ConUpdateGuy.tbLead.Value = vLH(0)
                ConUpdateGuy.tbHeight.Value = vLH(1)
            End If
            
            ConUpdateGuy.show
            
            attItem(2).TextString = ConUpdateGuy.tbLead.Value & "/" & ConUpdateGuy.tbHeight.Value
            attItem(3).TextString = "PE1-3G"
            
            Unload ConUpdateGuy
        Case "ExAncOR", "ExAncOL"
            attItem(0).TextString = "PF1-5A"
    End Select
    obrGP.Update

    GoTo update_block
    
Exit_Sub:
End Sub

Private Sub DropCallout()
    Dim amap As AcadMap
    Dim ODRcs As ODRecords
    Dim tbl As ODTable
    Dim tbls As ODTables
    Dim boolVal As Boolean
    Dim entPole As AcadEntity
    Dim objLWP As AcadLWPolyline
    Dim objPolyline As AcadPolyline
    Dim objLine As AcadLine
    Dim obrDrop As AcadBlockReference
    Dim objBlock As AcadBlockReference
    Dim attItem, vBasePnt As Variant
    Dim strType, strLength As String
    Dim strTemp As String
    Dim dRotate, dScale, Pi As Double
    Dim dTest, dDistScale As Double
    Dim dInsertPnt(0 To 2) As Double
    Dim dStartPnt(0 To 2) As Double
    Dim dEndPnt(0 To 2) As Double
    Dim dToText(0 To 2) As Double
    Dim dFromText(0 To 2) As Double
    Dim dDiff(0 To 2) As Double
    Dim vStartPnt, vEndPnt As Variant
    Dim vCoords, vAttList As Variant
    Dim layerObj As AcadLayer
    Dim iPosition, iLength As Integer
    
    'Me.Hide
  On Error Resume Next
  
    Pi = 3.14159265359
    
    Set amap = ThisDrawing.Application.GetInterfaceObject("AutoCADMap.Application")
    
    Set tbls = amap.Projects(ThisDrawing).ODTables
    
get_Drop:

    dScale = cbScale.Value / 100
    If dScale = 0 Then dScale = 1#
    
    Err = 0
    
    ThisDrawing.Utility.GetEntity entPole, vBasePnt, "Select Drop: "
    
    If Not Err = 0 Then GoTo Exit_Sub
    
    Select Case entPole.ObjectName
        Case "AcDbLine"
            Set objLine = entPole
            iLength = CInt(objLine.Length)
            vStartPnt = objLine.StartPoint
            vEndPnt = objLine.EndPoint
            
            dDiff(0) = vEndPnt(0) - vStartPnt(0)
            dDiff(1) = vEndPnt(1) - vStartPnt(1)
            dDiff(2) = (dDiff(0) * dDiff(0)) + (dDiff(1) * dDiff(1))
            dDiff(2) = Sqr(dDiff(2))
            
            If vBasePnt(0) > vStartPnt(0) Then
                dToText(0) = vBasePnt(0) - vStartPnt(0)
                dToText(1) = vBasePnt(1) - vStartPnt(1)
            Else
                dToText(0) = vStartPnt(0) - vBasePnt(0)
                dToText(1) = vStartPnt(1) - vBasePnt(1)
            End If
            dToText(2) = Sqr((dToText(0) * dToText(0)) + (dToText(1) * dToText(1)))
            
            dDistScale = dToText(2) / dDiff(2)
            dInsertPnt(0) = vStartPnt(0) + (dDiff(0) * dDistScale)
            dInsertPnt(1) = vStartPnt(1) + (dDiff(1) * dDistScale)
            dInsertPnt(2) = 0#
            
            If dToText(0) = 0 Then
                dRotate = Pi / 2
            Else
                dRotate = Atn(dDiff(1) / dDiff(0))
            End If
            
            iPosition = 34
            
            Select Case objLine.Layer
                Case "Integrity Drops-Aerial", "OHSecondary", "OH_Secondary", "F-DROP-A-E"
                    strType = "SEAO"
                Case Else
                    strType = "SEBO"
            End Select
            
            strLength = iLength
            
        Case "AcDbPolyline"
            Set objLWP = entPole
            iLength = CInt(objLWP.Length)
            vCoords = objLWP.Coordinates
            
            For i = 3 To UBound(vCoords) Step 2
                dDiff(0) = vCoords(i - 1) - vCoords(i - 3)
                dDiff(1) = vCoords(i) - vCoords(i - 2)
                dDiff(2) = Sqr((dDiff(0) * dDiff(0)) + (dDiff(1) * dDiff(1)))
            
                dToText(0) = vBasePnt(0) - vCoords(i - 3)
                dToText(1) = vBasePnt(1) - vCoords(i - 2)
                dToText(2) = Sqr((dToText(0) * dToText(0)) + (dToText(1) * dToText(1)))
                
                If dDiff(2) > dToText(2) Then
                    dFromText(0) = vBasePnt(0) - vCoords(i - 1)
                    dFromText(1) = vBasePnt(1) - vCoords(i)
                    dFromText(2) = Sqr((dFromText(0) * dFromText(0)) + (dFromText(1) * dFromText(1)))
                    
                    dTemp = (dFromText(2) + dToText(2)) / dDiff(2)
                    If dTemp < 1.01 Then
                        GoTo Exit_First_Next
                    End If
                End If
            Next i
Exit_First_Next:
            
            dDistScale = Abs(dToText(2) / dDiff(2))
            dInsertPnt(0) = vCoords(i - 3) + (dDiff(0) * dDistScale)
            dInsertPnt(1) = vCoords(i - 2) + (dDiff(1) * dDistScale)
            dInsertPnt(2) = 0#
            
            If dToText(0) = 0 Then
                dRotate = Pi / 2
            Else
                dRotate = Atn(dDiff(1) / dDiff(0))
            End If
            
            Select Case objLWP.Layer
                Case "Integrity Drops-Aerial", "OHSecondary", "OH_Secondary", "F-DROP-A-E"
                    strType = "SEAO"
                Case Else
                    strType = "SEBO"
            End Select
            
            strLength = iLength
            
        Case "AcDbBlockReference"
            Set objBlock = entPole
            
            Select Case objBlock.Name
                Case "Drop"
                    vAttList = objBlock.GetAttributes
                    strTemp = vAttList(0).TextString
                    If InStr(strTemp, "-") > 0 Then
                        vCoords = Split(strTemp, "-")
                        vCoords(0) = CInt(vCoords(0)) + 1
                        vAttList(0).TextString = vCoords(0) & "-" & vCoords(1)
                    Else
                        vAttList(0).TextString = "2-" & vAttList(0).TextString
                    End If
                    
                    objBlock.Update
                Case Else
                    Me.show
                    Exit Sub
            End Select
            
            GoTo get_Drop
        Case Else
            MsgBox entPole.ObjectName
            Me.show
            Exit Sub
    End Select

    Err = 0
    Set obrDrop = ThisDrawing.ModelSpace.InsertBlock(dInsertPnt, "Drop", dScale, dScale, dScale, dRotate)
    If Not Err = 0 Then MsgBox Err.desription
    If strType = "SEAO" Then
        obrDrop.Layer = "Integrity Drops-Aerial Text"
    Else
        obrDrop.Layer = "Integrity Drops-Buried Text"
    End If
    
    vAttList = obrDrop.GetAttributes
    vAttList(0).TextString = strType
    vAttList(1).TextString = strLength & "'"
    obrDrop.Update
    
    GoTo get_Drop
Exit_Sub:

End Sub

Private Sub DeleteDropCallouts()
    Me.Hide
    
    Dim result As Integer
    
    result = MsgBox("Are you sure you want to delete all drop callouts?", vbYesNo, "Delete Drop Callouts")
    If result = vbNo Then
        Me.show
    End If
    
    Dim vDwgLL, vDwgUR As Variant
    Dim filterType, filterValue As Variant
    Dim grpCode(0) As Integer
    Dim grpValue(0) As Variant
    Dim objSS As AcadSelectionSet
    Dim objBlock As AcadBlockReference
    Dim vAtt As Variant
    
    vDwgLL = ThisDrawing.Utility.GetPoint(, "Get DWG LL Corner: ")
    vDwgUR = ThisDrawing.Utility.GetCorner(vDwgLL, vbCr & "Get DWG UR Corner: ")
    
    grpCode(0) = 2
    grpValue(0) = "Drop"
    filterType = grpCode
    filterValue = grpValue
    
    Set objSS = ThisDrawing.SelectionSets.Add("objSS")
    objSS.Select acSelectionSetWindow, vDwgLL, vDwgUR, filterType, filterValue
    If objSS.count < 1 Then GoTo Exit_Sub
    
    For Each objBlock In objSS
        Select Case objBlock.Layer
            Case "Integrity Drops-Aerial Text", "Integrity Drops-Buried Text"
                objBlock.Delete
        End Select
    Next objBlock
    
Exit_Sub:
    objSS.Clear
    objSS.Delete
    
    ThisDrawing.Regen acAllViewports
    
    Me.show
End Sub

Attribute VB_Name = "Module1"
Public Sub AddLLtoPoles()
    Dim objSS As AcadSelectionSet
    Dim filterType, filterValue As Variant
    Dim grpCode(0) As Integer
    Dim grpValue(0) As Variant
    Dim vPnt1, vPnt2 As Variant
    Dim objBlock As AcadBlockReference
    Dim vAttList As Variant
    Dim i As Integer
    
    Dim dN, dE As Double
    Dim vLL As Variant
    
    i = 0

    grpCode(0) = 2
    grpValue(0) = "sPole"
    filterType = grpCode
    filterValue = grpValue
    
  On Error Resume Next
    
    vPnt1 = ThisDrawing.Utility.GetPoint(, "Get BL Corner: ")
    vPnt2 = ThisDrawing.Utility.GetCorner(vPnt1, vbCr & "Get UR Corner: ")
  
    Err = 0
    
    Set objSS = ThisDrawing.SelectionSets.Add("objSS")
    If Not Err = 0 Then
        Set objSS = ThisDrawing.SelectionSets.Item("objSS")
        Err = 0
    End If
    
    objSS.Select acSelectionSetWindow, vPnt1, vPnt2, filterType, filterValue
    If Not Err = 0 Then
        MsgBox "Error: " & Err.Number & vbCr & Err.Description
        Exit Sub
    End If
    
    For Each objBlock In objSS
        vAttList = objBlock.GetAttributes
        'If vAttList(0).TextString = "POLE" Then GoTo Next_objBlock
        'If vAttList(0).TextString = "" Then GoTo Next_objBlock
        
        dE = objBlock.InsertionPoint(0)
        dN = objBlock.InsertionPoint(1)
        vLL = TN83FtoLL(CDbl(dN), CDbl(dE))
        
        vAttList(7).TextString = vLL(0) & "," & vLL(1)
        objBlock.Update
        i = i + 1
Next_objBlock:
    Next objBlock
    
    MsgBox "Lat/Long added to " & i & " poles."
End Sub

Private Function TN83FtoLL(dNorth As Double, dEast As Double)
    Dim dLat, dLong, dDLat As Double
    Dim dDiffE, dEast0 As Double
    Dim dDiffN, dNorth0 As Double
    Dim dR, dCAR, dCA, dU, dK As Double
    Dim LL(2) As Double
    
    dEast = dEast * 0.3048006096
    dNorth = dNorth * 0.3048006096
    
    dDiffE = dEast - 600000
    dDiffN = dNorth - 166504.1691
    
    dR = 8842127.1422 - dDiffN
    dCAR = Atn(dDiffE / dR)
    dCA = dCAR * 180 / 3.14159265359
    dLong = -86 + dCA / 0.585439726459
    
    dU = dDiffN - dDiffE * Tan(dCAR / 2)
    dDLat = dU * (0.00000901305249 + dU * (-6.77268E-15 + dU * (-3.72351E-20 + dU * -9.2828E-28)))
    dLat = 35.8340607459 + dDLat
    
    dK = 0.999948401424 + (1.23188E-14 * dU * dU) + (4.54E-22 * dU * dU * dU)
    
    LL(0) = dLat
    LL(1) = dLong
    LL(2) = dK
    
    TN83FtoLL = LL
End Function

Private Function LLtoTN83F(dLat As Double, dLong As Double)
    Dim dDLat As Double
    Dim dEast, dDiffE, dEast0 As Double
    Dim dNorth, dDiffN, dNorth0 As Double
    Dim dU, dR, dCA, dK As Double
    Dim NE(2) As Double
    
    dDLat = dLat - 35.8340607459
    dU = dDLat * (110950.2019 + dDLat * (9.25072 + dDLat * (5.64572 + dDLat * 0.017374)))
    dR = 8842127.1422 - dU
    dCA = ((86 + dLong) * 0.585439726459) * 3.14159265359 / 180
    
    dDiffE = dR * Sin(dCA)
    dDiffN = dU + dDiffE * Tan(dCA / 2)
    
    dEast = (dDiffE + 600000) / 0.3048006096
    dNorth = (dDiffN + 166504.1691) / 0.3048006096
    
    dK = 0.999948401424 + (1.23188E-14 * dU * dU) + (4.54E-22 * dU * dU * dU)
    
    NE(0) = dNorth
    NE(1) = dEast
    NE(2) = dK
    
    LLtoTN83F = NE
End Function

Public Sub TransferPoleToSheets()
    Dim filterType, filterValue As Variant  '
    Dim grpCode(0) As Integer               '
    Dim grpValue(0) As Variant              '
    Dim objSS7 As AcadSelectionSet          '
    Dim SSobj3 As AcadSelectionSet          '
    Dim objMapPole As AcadBlockReference    '
    Dim objDwgPole As AcadBlockReference    '
    Dim vAttMap, vAttDwg As Variant         '
    Dim vPnt1, vPnt2 As Variant             '
    Dim strPoleNum As String                '
    Dim iTest, iCount  As Integer                   '
    Dim vTemp As Variant
    Dim iHeight As Integer
    Dim strTemp, strPole As String
    Dim strHC As String
    Dim vBasePnt As Variant
    Dim iAttPole, iPower As Integer
    Dim iCATV, iAtt, iTDS, iUTC As Integer
    Dim iXO, iZAYO, iCLEC, iTelco As Integer
    Dim iCity, iTraffic, iOHG As Integer
    Dim strMR As String
    
    On Error GoTo Exit_Sub
    
    iCount = 0
    
    vPnt1 = ThisDrawing.Utility.GetPoint(, "Get DWG BL Corner: ")
    vPnt2 = ThisDrawing.Utility.GetCorner(vPnt1, vbCr & "Get DWG UR Corner: ")
    
    grpCode(0) = 2
    grpValue(0) = "sPole"
    filterType = grpCode
    filterValue = grpValue
    
    Set objSS7 = ThisDrawing.SelectionSets.Add("objSS7")
    objSS7.Select acSelectionSetWindow, vPnt1, vPnt2, filterType, filterValue
    
    vPnt1 = ThisDrawing.Utility.GetPoint(, "Get MAP BL Corner: ")
    vPnt2 = ThisDrawing.Utility.GetCorner(vPnt1, vbCr & "Get MAP UR Corner: ")
    
    grpCode(0) = 2
    grpValue(0) = "sPole"
    filterType = grpCode
    filterValue = grpValue
    
    Set SSobj3 = ThisDrawing.SelectionSets.Add("SSobj3")
    SSobj3.Select acSelectionSetWindow, vPnt1, vPnt2, filterType, filterValue
    
    If objSS7.count < 1 Then GoTo Exit_Sub
    If SSobj3.count < 1 Then GoTo Exit_Sub

    For Each objDwgPole In objSS7
        vAttDwg = objDwgPole.GetAttributes
        strPoleNum = vAttDwg(0).TextString
        
        If strPoleNum = "POLE" Then GoTo Next_objDwgPole
        If strPoleNum = "" Then GoTo Next_objDwgPole
        iTest = 0
        
        For Each objMapPole In SSobj3
            vAttMap = objMapPole.GetAttributes
            
            If strPoleNum = vAttMap(0).TextString Then
                'If vAttDwg(2).TextString = "" Then vAttDwg(2).TextString = vAttMap(2).TextString
                'If vAttDwg(5).TextString = "" Then vAttDwg(5).TextString = vAttMap(5).TextString
                'vAttDwg(6).TextString = vAttMap(6).TextString
                vAttDwg(7).TextString = vAttMap(7).TextString
                
                objDwgPole.Update
                iTest = 1
                iCount = iCount + 1
                GoTo Next_objDwgPole
            End If
        Next objMapPole
Next_objDwgPole:
        If iTest = 0 And Not strPoleNum = "POLE" Then MsgBox strPoleNum & " was not found"
    Next objDwgPole
    
    '<---------------------------------------------------------------------------------------------------------
Exit_Sub:
    If Err <> 0 Then
        MsgBox "Error:" & vbCr & Err.Number & vbCr & Err.Description
    Else
        MsgBox "Done." & vbCr & iCount & " poles updated."
    End If
    
    objSS7.Clear
    objSS7.Delete

    SSobj3.Clear
    SSobj3.Delete
End Sub

Public Sub AddMatchlines()
    Dim objLWP As AcadLWPolyline
    Dim objText As AcadText
    Dim objBlock As AcadBlockReference
    Dim basePnt, returnPnt As Variant
    Dim vLWPO, vCoords, vTemp As Variant
    Dim lwpCoords(0 To 3) As Double
    Dim dTextInsert(0 To 2) As Double
    Dim dMidPnt(0 To 2) As Double
    Dim xDiff, yDiff, zDiff As Double
    Dim dRotate, dScale, dXScale, dTScale As Double
    Dim strLine, strTemp As String
    Dim iStatus As Integer
    
    On Error Resume Next
    
    While Err = 0
        returnPnt = ThisDrawing.Utility.GetPoint(, "Select First Point: ")
        lwpCoords(0) = returnPnt(0)
        lwpCoords(1) = returnPnt(1)
        
        vCoords = returnPnt
        
        If Not Err = 0 Then GoTo Exit_Sub
        
        returnPnt = ThisDrawing.Utility.GetPoint(, "Select Second Point: ")
        lwpCoords(2) = returnPnt(0)
        lwpCoords(3) = returnPnt(1)
        
        dMidPnt(0) = (lwpCoords(0) + lwpCoords(2)) / 2
        dMidPnt(1) = (lwpCoords(1) + lwpCoords(3)) / 2
        dMidPnt(2) = 0#
        
        strLine = UCase(ThisDrawing.Utility.GetString(0, "Matches Drawing #: "))
        
        If Not Err = 0 Then GoTo Exit_Sub
        
        strTemp = GetScale(vCoords)
        vTemp = Split(strTemp, ";;")
        strLayer = vTemp(0)
        dScale = CDbl(vTemp(1))
        dTScale = 8 * (dScale / 1.3333)
        
        If InStr(strLine, "R") > 0 Then
            strLine = Replace(strLine, "R", "")
            iStatus = 1
        Else
            iStatus = 0
        End If
        
        Select Case Len(strLine)
            Case Is = 1
                strLine = "SEE DWG 00" & strLine
            Case Is = 2
                strLine = "SEE DWG 0" & strLine
            Case Is = 3
                strLine = "SEE DWG " & strLine
        End Select
        
        xDiff = lwpCoords(2) - lwpCoords(0)
        yDiff = lwpCoords(3) - lwpCoords(1)
        zDiff = Sqr((xDiff * xDiff) + (yDiff * yDiff))
            
        Select Case xDiff
            Case Is < 0
                If yDiff = 0 Then
                    dRotate = 0#
                ElseIf yDiff < 0 Then
                    dRotate = Atn(yDiff / xDiff)
                Else
                    dRotate = Atn(yDiff / xDiff) '+ 3.14159265359
                End If
                
                If iStatus = 1 Then
                    dMidPnt(0) = dMidPnt(0) - 13.5 * yDiff / zDiff * dScale
                    dMidPnt(1) = dMidPnt(1) + 13.5 * xDiff / zDiff * dScale
                End If
                
                dTextInsert(0) = dMidPnt(0) - 13.5 * yDiff / zDiff * dScale
                dTextInsert(1) = dMidPnt(1) + 13.5 * xDiff / zDiff * dScale
            Case Is = 0
                dRotate = 1.570796327
                
                If yDiff > 0 Then
                    If iStatus = 1 Then
                        dMidPnt(0) = dMidPnt(0) - 7.5 * yDiff / zDiff * dScale
                        dMidPnt(1) = dMidPnt(1) + 7.5 * xDiff / zDiff * dScale
                    End If
                    
                    dTextInsert(0) = dMidPnt(0) - 7.5 * yDiff / zDiff * dScale
                    dTextInsert(1) = dMidPnt(1) + 7.5 * xDiff / zDiff * dScale
                Else
                    If iStatus = 1 Then
                        dMidPnt(0) = dMidPnt(0) - 13.5 * yDiff / zDiff * dScale
                        dMidPnt(1) = dMidPnt(1) + 13.5 * xDiff / zDiff * dScale
                    End If
                    
                    dTextInsert(0) = dMidPnt(0) - 13.5 * yDiff / zDiff * dScale
                    dTextInsert(1) = dMidPnt(1) + 13.5 * xDiff / zDiff * dScale
                End If
            Case Is > 0
                If yDiff = 0 Then
                    dRotate = 0#
                ElseIf yDiff > 0 Then
                    dRotate = Atn(yDiff / xDiff)
                Else
                    dRotate = Atn(yDiff / xDiff) '+ 3.14159265359
                End If
                
                If iStatus = 1 Then
                    dMidPnt(0) = dMidPnt(0) - 7.5 * yDiff / zDiff * dScale
                    dMidPnt(1) = dMidPnt(1) + 7.5 * xDiff / zDiff * dScale
                End If
                
                dTextInsert(0) = dMidPnt(0) - 7.5 * yDiff / zDiff * dScale
                dTextInsert(1) = dMidPnt(1) + 7.5 * xDiff / zDiff * dScale
        End Select
        
        dTextInsert(2) = 0#
        
        'If xDiff < 0 Then
            'dTextInsert(0) = dTextInsert(0) - 13.5 * yDiff / zDiff
            'dTextInsert(1) = dTextInsert(1) + 13.5 * xDiff / zDiff
        'Else
            'dTextInsert(0) = dTextInsert(0) - 7.5 * yDiff / zDiff
            'dTextInsert(1) = dTextInsert(1) + 7.5 * xDiff / zDiff
        'End If
        
        If iStatus = 0 Then
            lwpCoords(2) = lwpCoords(0) + (zDiff + 10) * xDiff / zDiff
            lwpCoords(3) = lwpCoords(1) + (zDiff + 10) * yDiff / zDiff
            lwpCoords(0) = lwpCoords(2) - (zDiff + 20) * xDiff / zDiff
            lwpCoords(1) = lwpCoords(3) - (zDiff + 20) * yDiff / zDiff
        
            Set objLWP = ThisDrawing.ModelSpace.AddLightWeightPolyline(lwpCoords)
            objLWP.Layer = "Integrity Sheets"
            objLWP.Update
        
            vLWPO = objLWP.Offset(-5)
        Else
            dXScale = dScale * ((zDiff + 20) / 100)
            
            Err = 0
            Set objBlock = ThisDrawing.ModelSpace.InsertBlock(dMidPnt, "RefLine", dXScale, dScale, dScale, dRotate)
            If Not Err = 0 Then
                MsgBox "Block may not be in drawing."
                GoTo Exit_Sub
            End If
            objBlock.Layer = strLayer
            objBlock.Update
        End If
            
        Set objText = ThisDrawing.ModelSpace.AddText(strLine, dTextInsert, dTScale)
        objText.Layer = "Integrity Sheets"
        objText.Alignment = acAlignmentCenter
        objText.TextAlignmentPoint = dTextInsert
        objText.Rotation = dRotate
        objText.Update
    Wend
Exit_Sub:
End Sub

Private Function GetScale(vCoords As Variant)
    Dim filterType, filterValue As Variant
    Dim grpCode(0) As Integer
    Dim grpValue(0) As Variant
    Dim objSS As AcadSelectionSet
    Dim objBlock As AcadBlockReference
    Dim vAttList As Variant
    Dim strLine As String
    Dim dMinX, dMaxX, dMinY, dMaxY As Double
    Dim dScale As Double
    
    On Error Resume Next
    
    strLine = "none;;"
    
    grpCode(0) = 2
    grpValue(0) = "SS-11x17"
    filterType = grpCode
    filterValue = grpValue
    
    Set objSS = ThisDrawing.SelectionSets.Add("objSS")
    If Not Err = 0 Then
        Set objSS = ThisDrawing.SelectionSets.Item("objSS")
        objSS.Clear
    End If
    
    objSS.Select acSelectionSetAll, , , filterType, filterValue
    
    For Each objBlock In objSS
        dScale = objBlock.XScaleFactor
        dMinX = objBlock.InsertionPoint(0)
        dMaxX = dMinX + (1652 * dScale)
        
        dMinY = objBlock.InsertionPoint(1)
        dMaxY = dMinY + (1052 * dScale)
        
        If vCoords(0) > dMinX And vCoords(0) < dMaxX Then
            If vCoords(1) > dMinY And vCoords(1) < dMaxY Then
                dScale = dScale * 1.333333333
                strLine = objBlock.Layer & ";;"
                GoTo Exit_Sub
            End If
        End If
    Next objBlock
    
    dScale = 1#
    
Exit_Sub:
    objSS.Clear
    objSS.Delete
    
    strLine = strLine & dScale
    GetScale = strLine
End Function

Attribute VB_Name = "Module2"

Public Sub LaunchMainMenu()
    Dim strPath As String
    
    strPath = LCase(ThisDrawing.Application.vbe.ActiveVBProject.Filename)
    
    If InStr(strPath, "integrity") = 0 Then Exit Sub
    
    'MsgBox ThisDrawing.Path & vbCr & ThisDrawing.Name
    If InStr(ThisDrawing.Name, "Drawing") > 0 Then
        If InStr(LCase(ThisDrawing.Path), "dropbox") = 0 Then
            Load ProjectOpen
                ProjectOpen.show
            Unload ProjectOpen
            
            Exit Sub
        End If
    End If
    
    Dim objSS As AcadSelectionSet
    Dim objEntity As AcadEntity
    Dim objText As AcadText
    Dim filterType, filterValue As Variant
    Dim grpCode(0) As Integer
    Dim grpValue(0) As Variant
    Dim iVersion As Integer
    
    iVersion = 1
    
    grpCode(0) = 8
    grpValue(0) = "Integrity Border Info"
    filterType = grpCode
    filterValue = grpValue
    
    On Error Resume Next
    Set objSS = ThisDrawing.SelectionSets.Item("objSS")
    If Not Err = 0 Then
        Set objSS = ThisDrawing.SelectionSets.Add("objSS")
        Err = 0
    End If
    
    objSS.Select acSelectionSetAll, , , filterType, filterValue
    
    For Each objEntity In objSS
        If TypeOf objEntity Is AcadText Then
            Set objText = objEntity
            If objText.TextString = "THIS JOB IS USING ENGINEERING 2.0" Then
                iVersion = 2
                GoTo Found_Version
            End If
        End If
    Next objEntity
    
Found_Version:
    
    objSS.Clear
    objSS.Delete
    
    Select Case iVersion
        Case Is = 1
            Application.LoadDVB "C:\Integrity\VBA\UTC.dvb"
            Application.RunMacro "AddModule.startMainForm"
        Case Is = 2
            Load MainForm
                MainForm.show
            Unload MainForm
    End Select
End Sub

Public Sub startMainForm()
    Dim strPath As String
    
    strPath = LCase(ThisDrawing.Application.vbe.ActiveVBProject.Filename)
    
    'MsgBox strPath
    If InStr(strPath, "integrity") = 0 Then Exit Sub
    
    Load MainForm
    MainForm.show
    Unload MainForm
End Sub

Public Sub United_Request()
    
End Sub

Attribute VB_Name = "Module3"
Public Sub ChangeODataLayers()
    Dim filterType, filterValue As Variant
    Dim grpCode(0) As Integer
    Dim grpValue(0) As Variant
    Dim objSS As AcadSelectionSet
    
    Dim objEntity As AcadEntity
    Dim objLWP As AcadLWPolyline
    Dim objLine As AcadLine
    Dim strFeeder, strLayer As String
    Dim iCount As Integer
    
    Dim amap As AcadMap
    Dim ODRcs As ODRecords
    Dim ODRc As ODRecord
    Dim tbl As ODTable
    Dim tbls As ODTables
    Dim boolVal As Boolean
    
    On Error Resume Next
    
    grpCode(0) = 8
    grpValue(0) = "OH_Primary"
    filterType = grpCode
    filterValue = grpValue
    
    Set objSS = ThisDrawing.SelectionSets.Add("objSS")
    If Not Err = 0 Then
        Set objSS = ThisDrawing.SelectionSets.Item("objSS")
        objSS.Clear
        Err = 0
    End If
    
    objSS.Select acSelectionSetAll, , , filterType, filterValue
    MsgBox "Objects found:  " & objSS.count
        
    Err = 0
    Set amap = ThisDrawing.Application.GetInterfaceObject("AutoCADMap.Application")
    
    Set tbls = amap.Projects(ThisDrawing).ODTables
    If tbls.count > 0 Then
        For Each tbl In tbls
            If tbl.Name = "OH_Primary" Then GoTo Exit_For
        Next
    End If
    
Exit_For:
    
    iCount = 0
    For Each objEntity In objSS
        iCount = iCount + 1
        If iCount > 10 Then GoTo Exit_Sub
        
        Set ODRcs = tbl.GetODRecords
        boolVal = ODRcs.Init(objEntity, True, False)
        Set ODRc = ODRcs.Record
        
        MsgBox Err.Description
        MsgBox iCount & vbCr & ODRc.Item(2).Value
        
        If Not Err = 0 Then GoTo Next_objEntity
        
        strFeeder = ODRc.Item(7).Value
        If strFeeder = "" Then GoTo Next_objEntity
        
        Select Case CInt(strFeeder)
            Case Is < 200
                objEntity.Layer = "OH_Primary - 100"
            Case Is < 300
                If CInt(strFeeder) > 200 Then strLayer = "OH_Primary - 200"
            Case Is < 400
                If CInt(strFeeder) > 300 Then strLayer = "OH_Primary - 300"
            Case Is < 500
                If CInt(strFeeder) > 400 Then strLayer = "OH_Primary - 400"
            Case Is < 600
                If CInt(strFeeder) > 500 Then strLayer = "OH_Primary - 500"
            Case Is < 700
                If CInt(strFeeder) > 600 Then strLayer = "OH_Primary - 600"
            Case Is < 800
                If CInt(strFeeder) > 700 Then strLayer = "OH_Primary - 700"
            Case Is < 900
                If CInt(strFeeder) > 800 Then strLayer = "OH_Primary - 800"
            Case Is < 1000
                If CInt(strFeeder) > 900 Then strLayer = "OH_Primary - 900"
            Case Else
                If CInt(strFeeder) > 1000 Then strLayer = "OH_Primary - 1000"
        End Select
        
        If TypeOf objEntity Is AcadLine Then
            Set objLine = objEntity
            objLine.Layer = strLayer
            
            objLine.Update
        Else
            Set objLWP = objEntity
            objLWP.Layer = strLayer
            
            objLWP.Update
        End If
        
Next_objEntity:
        'Set ODRc = Nothing
        Err = 0
    Next objEntity
    
Exit_Sub:
    objSS.Clear
    objSS.Delete
End Sub

Attribute VB_Name = "Module4"
Public Sub Export()
    Dim vbe As vbe
    Set vbe = ThisDrawing.Application.vbe
    Dim comp As VBComponent
    Dim outDir As String
    outDir = "C:\Users\GabrielFinke\OneDrive - Wecom LLC\Documents\autocad"
    If Dir(outDir, vbDirectory) = "" Then
        MkDir outDir
    End If
    For Each comp In vbe.ActiveVBProject.VBComponents
        Select Case comp.Type
            Case vbext_ct_StdModule
                comp.Export outDir & "\" & comp.Name & ".bas"
            Case vbext_ct_Document, vbext_ct_ClassModule
                comp.Export outDir & "\" & comp.Name & ".cls"
            Case vbext_ct_MSForm
                comp.Export outDir & "\" & comp.Name & ".frm"
            Case Else
                comp.Export outDir & "\" & comp.Name
        End Select
    Next comp

     MsgBox "VBA files were exported to : " & outDir
End Sub

Attribute VB_Name = "NewCableForm"
Attribute VB_Base = "0{AFC7442E-07C1-4085-9B98-C5E174C905EA}{2BB29463-7560-4F11-B81E-91C60EAFB2D6}"
Attribute VB_GlobalNameSpace = False
Attribute VB_Creatable = False
Attribute VB_PredeclaredId = True
Attribute VB_Exposed = False
Attribute VB_TemplateDerived = False
Attribute VB_Customizable = False
Dim iListIndex As Integer



Private Sub cbAdd_Click()
    Dim strLine As String

    strLine = tbFFiber.Value & "-" & tbTFiber.Value
    lbCounts.AddItem strLine
    
    strLine = cbCblName.Value & ": " & tbFCount.Value & "-" & tbTCount.Value
    lbCounts.List(lbCounts.ListCount - 1, 1) = strLine
End Sub

Private Sub cbCableSize_Change()
    If lbCounts.Value = "" Then Exit Sub
    
    
End Sub

Private Sub cbCancel_Click()
    If cbCblType.Value = "" Then
        MsgBox "Need Cable Type."
        Exit Sub
    End If
    If cbCableSize.Value = "" Then
        MsgBox "Need Cable Size."
        Exit Sub
    End If
    If tbPosition.Value = "" Then
        MsgBox "Need Cable Position."
        Exit Sub
    End If
    If cbCblType.Value = "CO" Then
        If cbSuffix.Value = "" Then
            MsgBox "Need Cable Suffix."
            Exit Sub
        End If
    End If
    
    Dim vList, vFibers, vCable, vCounts As Variant
    Dim iFiber, iTotal, iAtt As Integer
    Dim iSFiber, iEFiber, iSCount, iECount As Integer
    Dim strCblName As String
    
    Dim objEntity As AcadEntity
    Dim objBlock As AcadBlockReference
    Dim vAttList, vReturnPnt As Variant
    
    If Me.Caption = "Tap Cable" Then
        strCblName = tbPosition.Value & ": " & cbCblType.Value & "(" & cbCableSize.Value & ")"
        If Not cbSuffix.Value = "" Then strCblName = strCblName & cbSuffix.Value
        strCblName = strCblName & " / "
        
        If lbCounts.ListCount > 0 Then
            strCblName = strCblName & lbCounts.List(0, 1) & ": "
            If InStr(lbCounts.List(0, 1), "XD") > 0 Then
                strCblName = strCblName & "END"
            Else
                strCblName = strCblName & CountsForm.tbPoleNumber.Value
            End If
            
            If lbCounts.ListCount > 1 Then
                For i = 1 To lbCounts.ListCount - 1
                    strCblName = strCblName & " + " & lbCounts.List(i, 1) & ": "
                    If InStr(lbCounts.List(i, 1), "XD") > 0 Then
                        strCblName = strCblName & "END"
                    Else
                        strCblName = strCblName & CountsForm.tbPoleNumber.Value
                    End If
                Next i
            End If
        End If
        
        'MsgBox strCblName
        
        Me.Hide
        
        On Error Resume Next
        
        Err = 0
        ThisDrawing.Utility.GetEntity objEntity, vReturnPnt, vbCr & "Select Block:"
        If Not Err = 0 Then Exit Sub
        
        If Not TypeOf objEntity Is AcadBlockReference Then Exit Sub
        Set objBlock = objEntity
        
        Select Case objBlock.Name
            Case "sPole"
                iAtt = 25
            Case "sPed", "sHH", "sPanel"
                iAtt = 5
            Case Else
                Exit Sub
        End Select
        
        vAttList = objBlock.GetAttributes
        'If vAttList(iAtt).TextString = "" Then
            vAttList(iAtt).TextString = strCblName
        'Else
        'End If
        
        objBlock.Update
            
        Exit Sub
    End If
    
    iFiber = 1
    iTotal = CInt(cbCableSize.Value)
    strCblName = CountsForm.tbF1Name.Value
    
    CountsForm.lbCounts.AddItem ""
    For k = 1 To iTotal
        CountsForm.lbCounts.AddItem
        CountsForm.lbCounts.List(k, 0) = k
        CountsForm.lbCounts.List(k, 1) = "XD"
        CountsForm.lbCounts.List(k, 2) = k
        CountsForm.lbCounts.List(k, 3) = "<>"
        CountsForm.lbCounts.List(k, 4) = "<>"
        CountsForm.lbCounts.List(k, 5) = "<>"
        CountsForm.lbCounts.List(k, 6) = "<>"
        CountsForm.lbCounts.List(k, 7) = "<>"
    Next k
    
    For i = 0 To lbCounts.ListCount - 1
        vList = Split(lbCounts.List(i, 0), vbTab)
        vFibers = Split(vList(0), "-")
        iSFiber = CInt(vFibers(0))
        iEFiber = CInt(vFibers(1))
        
        vCable = Split(lbCounts.List(i, 1), ": ")
        vCounts = Split(vCable(1), "-")
        iSCount = CInt(vCounts(0))
        iECount = CInt(vCounts(1))
        
        If iSFiber < iFiber Then GoTo Next_I
        If iSFiber > iTotal Then GoTo Next_I
        
        For j = iSFiber To iEFiber
            CountsForm.lbCounts.List(j, 1) = vCable(0)
            CountsForm.lbCounts.List(j, 2) = iSCount
            
            'If vCable(0) = strCblName Then
                'DesignCountForm.lbCounts.List(j, 1) = iSCount
            'Else
                'DesignCountForm.lbCounts.List(j, 1) = " "
                'DesignCountForm.lbCounts.List(j, 6) = vCable(0) & ": " & iSCount
            'End If
            iSCount = iSCount + 1
        Next j
Next_I:
    Next i
    
    CountsForm.cbCableSize.Value = cbCableSize.Value

    Me.Hide
End Sub

Private Sub cbCblType_Change()
    If cbCblType.Value = "CO" Then
        cbSuffix.AddItem ""
        cbSuffix.AddItem "E"
        cbSuffix.AddItem "6M-EHS"
        cbSuffix.AddItem "10M"
        cbSuffix.Enabled = True
    Else
        cbSuffix.Clear
        cbSuffix.Value = ""
        cbSuffix.Enabled = False
    End If
End Sub

Private Sub cbCLR_Click()
    lbCounts.Clear
End Sub

Private Sub cbDelete_Click()
    lbCounts.RemoveItem (lbCounts.ListIndex)
End Sub

Private Sub cbDOWN_Click()
    Dim str1 As String
    Dim i, i2 As Integer
    
    If lbCounts.ListIndex = (lbCounts.ListCount - 1) Then Exit Sub
    i = lbCounts.ListIndex
    i2 = i + 1
    str1 = lbCounts.List(i)
    lbCounts.List(i) = lbCounts.List(i2)
    lbCounts.List(i2) = str1
    
    lbCounts.ListIndex = i2
End Sub

Private Sub cbGetCable_Click()
    Dim objEntity As AcadEntity
    Dim objBlock As AcadBlockReference
    Dim vReturnPnt, vAttList As Variant
    Dim vLine, vItem, vCount As Variant
    Dim iStart, iEnd As Integer
    Dim iFiber, iEndFiber As Integer
    Dim iCable, iCount As Integer
    
    Me.Hide
    On Error Resume Next
    
    ThisDrawing.Utility.GetEntity objEntity, vReturnPnt, vbCr & "Select Callout:"
    If Not Err = 0 Then GoTo Exit_Sub
    
    If Not TypeOf objEntity Is AcadBlockReference Then GoTo Exit_Sub
    Set objBlock = objEntity
    
    iCable = 1
    Select Case objBlock.Name
        Case "Callout"
            iCount = 2
        Case "CableCounts"
            iCount = 0
        Case Else
            GoTo Exit_Sub
    End Select
    'If Not objBlock.Name = "Callout" Then GoTo Exit_Sub
    vAttList = objBlock.GetAttributes
    
    If Not vAttList(iCable).TextString = "" Then
        vLine = Split(vAttList(iCable).TextString, "(")
        cbCblType.Value = vLine(0)
        If UBound(vLine) > 0 Then
            vItem = Split(vLine(1), ")")
            cbCableSize.Value = vItem(0)
            If UBound(vItem) > 0 Then cbSuffix.Value = vItem(1)
        End If
    End If
    
    iFiber = 1
    
    If Not vAttList(iCount).TextString = "" Then
        vLine = Split(vAttList(iCount).TextString, "\P")
        For i = 0 To UBound(vLine)
            vItem = Split(vLine(i), ": ")
            vCount = Split(vItem(1), "-")
            iStart = CInt(vCount(0))
            If UBound(vCount) > 0 Then
                iEnd = CInt(vCount(1))
            Else
                iEnd = iStart
            End If
            
            iEndFiber = iFiber + iEnd - iStart
            lbCounts.AddItem iFiber & "-" & iEndFiber
            lbCounts.List(lbCounts.ListCount - 1, 1) = vLine(i)
            iFiber = iEndFiber + 1
        Next i
    End If
    
Exit_Sub:
    Me.show
End Sub

Private Sub cbUP_Click()
    Dim str1 As String
    Dim i, i2 As Integer
    
    If lbCounts.ListIndex = 0 Then Exit Sub
    i = lbcountss.ListIndex
    i2 = i - 1
    str1 = lbCounts.List(i)
    lbCounts.List(i) = lbCounts.List(i2)
    lbCounts.List(i2) = str1
    
    lbCounts.ListIndex = i2
End Sub

Private Sub lbCounts_DblClick(ByVal Cancel As MSForms.ReturnBoolean)
    Dim iIndex As Integer
    Dim vLine, vItem, vTemp As Variant
    
    iIndex = lbCounts.ListIndex
    
    vTemp = Split(lbCounts.List(iIndex, 0), "-")
    
    tbFFiber.Value = vTemp(0)
    tbTFiber.Value = vTemp(1)
    
    vLine = Split(lbCounts.List(iIndex, 1), ": ")
    cbCblName.Value = vLine(0)
    
    vItem = Split(vLine(1), "-")
    tbFCount.Value = vItem(0)
    
    lbCounts.RemoveItem iIndex
End Sub

Private Sub tbFCount_AfterUpdate()
    Dim iFFiber, iTFiber, iFCount, iTCount As Integer
    Dim iDiff As Integer
    Dim dTest As Double
    
    iFFiber = CInt(tbFFiber.Value)
    iTFiber = CInt(tbTFiber.Value)
    iFCount = CInt(tbFCount.Value)
    iDiff = iFCount - iFFiber
    dTest = iDiff / 12
    If Not (dTest - Int(dTest)) = 0 Then MsgBox "Off-Color"
    iDiff = iTFiber - iFFiber
    tbTCount.Value = iFCount + iDiff
End Sub

Private Sub tbFFiber_AfterUpdate()
    If CInt(tbFFiber.Value) > CInt(cbCableSize.Value) Then tbFFiber.Value = 1
End Sub

Private Sub tbTFiber_AfterUpdate()
    If CInt(tbTFiber.Value) > CInt(cbCableSize.Value) Then tbTFiber.Value = cbCableSize.Value
End Sub

Private Sub UserForm_Initialize()
    cbCblType.AddItem ""
    cbCblType.AddItem "CO"
    cbCblType.AddItem "BFO"
    cbCblType.AddItem "UO"
    
    cbCableSize.AddItem ""
    cbCableSize.AddItem "12"
    cbCableSize.AddItem "24"
    cbCableSize.AddItem "36"
    cbCableSize.AddItem "48"
    cbCableSize.AddItem "72"
    cbCableSize.AddItem "96"
    cbCableSize.AddItem "144"
    cbCableSize.AddItem "216"
    cbCableSize.AddItem "288"
    cbCableSize.AddItem "360"
    cbCableSize.AddItem "432"
    
    cbUP.Caption = Chr(225)
    cbDOWN.Caption = Chr(226)
    
    On Error Resume Next
    
    cbCblName.AddItem "XD"
    cbCblName.AddItem CountsForm.tbF1Name.Value
    cbCblName.AddItem CountsForm.tbF2Name.Value
    
    cbCblType.Value = CountsForm.cbCblType.Value
    cbCableSize.Value = CountsForm.cbCableSize.Value
    If cbCableSize.Value = "" Then cbCableSize.Value = "144"
    
    cbSuffix.Value = CountsForm.cbSuffix.Value
    
    lbCounts.ColumnCount = 2
    lbCounts.ColumnWidths = "36;108"
End Sub

Attribute VB_Name = "ObjectDataInquiry"
Attribute VB_Base = "0{9B6F1C09-BB1D-4E25-8E33-E64A1BC93247}{5C8630FB-42ED-44D2-9D79-849EBA5DD449}"
Attribute VB_GlobalNameSpace = False
Attribute VB_Creatable = False
Attribute VB_PredeclaredId = True
Attribute VB_Exposed = False
Attribute VB_TemplateDerived = False
Attribute VB_Customizable = False
Private Sub cbAmount_Change()
    If cbAmount.Value = "Sum" Then
        Label7.Visible = True
        tbIndex.Visible = True
    Else
        Label7.Visible = False
        tbIndex.Visible = False
    End If
End Sub

Private Sub cbDeselectAll_Click()
    If lbValues.ListCount < 1 Then Exit Sub
    
    For i = 0 To lbValues.ListCount - 1
        lbValues.Selected(i) = False
    Next i
End Sub

Private Sub cbFromList_Change()
    Dim amap As AcadMap
    Dim ODRcs As ODRecords
    Dim ODRc As ODRecord
    Dim tbl As ODTable
    Dim tbls As ODTables
    Dim refColumn As ODFieldDef
    Dim objEntity As AcadEntity
    Dim boolVal As Boolean
    Dim iCount As Integer
    Dim strTest As String
    
    On Error Resume Next
    
    Set amap = ThisDrawing.Application.GetInterfaceObject("AutoCADMap.Application")
    
    Set tbls = amap.Projects(ThisDrawing).ODTables
    If tbls.count > 0 Then
        For Each tbl In tbls
            If tbl.Name = cbFromList.Value Then GoTo Exit_For
        Next
    End If
Exit_For:

    Set ODRcs = tbl.GetODRecords
        
    iCount = 0
    Err = 0
    
    lbFrom.Clear
        
    While Err = 0
        Set refColumn = tbl.ODFieldDefs(iCount)
        strTest = refColumn.Name
        If Not Err = 0 Then GoTo Exit_objEntity
            
        lbFrom.AddItem
        lbFrom.List(iCount, 0) = iCount
        lbFrom.List(iCount, 1) = strTest
        iCount = iCount + 1
    Wend
Exit_objEntity:
    
    'For i = 0 To lbFrom.ListCount - 1
        'If lbFrom.List(i, 1) = "FID_NUMBER" Then
            'lbFrom.Selected(i) = True
            'Exit Sub
        'End If
    'Next i
End Sub

Private Sub cbGetPolygon_Click()
    If cbAmount.Value = "Sum" And tbIndex.Value = "" Then Exit Sub
    
    Dim amap As AcadMap
    Dim tbl As ODTable
    Dim tbls As ODTables
    
    Dim filterType, filterValue As Variant
    Dim grpCode(0) As Integer
    Dim grpValue(0) As Variant
    Dim objSS As AcadSelectionSet
    Dim objEntity As AcadEntity
    Dim objPoint As AcadPoint
    Dim objLine As AcadLine
    Dim objLWP As AcadLWPolyline
    Dim vReturnPnt As Variant
    Dim vLine As Variant
    Dim strLine, strTemp As String
    Dim iIndex, iLIndex, iAmount As Integer
    Dim dCoords() As Double
    Dim iCounter As Integer
    'Dim iNPG, iGN As Integer
    
    On Error Resume Next
    
    'iNPG = CInt(tbNPG.Value)
    'iGN = 0
    
    If lbFrom.ListIndex < 0 Then Exit Sub
    iIndex = CInt(lbFrom.List(lbFrom.ListIndex, 0))
    
    lbValues.Clear
    
    If tbIndex.Visible = True And Not tbIndex.Value = "" Then iLIndex = CInt(tbIndex.Value)
    
    'strLine = ""
    
    Set amap = ThisDrawing.Application.GetInterfaceObject("AutoCADMap.Application")
    
    Set tbls = amap.Projects(ThisDrawing).ODTables
    If tbls.count > 0 Then
        For Each tbl In tbls
            If tbl.Name = cbFromList.Value Then GoTo Exit_For
        Next
    End If
    
    Exit Sub
    
Exit_For:
    
    Set ODRcs = tbl.GetODRecords
    
    Me.Hide
    
    ThisDrawing.Utility.GetEntity objEntity, vReturnPnt, "Select Polygon Border: "
    If Not objEntity.ObjectName = "AcDbPolyline" Then
        MsgBox "Error: Invalid Selection."
        Me.show
        Exit Sub
    End If
    
    Set objLWP = objEntity
    vCoords = objLWP.Coordinates
    
    iTemp = (UBound(vCoords) + 1) / 2 * 3 - 1
    ReDim dCoords(iTemp) As Double
    
    iCounter = 0
    For i = 0 To UBound(vCoords) Step 2
        dCoords(iCounter) = vCoords(i)
        iCounter = iCounter + 1
        dCoords(iCounter) = vCoords(i + 1)
        iCounter = iCounter + 1
        dCoords(iCounter) = 0#
        iCounter = iCounter + 1
    Next i
    
    grpCode(0) = 8
    grpValue(0) = cbFromList.Value
    filterType = grpCode
    filterValue = grpValue
    
    Err = 0
    Set objSS = ThisDrawing.SelectionSets.Add("objSS")
    If Not Err = 0 Then Set objSS = ThisDrawing.SelectionSets.Item("objSS")
    
    objSS.SelectByPolygon acSelectionSetWindowPolygon, dCoords, filterType, filterValue
    
        'MsgBox objSS.Item(0).ObjectName & vbCr & objSS.Item(0).ObjectID
        'GoTo Exit_Sub
    
    
    For Each objEntity In objSS
        'Select Case objEntity.ObjectName
            'Case "AcDbPoint"
                'Set objPoint = objEntity
            
                boolVal = ODRcs.Init(objEntity, True, False)
                Set ODRc = ODRcs.Record
                
                strTemp = ODRc.Item(iIndex).Value
                If strTemp = "" Then GoTo Next_Object
                
                If lbValues.ListCount > 0 Then
                    For i = 0 To lbValues.ListCount - 1
                        If strTemp = lbValues.List(i, 1) Then
                            If cbAmount.Value = "Sum" Then
                                iAmount = CInt(ODRc.Item(iLIndex).Value)
                                lbValues.List(i, 0) = CLng(lbValues.List(i, 0)) + iAmount
                            Else
                                lbValues.List(i, 0) = CInt(lbValues.List(i, 0)) + 1
                            End If
                            
                            GoTo Next_Object
                        End If
                    Next i
                End If
                
                If cbAmount.Value = "Sum" Then
                    iAmount = CInt(ODRc.Item(iLIndex).Value)
                    lbValues.AddItem iAmount
                    lbValues.List(lbValues.ListCount - 1, 1) = strTemp
                Else
                    lbValues.AddItem "1"
                    lbValues.List(lbValues.ListCount - 1, 1) = strTemp
                End If
            'Case "AcDbLine"
            'Case "AcDbPolyline"
            'Case "AcDbBlockReference"
        'End Select
Next_Object:
    Next objEntity
    
    'tbResult.Value = strLine
Exit_Sub:
    objSS.Clear
    objSS.Delete
    
    Me.show
End Sub

Private Sub cbSearchText_Click()
    If lbValues.ListCount < 1 Then Exit Sub
    If tbFind.Value = "" Then Exit Sub
    
    Dim strText, strFind As String
    
    strFind = UCase(tbFind.Value)
    
    For i = 0 To lbValues.ListCount - 1
        strText = UCase(lbValues.List(i, 1))
        
        If InStr(strText, strFind) > 0 Then lbValues.Selected(i) = True
    Next i
End Sub

Private Sub cbSelectAll_Click()
    If lbValues.ListCount < 1 Then Exit Sub
    
    For i = 0 To lbValues.ListCount - 1
        lbValues.Selected(i) = True
    Next i
End Sub

Private Sub cbTotalSelected_Click()
    If lbValues.ListCount < 1 Then Exit Sub
    
    Dim lTotal, lTemp As Long
    
    lTotal = 0#
    
    For i = 0 To lbValues.ListCount - 1
        If lbValues.Selected(i) = True Then
            lTemp = CLng(lbValues.List(i, 0))
            lTotal = lTotal + lTemp
        End If
    Next i
    
    tbTotal.Value = lTotal
End Sub

Private Sub lbValues_KeyDown(ByVal KeyCode As MSForms.ReturnInteger, ByVal Shift As Integer)
    If lbValues.ListCount < 1 Then Exit Sub
    
    Select Case KeyCode
        Case vbKeyDelete
            If lbValues.ListIndex < 0 Then Exit Sub
            
            lbValues.RemoveItem lbValues.ListIndex
    End Select
End Sub

Private Sub UserForm_Initialize()
    lbFrom.Clear
    lbFrom.ColumnCount = 2
    lbFrom.ColumnWidths = "20;90"
    
    lbValues.Clear
    lbValues.ColumnCount = 2
    lbValues.ColumnWidths = "48;154"
    
    cbAmount.AddItem "Count"
    cbAmount.AddItem "Sum"
    cbAmount.Value = "Count"
    
    Dim amap As AcadMap
    Dim tbl As ODTable
    Dim tbls As ODTables
    
    Set amap = ThisDrawing.Application.GetInterfaceObject("AutoCADMap.Application")
    
    Set tbls = amap.Projects(ThisDrawing).ODTables
    If tbls.count > 0 Then
        cbFromList.Clear
        For Each tbl In tbls
            cbFromList.AddItem tbl.Name
        Next
    End If
End Sub

Attribute VB_Name = "OpenDrawing"
Attribute VB_Base = "0{3300C922-89AA-4778-BD3B-16B819763122}{6AC17B12-E229-4B4D-A2A8-A1B77DC803AA}"
Attribute VB_GlobalNameSpace = False
Attribute VB_Creatable = False
Attribute VB_PredeclaredId = True
Attribute VB_Exposed = False
Attribute VB_TemplateDerived = False
Attribute VB_Customizable = False
Private Sub cbGetInfo_Click()
    tbPath.Value = ""
    tbFolder.Value = ""
    tbDrawingName.Value = ""
    tbOComputer.Value = ""
    tbOName.Value = ""
    
    Dim vLine As Variant
    Dim strPath, strFolder, strDWG, strDWL As String
    Dim strAll, strNumber, strTemp As String
    Dim strUser As String
    
    strUser = Environ("USERNAME")
    tbNumber.Value = UCase(tbNumber.Value)
    strNumber = tbNumber.Value
    'strNumber = Replace(tbNumber.Value, "L", "")
    'strNumber = Replace(strNumber, "MAS", "")
    
    vLine = Split(strNumber, "20")
    Select Case vLine(0)
        Case ""
            strPath = "C:\Users\" & strUser & "\Dropbox\UNITED COMMUNICATIONS JOB INFORMATION\1-JOBS\"
            vLine = Split(strNumber, "-")
            
            Select Case vLine(0)
                Case "2019"
                    strPath = strPath & "1-2019 JOBS\"
                Case "2020"
                    strPath = strPath & "2-2020 JOBS\"
                Case "2021"
                    strPath = strPath & "3-2021 JOBS\"
                Case "2022"
                    strPath = strPath & "4-2022 JOBS\"
                Case "2023"
                    strPath = strPath & "5-2023 JOBS\"
            End Select
        Case "L"
            strPath = "C:\Users\" & strUser & "\Dropbox\LORETTO TEL & KCW SHARED FOLDER\01 - JOBS\"
            strNumber = Replace(strNumber, "L", "")
            vLine = Split(strNumber, "-")
            
            Select Case vLine(0)
                Case "2019"
                    strPath = strPath & "2019\"
                Case "2020"
                    strPath = strPath & "2020\"
                Case "2021"
                    strPath = strPath & "2021\"
                Case "2022"
                    strPath = strPath & "2022\"
                Case "2023"
                    strPath = strPath & "2023\"
            End Select
        Case "MAS"
            strPath = "C:\Users\" & strUser & "\Dropbox\MASTEC JOB INFORMATION\1 - JOBS\"
            strNumber = Replace(strNumber, "MAS", "")
            vLine = Split(strNumber, "-")
            
            Select Case vLine(0)
                Case "2019"
                    strPath = strPath & "2019\"
                Case "2020"
                    strPath = strPath & "2020\"
                Case "2021"
                    strPath = strPath & "1-2021 JOBS\"
                Case "2022"
                    strPath = strPath & "2-2022 JOBS\"
                Case "2023"
                    strPath = strPath & "3-2023 JOBS\"
            End Select
        
    End Select
    
    tbPath.Value = strPath
    
    'strAll = strPath & strFolder
    strFolder = GetFolderName(CStr(strPath), CStr(strNumber))
    'strFolder = GetFolderName(CStr(strPath), CStr(tbNumber.Value))
    If strFolder = "<not found>" Then
        tbFolder.Value = strFolder
        Exit Sub
    End If
    
    strFolder = strFolder & "\"
    tbFolder.Value = strFolder
    strDWG = GetDrawingName(CStr(strPath), CStr(strFolder), CStr(strNumber))
    
    'tbFolder.Value = strFolder
    tbDrawingName.Value = strDWG
    
    Call CheckIfOpen
    
    If tbDrawingName.Value = "<not found>" Then
        cbOpen.Enabled = False
        cbReadOnly.Enabled = False
    Else
        cbOpen.Enabled = True
        cbReadOnly.Enabled = True
        
        cbOpen.SetFocus
    End If
    
    If Not tbOComputer.Value = "<none>" Then
        cbOpen.Enabled = False
        cbReadOnly.SetFocus
    End If
End Sub

Private Sub cbOpen_Click()
    If tbDrawingName.Value = "<not found>" Then Exit Sub
    
    Dim strFileName As String
    
    strFileName = tbPath.Value & tbFolder.Value & tbDrawingName.Value
    
    ThisDrawing.Application.Documents.Open strFileName, True
    
    Me.Hide
End Sub

Private Sub cbReadOnly_Click()
    If tbDrawingName.Value = "<not found>" Then Exit Sub
    
    Dim strFileName As String
    
    strFileName = tbPath.Value & tbFolder.Value & tbDrawingName.Value
    
    ThisDrawing.Application.Documents.Open strFileName, True
    
    Me.Hide
End Sub

Private Sub UserForm_Initialize()
    tbNumber.SetFocus
End Sub

Private Function GetFolderName(strFolder As String, strNumber As String)
    Dim vDirectory As Variant
    Dim strFile As String
    Dim strResult As String
    Dim vTemp As Variant
    
    strResult = "<not found>"
    vDirectory = Dir(strFolder, vbDirectory)
    
    'MsgBox vDirectory
    
    Do While vDirectory <> ""
        If InStr(vDirectory, strNumber) > 0 Then
            strResult = CStr(vDirectory)
            GoTo Exit_Function
        End If
        vDirectory = Dir$
    Loop
Exit_Function:
    GetFolderName = strResult
End Function

Private Function GetDrawingName(strPath As String, strFolder As String, strNumber As String)
    Dim vDirectory As Variant
    Dim strTemp, strFile As String
    Dim strResult As String
    Dim vTemp As Variant
    
    strTemp = strPath & strFolder
    strResult = "<not found>"
    vDirectory = Dir(strTemp, vbDirectory)
    
    'MsgBox vDirectory
    
    Do While vDirectory <> ""
        If InStr(vDirectory, strNumber) > 0 Then
            If Right(vDirectory, 4) = ".dwg" Then
                strResult = CStr(vDirectory)
                GoTo Exit_Function
            End If
        End If
        vDirectory = Dir$
    Loop
    
    strFolder = strFolder & tbNumber.Value & " CONSTRUCTION DRAWINGS\"
    tbFolder.Value = strFolder
    strTemp = strPath & strFolder
    vDirectory = Dir(strTemp, vbDirectory)
    
    'MsgBox vDirectory
    
    Do While vDirectory <> ""
        If InStr(vDirectory, strNumber) > 0 Then
            If Right(vDirectory, 4) = ".dwg" Then
                strResult = CStr(vDirectory)
                GoTo Exit_Function
            End If
        End If
        vDirectory = Dir$
    Loop
    
    
Exit_Function:
    GetDrawingName = strResult
End Function

Private Sub CheckIfOpen()
    Dim strFolder, strFile, strDWL As String
    Dim strLine As String
    Dim vTemp As Variant
    
    strFolder = tbPath.Value & tbFolder.Value
    strDWL = Replace(tbDrawingName.Value, ".dwg", ".dwl")
    
    strFile = Dir$(strFolder, vbHidden)
    
    Do While strFile <> ""
        If strFile = strDWL Then GoTo Found_File
        
        strFile = Dir$
    Loop
    
    tbOComputer.Value = "<none>"
    Exit Sub
Found_File:
    
    strDWL = strFolder & strFile
    
    Open strDWL For Input As #1
    
    Line Input #1, strLine
    vTemp = Split(strLine, vbLf)
    vTemp(0) = Replace(vTemp(0), vbCr, "")
    
    tbOComputer.Value = vTemp(0)
    Close #1
    
    Select Case LCase(vTemp(0))
        Case "integrity"
            tbOName.Value = "Dylan Spears"
        Case "integrity.tab"
            tbOName.Value = "Jeremy Pafford"
        Case "integrity.1"
            tbOName.Value = "Ronn Elliott"
        Case "integrity.2"
            tbOName.Value = "Rich Taylor"
        Case "integrity.3"
            tbOName.Value = "Jason Pafford"
        Case "integrity.4"
            tbOName.Value = "Byron Auer"
        Case "integrity.5"
            tbOName.Value = "Adam Kemper"
        Case "integrity.6"
            tbOName.Value = "Jon Wilburn"
        Case "integrity.7"
            tbOName.Value = "Tara Taylor"
        Case "integrity.8"
            tbOName.Value = "Franklin Angulo"
        Case "integrity9"
            tbOName.Value = "Wade Hampton"
        Case "integrity10"
            tbOName.Value = "Sam Jackson"
        Case "integrity11"
            tbOName.Value = "A Ghost?"
        Case "integrity12"
            tbOName.Value = "Daniel Campbell"
        Case "integrity13"
            tbOName.Value = "Nick Lockyear"
        Case "integrity14"
            tbOName.Value = "A Ghost?"
        Case "integrity15"
            tbOName.Value = "Jay Penny"
        Case "integrity16"
            tbOName.Value = "Drew Curtis"
        Case Else
            tbOName.Value = "Unknown"
    End Select
End Sub

Attribute VB_Name = "OpenProject"
Attribute VB_Base = "0{F1DDA293-CAE4-40DA-9503-438EE0E668E5}{74813668-4832-4976-853A-A5EC5BBE49F9}"
Attribute VB_GlobalNameSpace = False
Attribute VB_Creatable = False
Attribute VB_PredeclaredId = True
Attribute VB_Exposed = False
Attribute VB_TemplateDerived = False
Attribute VB_Customizable = False
Private Sub cbAllDWGs_Click()
    If cbAllDWGs.Value = False Then cbAllFiles.Value = False
End Sub

Private Sub cbAllFiles_Click()
    If cbAllFiles.Value = True Then cbAllDWGs.Value = True
End Sub

Private Sub cbCleanupTemp_Click()
    If InStr(tbCopyFolder.Value, "Dropbox") > 0 Then Exit Sub
    
    tbPath.Value = ""
    tbFolder.Value = ""
    lbDrawings.Clear
    lbSubFolders.Clear
    tbNumber.Value = ""
    cbAllDWGs.Value = True
    cbDeleteFile.Enabled = True
    
    Dim vLine As Variant
    Dim strPath, strFolder, strDWG, strDWL As String
    Dim strAll, strNumber, strTemp As String
    Dim strUser As String
    Dim iIndex As Integer
    
    strPath = "C:\Integrity\"
    strFolder = "Temp\"
    
    tbPath.Value = strPath
    tbFolder.Value = strFolder
    
    Call GetSubFolders
    
    If lbSubFolders.ListCount > 0 Then
        iIndex = 1
        While iIndex < lbSubFolders.ListCount
            Call GetSubSubFolders(lbSubFolders.List(iIndex))
            
            iIndex = iIndex + 1
        Wend
        
        Call SortSubFolders
    End If
    
    Call GetDrawingNames(CStr(strPath), CStr(strFolder), "")
    If Not lbSubFolders.ListCount < 0 Then
        For i = 0 To lbSubFolders.ListCount - 1
            Call GetDrawingNames(CStr(strPath), CStr(strFolder), lbSubFolders.List(i) & "\")
        Next i
    End If
    
    If lbDrawings.ListCount > -1 Then
        For i = 0 To lbDrawings.ListCount - 1
            strTemp = strPath & strFolder & lbSubFolders.List(lbSubFolders.ListIndex) & "\"
            strDWG = CheckIfOpen(CStr(strTemp), CStr(lbDrawings.List(i, 1)))
            
            lbDrawings.List(i, 2) = strDWG
        Next i
    End If
    
End Sub

Private Sub cbDeleteFile_Click()
    If lbDrawings.ListIndex < 0 Then Exit Sub
    
    Dim iIndex As Integer
    
    iIndex = lbDrawings.ListIndex
    If Not lbDrawings.List(iIndex, 2) = "" Then
        If iIndex = lbDrawings.ListCount - 1 Then
            If Not iIndex = 0 Then
                iIndex = iIndex - 1
                lbDrawings.Selected(iIndex) = True
                lbDrawings.ListIndex = iIndex
            End If
        Else
            iIndex = iIndex + 1
            lbDrawings.Selected(iIndex) = True
            lbDrawings.ListIndex = iIndex
        End If
        
        Exit Sub
    End If
    
    Dim strFile As String
    Dim result As Integer
    
    strFile = tbPath.Value & tbFolder.Value
    If Not lbDrawings.List(iIndex, 0) = "" Then strFile = strFile & lbDrawings.List(iIndex, 0) & "\"
    strFile = strFile & lbDrawings.List(iIndex, 1)
    
    'MsgBox strFile
    
    result = MsgBox("Are you sure you want to delete" & vbCr & strFile & "?", vbYesNo, "Delete File!")
    If result = vbYes Then
        Kill strFile
        lbDrawings.RemoveItem iIndex
    End If
    
Exit_Sub:
    
End Sub

Private Sub cbGetInfo_Click()
    tbPath.Value = ""
    tbFolder.Value = ""
    lbDrawings.Clear
    lbSubFolders.Clear
    cbDeleteFile.Enabled = False
    'cbAllFiles.Value = False
    
    If tbNumber.Value = "" Then Exit Sub
    
    Dim vLine As Variant
    Dim strPath, strFolder, strDWG, strDWL As String
    Dim strAll, strNumber, strTemp As String
    Dim strUser As String
    
    strUser = Environ("USERNAME")
    tbNumber.Value = UCase(tbNumber.Value)
    strNumber = tbNumber.Value
    
    vLine = Split(strNumber, "20")
    Select Case vLine(0)
        Case ""
            strPath = "C:\Users\" & strUser & "\Dropbox\UNITED COMMUNICATIONS JOB INFORMATION\1-JOBS\"
            vLine = Split(strNumber, "-")
            
            Select Case vLine(0)
                Case "2019"
                    strPath = strPath & "1-2019 JOBS\"
                Case "2020"
                    strPath = strPath & "2-2020 JOBS\"
                Case "2021"
                    strPath = strPath & "3-2021 JOBS\"
                Case "2022"
                    strPath = strPath & "4-2022 JOBS\"
                Case "2023"
                    strPath = strPath & "5-2023 JOBS\"
            End Select
        Case "L"
            strPath = "C:\Users\" & strUser & "\Dropbox\LORETTO TEL & KCW SHARED FOLDER\01 - JOBS\"
            strNumber = Replace(strNumber, "L", "")
            vLine = Split(strNumber, "-")
            
            Select Case vLine(0)
                Case "2019"
                    strPath = strPath & "2019\"
                Case "2020"
                    strPath = strPath & "2020\"
                Case "2021"
                    strPath = strPath & "2021\"
                Case "2022"
                    strPath = strPath & "2022\"
                Case "2023"
                    strPath = strPath & "2023\"
            End Select
        Case "MAS"
            strPath = "C:\Users\" & strUser & "\Dropbox\MASTEC JOB INFORMATION\1 - JOBS\"
            strNumber = Replace(strNumber, "MAS", "")
            vLine = Split(strNumber, "-")
            
            Select Case vLine(0)
                Case "2019"
                    strPath = strPath & "2019\"
                Case "2020"
                    strPath = strPath & "2020\"
                Case "2021"
                    strPath = strPath & "1-2021 JOBS\"
                Case "2022"
                    strPath = strPath & "2-2022 JOBS\"
                Case "2023"
                    strPath = strPath & "3-2023 JOBS\"
            End Select
        
    End Select
    
    tbPath.Value = strPath
    
    strFolder = GetFolderName(CStr(strPath), CStr(strNumber))
    'strFolder = GetFolderName(CStr(strPath), CStr(tbNumber.Value))
    If strFolder = "<not found>" Then
        tbFolder.Value = strFolder
        Exit Sub
    End If
    
    strFolder = strFolder & "\"
    tbFolder.Value = strFolder
    'strDWG = GetDrawingName(CStr(strPath), CStr(strFolder), CStr(strNumber))
    Call GetSubFolders
    
    If lbSubFolders.ListCount > 1 Then
        iIndex = 1
        While iIndex < lbSubFolders.ListCount
            Call GetSubSubFolders(lbSubFolders.List(iIndex))
            
            iIndex = iIndex + 1
        Wend
        
        Call SortSubFolders
    End If
    
    Call GetDrawingNames(CStr(strPath), CStr(strFolder), "")
    
    If cbAllFiles.Value = False Then
        If lbSubFolders.ListCount > 1 Then
            For i = 1 To lbSubFolders.ListCount - 1
                Call GetDrawingNames(CStr(strPath), CStr(strFolder), lbSubFolders.List(i) & "\")
            Next i
        End If
    End If
    
    If lbDrawings.ListCount > -1 Then
        For i = 0 To lbDrawings.ListCount - 1
            If InStr(lbDrawings.List(i, 1), ".dwg") > 0 Then
                strTemp = strPath & strFolder & lbDrawings.List(i, 0) & "\"
                strDWG = CheckIfOpen(CStr(strTemp), CStr(lbDrawings.List(i, 1)))
                
                lbDrawings.List(i, 2) = strDWG
            End If
        Next i
        
        vLine = Split(tbFolder.Value, "\")
        strTemp = LCase(vLine(UBound(vLine) - 1)) & ".dwg"
        
        For i = 0 To lbDrawings.ListCount - 1
            If LCase(lbDrawings.List(i, 1)) = strTemp Then
                lbDrawings.Selected(i) = True
                If lbDrawings.List(i, 0) = "" Then GoTo Exit_Sub
                If InStr(lbDrawings.List(i, 0), "CONSTRUCTION DRAWINGS") > 0 Then GoTo Exit_Sub
            End If
        Next i
    End If
Exit_Sub:
    
End Sub

Private Sub cbCopyDWG_Click()
    Dim iIndex As Integer
    
    iIndex = lbDrawings.ListIndex
    If iIndex < 0 Then Exit Sub
    
    Dim fso As Object
    Dim strFileFrom, strFileTo As String
    
    strFileFrom = tbPath.Value & tbFolder.Value
    If Not lbDrawings.List(iIndex, 0) = "" Then
        strFileFrom = strFileFrom & lbDrawings.List(iIndex, 0) & "\"
    End If
    strFileFrom = strFileFrom & lbDrawings.List(iIndex, 1)
    strFileTo = tbCopyFolder & lbDrawings.List(iIndex, 1)
    
    'MsgBox "Copying from:" & vbCr & vbCr & strFileFrom & vbCr & vbCr & "Copying to:" & vbCr & vbCr & strFileTo
    Set fso = VBA.CreateObject("Scripting.FileSystemObject")
    
    Call fso.CopyFile(strFileFrom, strFileTo)
    
    If Right(strFileTo, 4) = ".dwg" Then
        ThisDrawing.Application.Documents.Open strFileTo
    Else
        CreateObject("Shell.Application").Open CVar(strFileTo)
    End If
End Sub

Private Sub cbOpen_Click()
    If lbDrawings.ListIndex < 0 Then Exit Sub
    If Not lbDrawings.List(lbDrawings.ListIndex, 2) = "" Then Exit Sub
    
    Dim strFileName As String
    
    strFileName = tbPath.Value & tbFolder.Value & lbDrawings.List(lbDrawings.ListIndex, 0)
    If Not Right(strFileName, 1) = "\" Then strFileName = strFileName & "\"
    strFileName = strFileName & lbDrawings.List(lbDrawings.ListIndex, 1)
    
    If Right(strFileName, 4) = ".dwg" Then
        ThisDrawing.Application.Documents.Open strFileName
    Else
        CreateObject("Shell.Application").Open CVar(strFileName)
    End If
End Sub

Private Sub cbReadOnly_Click()
    If lbDrawings.ListIndex < 0 Then Exit Sub
    
    Dim strFileName As String
    
    strFileName = tbPath.Value & tbFolder.Value & lbDrawings.List(lbDrawings.ListIndex, 0)
    If Not Right(strFileName, 1) = "\" Then strFileName = strFileName & "\"
    strFileName = strFileName & lbDrawings.List(lbDrawings.ListIndex, 1)
    
    ThisDrawing.Application.Documents.Open strFileName, True
End Sub

Private Sub lbDrawings_Click()
    cbReadOnly.Enabled = True
    cbOpen.Enabled = True
    cbCopyDWG.Enabled = True
    
    If Not lbDrawings.List(lbDrawings.ListIndex, 2) = "" Then cbOpen.Enabled = False
End Sub

Private Sub lbDrawings_DblClick(ByVal Cancel As MSForms.ReturnBoolean)
    Dim strFileName As String
    
    strFileName = tbPath.Value & tbFolder.Value & lbDrawings.List(lbDrawings.ListIndex, 0)
    If Not Right(strFileName, 1) = "\" Then strFileName = strFileName & "\"
    strFileName = strFileName & lbDrawings.List(lbDrawings.ListIndex, 1)
    
    If Right(strFileName, 4) = ".dwg" Then
        Select Case lbDrawings.List(lbDrawings.ListIndex, 2)
            Case ""
                ThisDrawing.Application.Documents.Open strFileName
            Case Else
                'MsgBox strFileName
                ThisDrawing.Application.Documents.Open strFileName, True
                MsgBox lbDrawings.List(lbDrawings.ListIndex, 1) & vbCr & "was opened in ReadOnly."
        End Select
        'ThisDrawing.Application.Documents.Open strFileName
    Else
        CreateObject("Shell.Application").Open CVar(strFileName)
    End If
End Sub

Private Sub lbDrawings_KeyDown(ByVal KeyCode As MSForms.ReturnInteger, ByVal Shift As Integer)
    Dim strFileName As String
    
    strFileName = tbPath.Value & tbFolder.Value & lbDrawings.List(lbDrawings.ListIndex, 0)
    If Not Right(strFileName, 1) = "\" Then strFileName = strFileName & "\"
    strFileName = strFileName & lbDrawings.List(lbDrawings.ListIndex, 1)
    
    Select Case KeyCode
        Case vbKeyReturn
            If Right(strFileName, 4) = ".dwg" Then
                Select Case lbDrawings.List(lbDrawings.ListIndex, 2)
                    Case ""
                        ThisDrawing.Application.Documents.Open strFileName
                    Case Else
                        ThisDrawing.Application.Documents.Open strFileName, True
                        MsgBox lbDrawings.List(lbDrawings.ListIndex, 1) & vbCr & "was opened in ReadOnly."
                End Select
            Else
                CreateObject("Shell.Application").Open CVar(strFileName)
            End If
    End Select
End Sub

Private Sub lbSubFolders_Click()
    Dim strPath, strFolder As String
    Dim iIndex As Integer
    
    lbDrawings.Clear
    iIndex = lbSubFolders.ListIndex
    'For i = 0 To lbSubFolders.ListCount - 1
        'MsgBox lbSubFolders.List(i) & vbCr & lbSubFolders.Selected(i)
        'If lbSubFolders.Selected(i) = True Then
            'iIndex = i
            'GoTo Found_Selected
        'End If
    'Next i
    
'Found_Selected:
    'MsgBox iIndex
    If iIndex < 0 Then Exit Sub
    
    strPath = tbPath.Value
    strFolder = tbFolder.Value
    
    Call GetDrawingNames(CStr(strPath), CStr(strFolder), lbSubFolders.List(iIndex) & "\")
    
    If lbDrawings.ListCount > -1 Then
        For i = 0 To lbDrawings.ListCount - 1
            If InStr(lbDrawings.List(i, 1), ".dwg") > 0 Then
                strTemp = strPath & strFolder & lbDrawings.List(i, 0) & "\"
                strDWG = CheckIfOpen(CStr(strTemp), CStr(lbDrawings.List(i, 1)))
                
                lbDrawings.List(i, 2) = strDWG
            End If
        Next i
        
        vLine = Split(tbFolder.Value, "\")
        strTemp = LCase(vLine(UBound(vLine) - 1)) & ".dwg"
        
        For i = 0 To lbDrawings.ListCount - 1
            If LCase(lbDrawings.List(i, 1)) = strTemp Then
                lbDrawings.Selected(i) = True
                GoTo Exit_Sub
            End If
        Next i
    End If
Exit_Sub:
    
End Sub

Private Sub lbSubFolders_DblClick(ByVal Cancel As MSForms.ReturnBoolean)
    Dim strPath, strFolder As String
    Dim iIndex As Integer
    
    lbDrawings.Clear
    iIndex = lbSubFolders.ListIndex
    'For i = 0 To lbSubFolders.ListCount - 1
        'MsgBox lbSubFolders.List(i) & vbCr & lbSubFolders.Selected(i)
        'If lbSubFolders.Selected(i) = True Then
            'iIndex = i
            'GoTo Found_Selected
        'End If
    'Next i
    
'Found_Selected:
    'MsgBox iIndex
    If iIndex < 0 Then Exit Sub
    
    strPath = tbPath.Value
    strFolder = tbFolder.Value
    
    Call GetDrawingNames(CStr(strPath), CStr(strFolder), lbSubFolders.List(iIndex) & "\")
    
    If lbDrawings.ListCount > -1 Then
        For i = 0 To lbDrawings.ListCount - 1
            If InStr(lbDrawings.List(i, 1), ".dwg") > 0 Then
                strTemp = strPath & strFolder & lbDrawings.List(i, 0) & "\"
                strDWG = CheckIfOpen(CStr(strTemp), CStr(lbDrawings.List(i, 1)))
                
                lbDrawings.List(i, 2) = strDWG
            End If
        Next i
        
        vLine = Split(tbFolder.Value, "\")
        strTemp = LCase(vLine(UBound(vLine) - 1)) & ".dwg"
        
        For i = 0 To lbDrawings.ListCount - 1
            If LCase(lbDrawings.List(i, 1)) = strTemp Then
                lbDrawings.Selected(i) = True
                GoTo Exit_Sub
            End If
        Next i
    End If
Exit_Sub:
    
End Sub

Private Sub UserForm_Initialize()
    lbDrawings.ColumnCount = 3
    lbDrawings.ColumnWidths = "180;264;42"
    
    tbNumber.SetFocus
End Sub

Private Function GetFolderName(strFolder As String, strNumber As String)
    Dim vDirectory As Variant
    Dim strFile As String
    Dim strResult As String
    Dim vTemp As Variant
    
    strResult = "<not found>"
    vDirectory = Dir(strFolder, vbDirectory)
    
    'MsgBox vDirectory
    
    Do While vDirectory <> ""
        If InStr(vDirectory, strNumber) > 0 Then
            strResult = CStr(vDirectory)
            GoTo Exit_Function
        End If
        vDirectory = Dir$
    Loop
Exit_Function:
    GetFolderName = strResult
End Function

Private Sub GetDrawingNames(strPath As String, strFolder As String, strSub As String)
    Dim vDirectory As Variant
    Dim strTemp, strFile, strDWG As String
    Dim strResult As String
    Dim vTemp As Variant
    
    strTemp = strPath & strFolder & strSub
    If cbAllFiles.Value = False Then strTemp = strTemp & "*.dwg"
    
    strFile = Dir(strTemp, vbHidden)
    
    Do While strFile <> ""
        If cbAllDWGs.Value = False Then
            If InStr(strFile, tbNumber.Value) > 0 Then
                If strSub = "" Then
                    lbDrawings.AddItem strSub
                Else
                    lbDrawings.AddItem Left(strSub, Len(strSub) - 1)
                End If
                lbDrawings.List(lbDrawings.ListCount - 1, 1) = strFile
            End If
        Else
            'lbDrawings.AddItem Replace(strSub, "\", "")
            If strSub = "" Then
                lbDrawings.AddItem strSub
            Else
                lbDrawings.AddItem Left(strSub, Len(strSub) - 1)
            End If
            lbDrawings.List(lbDrawings.ListCount - 1, 1) = strFile
        End If
        
        strFile = Dir()
    Loop
End Sub

Private Sub GetSubFolders()
    Dim strFolder, strFile As String
    Dim strTemp As String
    
    lbSubFolders.Clear
    lbSubFolders.AddItem ""
    strFolder = tbPath.Value & tbFolder.Value
    
    strFile = Dir(strFolder, vbDirectory)
    
    Do While strFile <> ""
        strTemp = strFolder & strFile
        'MsgBox strFile & vbCr & GetAttr(strTemp)
        
        If GetAttr(strTemp) = 48 Or GetAttr(strTemp) = 16 Then
            If Not strFile = "." Then
                If Not strFile = ".." Then lbSubFolders.AddItem strFile
            End If
        End If
        
        strFile = Dir()
    Loop
End Sub

Private Sub GetSubSubFolders(strSub As String)
    Dim strFolder, strFile As String
    Dim strTemp As String
    Dim vCount As Variant
    
    If Left(strSub, 1) = "\" Then strSub = Right(strSub, Len(strSub) - 1)
    
    strFolder = tbPath.Value & tbFolder.Value & strSub & "\"
    vCount = Split(strFolder, "\")
    If UBound(vCount) > 10 Then Exit Sub
    
    strFile = Dir(strFolder, vbDirectory)
    
    Do While strFile <> ""
        strTemp = strFolder & strFile
        'MsgBox strTemp & vbCr & GetAttr(strTemp)
        'Exit Sub
        
        If Len(strFile) > 70 Then GoTo Next_strFile
        
        If GetAttr(strTemp) = 48 Or GetAttr(strTemp) = 16 Then
            If Not strFile = "." Then
                If Not strFile = ".." Then lbSubFolders.AddItem strSub & "\" & strFile
            End If
        End If
        
Next_strFile:
        strFile = Dir()
    Loop
End Sub

Private Sub SortSubFolders()
    Dim a, b As Integer
    Dim iCount As Integer
    Dim strAtt As String
    'Dim strAtt(0 To 2) As String
    
    iCount = lbSubFolders.ListCount - 1
    If iCount < 1 Then Exit Sub
    
    On Error Resume Next
    
    For a = iCount To 0 Step -1
        For b = 0 To a - 1
            If lbSubFolders.List(b, 0) > lbSubFolders.List(b + 1, 0) Then
                'If Not Err = 0 Then
                    'MsgBox "Error sorting list"
                    'lbSubFolders.Selected(b) = True
                    'lbSubFolders.ListIndex = b
                    'Exit Sub
                'End If
                
                strAtt = lbSubFolders.List(b + 1, 0)
                lbSubFolders.List(b + 1, 0) = lbSubFolders.List(b, 0)
                lbSubFolders.List(b, 0) = strAtt
            End If
        Next b
    Next a
End Sub

Private Function CheckIfOpen(strFolder As String, strNumber As String)
    If InStr(strNumber, ".dwg") = 0 Then Exit Function
    
    Dim strFile, strDWL As String
    Dim strLine As String
    Dim vTemp As Variant
    
    'strFolder = tbPath.Value & tbFolder.Value
    strDWL = Replace(strNumber, ".dwg", ".dwl")
    
    strFile = Dir$(strFolder, vbHidden)
    
    Do While strFile <> ""
        If strFile = strDWL Then GoTo Found_File
        
        strFile = Dir$()
    Loop
    
    CheckIfOpen = ""
    
    Exit Function
Found_File:
    
    strDWL = strFolder & strFile
    
    Open strDWL For Input As #1
    
    Line Input #1, strLine
    vTemp = Split(strLine, vbLf)
    vTemp(0) = Replace(vTemp(0), vbCr, "")
    
    Close #1
    
    Select Case LCase(vTemp(0))
        Case "integrity"
            strLine = "Dylan Spears"
        Case "integrity.tab"
            strLine = "Jeremy Pafford"
        Case "integrity.1"
            strLine = "Ronn Elliott"
        Case "integrity.2"
            strLine = "Rich Taylor"
        Case "integrity.3"
            strLine = "Jason Pafford"
        Case "integrity.4"
            strLine = "Byron Auer"
        Case "integrity.5"
            strLine = "Adam Kemper"
        Case "integrity.6"
            strLine = "Jon Wilburn"
        Case "integrity.7"
            strLine = "Tara Taylor"
        Case "integrity8"
            strLine = "Franklin Angulo"
        Case "integrity9"
            strLine = "Wade Hampton"
        Case "integrity10"
            strLine = "Sam Jackson"
        'Case "integrity11"
            'strLine = "A Ghost?"
        Case "integrity12"
            strLine = "Daniel Campbell"
        Case "integrity13"
            strLine = "Nick Lockyear"
        'Case "integrity14"
            'strLine = "A Ghost?"
        Case "integrity.15"
            strLine = "Jay Penny"
        Case "integrity16"
            strLine = "Drew Curtis"
        Case Else
            strLine = LCase(vTemp(0)) & " ?"
    End Select
    
    CheckIfOpen = strLine
End Function

Attribute VB_Name = "PalmettoPoleConversion"
Attribute VB_Base = "0{C3FD4AC8-C239-4DA9-8091-DA5EB3C91704}{A78D7418-1F56-46BA-88D1-D1F5950A3C50}"
Attribute VB_GlobalNameSpace = False
Attribute VB_Creatable = False
Attribute VB_PredeclaredId = True
Attribute VB_Exposed = False
Attribute VB_TemplateDerived = False
Attribute VB_Customizable = False
Private Sub cbConvertWindow_Click()
    Dim vPnt1, vPnt2 As Variant
    Dim objSS As AcadSelectionSet
    Dim filterType, filterValue As Variant
    Dim grpCode(0) As Integer
    Dim grpValue(0) As Variant
    Dim objEntity As AcadEntity
    Dim objMText As AcadMText
    
    'Dim strLine, strTemp As String
    'Dim strAttach As String
    'Dim vLine, vAttach As Variant
    
    On Error Resume Next
    
    Me.Hide
    
    'lbAttachments.Clear
    
    vPnt1 = ThisDrawing.Utility.GetPoint(, "Get BL Corner: ")
    vPnt2 = ThisDrawing.Utility.GetCorner(vPnt1, vbCr & "Get UR Corner: ")
    If Not Err = 0 Then GoTo Exit_Sub
    
    grpCode(0) = 0
    grpValue(0) = "MTEXT"
    filterType = grpCode
    filterValue = grpValue
    
    Set objSS = ThisDrawing.SelectionSets.Add("objSS")
    If Not Err = 0 Then Set objSS = ThisDrawing.SelectionSets.Item("objSS")
    
    objSS.Select acSelectionSetWindow, vPnt1, vPnt2, filterType, filterValue
    
    For Each objMText In objSS
        Call PlaceBlock(objMText)
    Next objMText
    
Exit_Sub:
    Me.show
End Sub

Private Sub cbCreatePoint_Click()
    Dim objEntity As AcadEntity
    Dim objMText As AcadMText
    Dim vReturnPnt As Variant
    
    Me.Hide
    
    On Error Resume Next
    
    ThisDrawing.Utility.GetEntity objEntity, vReturnPnt
    If TypeOf objEntity Is AcadMText Then
        Set objMText = objEntity
    Else
        MsgBox "Not a valid object."
        Me.show
        Exit Sub
    End If
    
    Call PlaceBlock(objMText)
    
    Me.show
End Sub

Private Sub cbGetAttachments_Click()
    Dim vPnt1, vPnt2 As Variant
    Dim objSS As AcadSelectionSet
    Dim filterType, filterValue As Variant
    Dim grpCode(0) As Integer
    Dim grpValue(0) As Variant
    Dim objEntity As AcadEntity
    Dim objMText As AcadMText
    
    Dim strLine, strTemp As String
    Dim strAttach As String
    Dim vLine, vAttach As Variant
    
    On Error Resume Next
    
    Me.Hide
    
    lbAttachments.Clear
    
    vPnt1 = ThisDrawing.Utility.GetPoint(, "Get BL Corner: ")
    vPnt2 = ThisDrawing.Utility.GetCorner(vPnt1, vbCr & "Get UR Corner: ")
    If Not Err = 0 Then GoTo Exit_Sub
    
    grpCode(0) = 0
    grpValue(0) = "MTEXT"
    filterType = grpCode
    filterValue = grpValue
    
    Set objSS = ThisDrawing.SelectionSets.Add("objSS")
    If Not Err = 0 Then Set objSS = ThisDrawing.SelectionSets.Item("objSS")
    
    objSS.Select acSelectionSetWindow, vPnt1, vPnt2, filterType, filterValue
    
    For Each objMText In objSS
        strLine = UCase(objMText.TextString)
        vLine = Split(strLine, "ATTACHMENT HEIGHTS")
        If UBound(vLine) < 1 Then GoTo Next_ObjMText
        
        strAttach = vLine(1)
        
        strLine = Replace(strAttach, "{", "")
        strLine = Replace(strLine, "}", "")
        strLine = Replace(strLine, "\L", "")
        strLine = Replace(strLine, "\C7;", "")
        strLine = Replace(strLine, "\C6;", "")
        strLine = Replace(strLine, "\C1;", "")
        strLine = Replace(strLine, "\C0;", "")
        strLine = Replace(strLine, "\I;", "")
        
        vAttach = Split(strLine, "\P")
        
        For i = 0 To UBound(vAttach)
            vLine = Split(vAttach(i), "=")
            
            If lbAttachments.ListCount < 1 Then
                lbAttachments.AddItem vLine(0)
                lbAttachments.List(lbAttachments.ListCount - 1, 1) = ""
            Else
                For j = 0 To lbAttachments.ListCount - 1
                    If lbAttachments.List(j, 0) = vLine(0) Then GoTo Next_Attachment
                Next j
                
                lbAttachments.AddItem vLine(0)
                lbAttachments.List(lbAttachments.ListCount - 1, 1) = ""
            End If
Next_Attachment:
        Next i
        
Next_ObjMText:
    Next objMText
    
Exit_Sub:
    objSS.Clear
    objSS.Delete
    
    Me.show
End Sub

Private Sub cbToAttribute_Click()
    If lbAttachments.ListIndex < 0 Then Exit Sub
    
    lbAttachments.List(lbAttachments.ListIndex, 1) = cbAttribute.Value
End Sub

Private Sub UserForm_Initialize()
    lbAttachments.ColumnCount = 2
    lbAttachments.ColumnWidths = "216;108"
    
    cbAttribute.AddItem ""
    cbAttribute.AddItem "9 NEUTRAL"
    cbAttribute.AddItem "10 TRANSFORMER"
    cbAttribute.AddItem "11 LOW POWER"
    cbAttribute.AddItem "12 ANTENNA"
    cbAttribute.AddItem "13 ST LT CIRCUIT"
    cbAttribute.AddItem "14 ST LT"
    cbAttribute.AddItem "15 NEW"
    cbAttribute.AddItem "15 OHG"
    cbAttribute.AddItem "15 FUTURE"
    cbAttribute.AddItem " COMM"
    cbAttribute.AddItem " COMM DROP"
    cbAttribute.AddItem " COMM C-WIRE"
    cbAttribute.AddItem " COMM OHG"
    cbAttribute.AddItem " COMM SS"
End Sub

Private Sub PlaceBlock(objMText As AcadMText)
    Dim vNE, vAttList As Variant
    Dim objBlock As AcadBlockReference
    Dim vLine, vItem, vTemp As Variant
    Dim strLine, strText As String
    
    Dim dCoords(2) As Double
    Dim strAtt(27) As String
    Dim strCompany, strAttach As String
    Dim iCOMM As Integer
    
    iCOMM = 16
    
    For i = 0 To 27
        strAtt(i) = ""
    Next i
    
    On Error Resume Next
    
    strLine = UCase(objMText.TextString)
    If InStr(strLine, "ATTACHMENT HEIGHTS") < 1 Then Exit Sub
                
    strLine = Replace(strLine, "{", "")
    strLine = Replace(strLine, "}", "")
    strLine = Replace(strLine, "\L", "")
    strLine = Replace(strLine, "\C7;", "")
    strLine = Replace(strLine, "\C6;", "")
    strLine = Replace(strLine, "\C1;", "")
    strLine = Replace(strLine, "\C0;", "")
    strLine = Replace(strLine, "\I;", "")
    
    vLine = Split(strLine, "\P")
    
    strAtt(0) = vLine(0)
    strAtt(2) = "MTE"
    
    vItem = Split(vLine(1), ":")
    If UBound(vItem) > 0 Then
        strAtt(3) = "FID: " & vItem(1)
    Else
        strAtt(3) = "NA"
    End If
    
    vItem = Split(vLine(2), ":")
    vItem(1) = Replace(vItem(1), " ", "")
    vItem(1) = Replace(vItem(1), vbTab, "")
    dCoords(0) = CDbl(vItem(1))
    dCoords(1) = CDbl(vLine(3))
    strAtt(7) = vItem(1) & "," & vLine(3)
    
    vNE = LLtoTN83F(CDbl(dCoords(0)), CDbl(dCoords(1)))
    dCoords(0) = CDbl(vNE(1))
    dCoords(1) = CDbl(vNE(0))
    dCoords(2) = 0#
    'strText = vNE(1) & "," & vNE(0) & vbCr & strNumber & vbCr & "FID: " & strFID
    'strText = strText & vbCr & vItem(1) & "," & vLine(3)
    
    ''MsgBox strAtt(0) & vbCr & strAtt(3) & vbCr & strAtt(7)
    
    If UBound(vLine) > 4 Then
        For i = 5 To UBound(vLine)
            vItem = Split(vLine(i), "=")
            strCompany = vItem(0)
            'vTemp = Split(vItem(0), " ")
            'strCompany = vTemp(0)
            
            vItem(1) = Replace(vItem(1), "'", "-")
            vItem(1) = Replace(vItem(1), """", "")
            vTemp = Split(vItem(1), " MOVE TO ")
            
            If UBound(vTemp) = 0 Then
                strAttach = vTemp(0)
            Else
                strAttach = "(" & vTemp(0) & ")" & vTemp(1)
            End If
            
            If lbAttachments.ListCount > 0 Then
                For j = 0 To lbAttachments.ListCount - 1
                    If lbAttachments.List(j, 0) = strCompany Then
                        Select Case lbAttachments.List(j, 1)
                            Case ""
                                If iCOMM > 16 Then
                                    For k = 16 To 23
                                        If strAtt(k) = "" Then GoTo Not_Found
                                        vTemp = Split(strAtt(k), "=")
                                        If vTemp(0) = strCompany Then
                                            strAtt(k) = strAtt(k) & " " & strAttach
                                            GoTo Next_J
                                        End If
                                    Next k
                                End If
Not_Found:
                                strAtt(iCOMM) = strCompany & "=" & strAttach
                                iCOMM = iCOMM + 1
                            Case "9 NEUTRAL"
                                If strAtt(9) = "" Then
                                    strAtt(9) = strAttach
                                Else
                                    strAtt(9) = strAtt(9) & " " & strAttach
                                End If
                            Case "10 TRANSFORMER"
                                If strAtt(10) = "" Then
                                    strAtt(10) = strAttach
                                Else
                                    strAtt(10) = strAtt(10) & " " & strAttach
                                End If
                            Case "11 LOW POWER"
                                If strAtt(11) = "" Then
                                    strAtt(11) = strAttach
                                Else
                                    strAtt(11) = strAtt(11) & " " & strAttach
                                End If
                            Case "12 ANTENNA"
                                If strAtt(12) = "" Then
                                    strAtt(12) = strAttach
                                Else
                                    strAtt(12) = strAtt(12) & " " & strAttach
                                End If
                            Case "13 ST LT CIRCUIT"
                                If strAtt(13) = "" Then
                                    strAtt(13) = strAttach
                                Else
                                    strAtt(13) = strAtt(13) & " " & strAttach
                                End If
                            Case "14 ST LT"
                                If strAtt(14) = "" Then
                                    strAtt(14) = strAttach
                                Else
                                    strAtt(14) = strAtt(14) & " " & strAttach
                                End If
                            Case "15 NEW"
                                If strAtt(15) = "" Then
                                    strAtt(15) = strAttach
                                Else
                                    strAtt(15) = strAtt(15) & " " & strAttach
                                End If
                            Case "15 OHG"
                                If strAtt(15) = "" Then
                                    strAtt(15) = strAttach & "o"
                                Else
                                    strAtt(15) = strAtt(15) & " " & strAttach & "o"
                                End If
                            Case "15 FUTURE"
                                If strAtt(15) = "" Then
                                    strAtt(15) = strAttach & "f"
                                Else
                                    strAtt(15) = strAtt(15) & " " & strAttach & "f"
                                End If
                            Case Else
                                vItem = Split(strCompany, " ")
                                strCompany = vItem(0)
                                
                                If iCOMM > 16 Then
                                    For k = 16 To 23
                                        If strAtt(k) = "" Then GoTo Not_Found2
                                        
                                        vItem = Split(strAtt(k), "=")
                                        
                                        If strCompany = vItem(0) Then
                                            strAtt(k) = strAtt(k) & " " & strAttach
                                            GoTo Add_Suffix
                                        End If
                                    Next k
                                End If
Not_Found2:
                                strAtt(iCOMM) = vItem(0) & "=" & strAttach
                                k = iCOMM
                                iCOMM = iCOMM + 1
Add_Suffix:
                                Select Case lbAttachments.List(j, 1)
                                    Case " COMM DROP"
                                        strAtt(k) = strAtt(k) & "d"
                                    Case " COMM C-WIRE"
                                        strAtt(k) = strAtt(k) & "c"
                                    Case " COMM OHG"
                                        strAtt(k) = strAtt(k) & "o"
                                    Case " COMM SS"
                                        strAtt(k) = strAtt(k) & "s"
                                End Select
                                
                        End Select
                    End If
Next_J:
                Next j
            Else
                'vItem = Split(vLine(i), "=")
                
                If iCOMM > 16 Then
                    For k = 16 To 23
                        If strAtt(k) = "" Then GoTo Not_Found3
                        vTemp = Split(strAtt(k), "=")
                        If vTemp(0) = strCompany Then
                            strAtt(k) = strAtt(k) & " " & strAttach
                            GoTo Next_J
                        End If
                    Next k
                End If
Not_Found3:
                strAtt(iCOMM) = strCompany & "=" & strAttach
                iCOMM = iCOMM + 1
            End If
        Next i
        
        'strText = dCoords(0) & "," & dCoords(1) & vbCr & strAtt(0)
        'For m = 1 To 27
            'If Not strAtt(m) = "" Then strText = strText & vbCr & strAtt(m)
        'Next m
        
        Set objBlock = ThisDrawing.ModelSpace.InsertBlock(dCoords, "sPole", 1#, 1#, 1#, 0#)
        objBlock.Layer = "Integrity Poles-Power"
        vAttList = objBlock.GetAttributes
        For i = 0 To 27
            vAttList(i).TextString = strAtt(i)
        Next i
        
        objBlock.Update
    End If
    'tbResult.Value = strText
End Sub

Private Function LLtoTN83F(dLat As Double, dLong As Double)
    Dim dDLat As Double
    Dim dEast, dDiffE, dEast0 As Double
    Dim dNorth, dDiffN, dNorth0 As Double
    Dim dU, dR, dCA, dK As Double
    Dim NE(2) As Double
    
    dDLat = dLat - 35.8340607459
    dU = dDLat * (110950.2019 + dDLat * (9.25072 + dDLat * (5.64572 + dDLat * 0.017374)))
    dR = 8842127.1422 - dU
    dCA = ((86 + dLong) * 0.585439726459) * 3.14159265359 / 180
    
    dDiffE = dR * Sin(dCA)
    dDiffN = dU + dDiffE * Tan(dCA / 2)
    
    dEast = (dDiffE + 600000) / 0.3048006096
    dNorth = (dDiffN + 166504.1691) / 0.3048006096
    
    dK = 0.999948401424 + (1.23188E-14 * dU * dU) + (4.54E-22 * dU * dU * dU)
    
    NE(0) = dNorth
    NE(1) = dEast
    NE(2) = dK
    
    LLtoTN83F = NE
End Function

Attribute VB_Name = "PlaceAerialCable"
Attribute VB_Base = "0{EE0C075A-3E17-4D28-945C-4C6D9A39C73F}{F2168225-3601-4048-9F04-FA76A3D02FAA}"
Attribute VB_GlobalNameSpace = False
Attribute VB_Creatable = False
Attribute VB_PredeclaredId = True
Attribute VB_Exposed = False
Attribute VB_TemplateDerived = False
Attribute VB_Customizable = False

Private Sub cbADSS_Click()
    If cbADSS.Value = True Then
        cbGuy.Value = False
        cbGuy.Enabled = False
        
        tbLashedCables.Value = ""
        tbLashedCables.Enabled = False
    Else
        cbGuy.Enabled = True
        If tbStrandCable.Value = "" Then
            cbGuy.Value = False
        Else
            cbGuy.Value = True
        End If
        
        tbLashedCables.Enabled = True
    End If
End Sub

Private Sub cbPlace_Click()
    Dim objEntity As AcadEntity
    Dim objPole As AcadBlockReference
    Dim objPrevious As AcadBlockReference
    Dim vAttItem, vBasePnt, vTemp As Variant
    Dim vAttPrevious As Variant
    Dim dPnt1(0 To 2), dPnt2(0 To 2), dPnt3(0 To 2) As Double
    Dim X(0 To 2), Y(0 To 2), Z(0 To 2) As Double
    Dim dInsertPnt(0 To 2), dLeaderPnt(0 To 3) As Double
    Dim dTextPnt(0 To 2) As Double
    Dim xDiff, yDiff, dDist As Double
    Dim dRotate, dScale, distance As Double
    'Dim dNewVertex(0 To 1) As Double
    Dim iCounter, iTemp As Integer
    Dim objLine As AcadLWPolyline
    Dim objSpan As AcadBlockReference
    Dim strLayer, strTextLayer, strLine, strTemp As String
    Dim strCables As String
    Dim strResult As String
    Dim dInfo(0 To 6) As Double
    Dim vInfo As Variant
    
    iCounter = 0
    dScale = CDbl(cbScale.Value) / 100
    
    Select Case cbStatus.Value
        Case "Proposed"
            strLayer = "Integrity Cable-Aerial"
            strTextLayer = "Integrity Cable-Aerial Text"
        Case "Existing"
            strLayer = "Integrity Existing"
            strTextLayer = "Integrity Existing"
        Case "Removed"
            strLayer = "Integrity Removed"
            strTextLayer = "Integrity Removed"
    End Select
    
    Me.Hide
    
  On Error Resume Next
    
    ThisDrawing.Utility.GetEntity objEntity, vBasePnt, "From Pole: "
    If Not Err = 0 Then GoTo Exit_While
    
    If TypeOf objEntity Is AcadBlockReference Then
        Set objPrevious = objEntity
    Else
        GoTo Exit_While
    End If
    
    X(1) = objPrevious.InsertionPoint(0)
    Y(1) = objPrevious.InsertionPoint(1)
    Z(1) = 0#
    
Add_Another:
    
    ThisDrawing.Utility.GetEntity objEntity, vBasePnt, "To Pole: "
    If Not Err = 0 Then GoTo Exit_While
    
    If TypeOf objEntity Is AcadBlockReference Then
        Set objPole = objEntity
    Else
        GoTo Exit_While
    End If
    
    X(0) = objPole.InsertionPoint(0)
    Y(0) = objPole.InsertionPoint(1)
    Z(0) = 0#
    
    If iCounter = 0 Then
        X(2) = X(0)
        Y(2) = Y(0)
        Z(2) = 0#
    End If
    
    dLeaderPnt(0) = X(1)
    dLeaderPnt(1) = Y(1)
    dLeaderPnt(2) = X(0)
    dLeaderPnt(3) = Y(0)
    
    If cbCable.Value = True Then
        Set objLine = ThisDrawing.ModelSpace.AddLightWeightPolyline(dLeaderPnt)
        objLine.Layer = strLayer
        objLine.Update
    End If
    
    dTextPnt(0) = (dLeaderPnt(0) + dLeaderPnt(2)) / 2
    dTextPnt(1) = (dLeaderPnt(1) + dLeaderPnt(3)) / 2
    dTextPnt(2) = 0#
      
    xDiff = dLeaderPnt(2) - dLeaderPnt(0)
    yDiff = dLeaderPnt(3) - dLeaderPnt(1)
        
    If (yDiff = 0) Then
        dRotate = 0
    ElseIf (xDiff = 0) Then
        dRotate = Pi / 2
    Else
        dRotate = Atn(yDiff / xDiff)
    End If
    distance = Int(Math.Sqr(xDiff ^ 2 + yDiff ^ 2)) + 1
    
    strCables = ""
    If Not tbStrandCable.Value = "" Then
        If cbADSS.Value = False Then
            strCables = "CO(" & tbStrandCable.Value & ")M"
        Else
            strCables = "ADSS(" & tbStrandCable.Value & ")"
        End If
    End If
    
    If Not tbLashedCables.Value = "" Then
        vTemp = Split(tbLashedCables.Value, " ")
        For i = 0 To UBound(vTemp)
            If strCables = "" Then
                strCables = "CO(" & vTemp(i) & ")E"
            Else
                strCables = strCables & " CO(" & vTemp(i) & ")E"
            End If
        Next i
    End If
    
    Set objSpan = ThisDrawing.ModelSpace.InsertBlock(dTextPnt, "cable_span", dScale, dScale, dScale, dRotate)
    objSpan.Layer = strTextLayer
    
    vAttItem = objSpan.GetAttributes
    
    vAttItem(0).TextString = ""
    vAttItem(1).TextString = strCables
    vAttItem(2).TextString = distance & "'"
    vAttItem(3).TextString = "INCOMPLETE"
    objSpan.Update
    
    If cbGuy.Value = True Then
        If iCounter = 0 Then
            strTemp = PlaceGuy((X(1)), (Y(1)), (X(0)), (Y(0)), (X(0)), (Y(0)))
            'strTemp = "+PM2A=1;;"
        Else
            strTemp = PlaceGuy((X(1)), (Y(1)), (X(0)), (Y(0)), (X(2)), (Y(2)))
            'strTemp = ""
        End If
            
        If Not strTemp = "" Then
            vAttPrevious = objPrevious.GetAttributes
            
            If vAttPrevious(27).TextString = "" Then
                vAttPrevious(27).TextString = strTemp
            Else
                vAttPrevious(27).TextString = vAttPrevious(27).TextString & ";;" & strTemp
            End If
        End If
    End If
    iCounter = iCounter + 1
    
    strResult = ThisDrawing.Utility.GetString(0, "Need a Closure [y/n]:(n)")
    If Err = 0 Then
        If LCase(strResult) = "y" Then
            dInfo(0) = distance
            dInfo(1) = dScale
            dInfo(2) = dRotate
            dInfo(3) = X(0)
            dInfo(4) = Y(0)
            dInfo(5) = X(1)
            dInfo(6) = Y(1)
            
            vInfo = dInfo
            Call PlaceClosure(vInfo)
            
            If strLine = "" Then
                strLine = "+CO(" & tbCoilCable.Value & ")E=100  LOOP;;+HACO(" & tbCoilCable.Value & ")=1  " & cbClosure.Value
            Else
                strLine = "+CO(" & tbCoilCable.Value & ")E=100  LOOP;;+HACO(" & tbCoilCable.Value & ")=1  " & cbClosure.Value & ";;" & strLine
            End If
        End If
    Else
        Err = 0
    End If
    
    If Not tbLashedCables.Value = "" Then
        vTemp = Split(tbLashedCables.Value, " ")
        For i = 0 To UBound(vTemp)
            If strLine = "" Then
                strLine = "+CO(" & vTemp(i) & ")E=" & distance & "'"
            Else
                strLine = "+CO(" & vTemp(i) & ")E=" & distance & ";;" & strLine
            End If
        Next i
    End If
    
    vAttList = objPole.GetAttributes
    
    If Not tbStrandCable.Value = "" Then
        If strLine = "" Then
            If cbADSS.Value = False Then
                strLine = "+CO(" & tbStrandCable.Value & ")6M-EHS=" & distance
            Else
                strLine = "+ADSS(" & tbStrandCable.Value & ")=" & distance
            End If
        Else
            If cbADSS.Value = False Then
                strLine = "+CO(" & tbStrandCable.Value & ")6M-EHS=" & distance & ";;" & strLine
            Else
                strLine = "+ADSS(" & tbStrandCable.Value & ")" & distance & ";;" & strLine
            End If
        End If
        
        If cbADSS.Value = False Then
            Select Case Left(UCase(vAttList(8).TextString), 1)
                Case "M", "m"
                    strLine = strLine & ";;+PM2A=1"
            End Select
        End If
    End If
    
    If vAttList(27).TextString = "" Then
        vAttList(27).TextString = strLine
    Else
        vAttList(27).TextString = vAttList(27).TextString & ";;" & strLine
    End If
    
    objPole.Update
    
    Err = 0
    strLine = ""
    iCounter = iCounter + 1
    
    X(2) = X(1)
    Y(2) = Y(1)
    Z(2) = Z(1)
    
    X(1) = X(0)
    Y(1) = Y(0)
    Z(1) = Z(0)
    
    Set objPrevious = objPole
    
    GoTo Add_Another    '<--------------------------------------------------------------Get Another Pole
    
Exit_While:
    If cbADSS.Value = True Then iCounter = 0
    
    If Not iCounter = 0 Then
        If cbGuy Then
            iTemp = PlaceGuy((X(1)), (Y(1)), (X(2)), (Y(2)), (X(2)), (Y(2)))
        
            strLine = ";;+PE1-3G=1;;+PF1-5A=1;;+PM11=1"
        End If
        
        vAttList = objPole.GetAttributes
        vAttList(27).TextString = vAttList(27).TextString & strLine
        objPole.Update
    End If
    
    Me.show
End Sub

Private Sub cbQuit_Click()
    Me.Hide
End Sub


Private Function PlaceGuy(X0 As Double, Y0 As Double, X1 As Double, Y1 As Double, X2 As Double, Y2 As Double)
    Dim startPnt(0 To 2), midPnt(0 To 2), endPnt(0 To 2) As Double
    Dim firstAng, endAng, defAng, rotateAng, ancAng, pull, tempPull As Double
    Dim dRotate, Pi, dTemp As Double
    Dim returnPoint As Variant
    Dim insertPnt(0 To 2) As Double
    Dim n, result, iDirection As Integer  'iDirection 0=L 1=R
    Dim str, str2, strTemp As String
    Dim layerObj As AcadLayer
    Dim strPull, strResult As String
    Dim vPoleCoords As Variant
    Dim entPole As AcadObject
    Dim obrGP As AcadBlockReference
    Dim attItem, basePnt As Variant
    Dim iCount As Integer
    
    Pi = 3.14159265359
    
'On Error GoTo Exit_Sub
    
    If (X1 - X0) = 0 Then
        If (Y1 - Y0) < 0 Then
            firstAng = 3 * Pi / 2
        Else
            firstAng = Pi / 2
        End If
    Else
        firstAng = Math.Atn((Y1 - Y0) / (X1 - X0))
        If (X1 - X0) < 0 Then
            firstAng = Pi + firstAng
        ElseIf (Y1 - Y0) < 0 Then
            firstAng = 2 * Pi + firstAng
        End If
    End If
    
    If (X2 - X0) = 0 Then
        If (Y2 - Y0) < 0 Then
            endAng = 3 * Pi / 2
        Else
            endAng = Pi / 2
        End If
    Else
        endAng = Math.Atn((Y2 - Y0) / (X2 - X0))
        If (X2 - X0) < 0 Then
            endAng = Pi + endAng
        ElseIf (Y2 - Y0) < 0 Then
            endAng = 2 * Pi + endAng
        End If
    End If
    
    Select Case Abs(endAng - firstAng)
        Case Is = 0
            rotateAng = firstAng + Pi
        Case Is < Pi
            rotateAng = (endAng + firstAng) / 2 + Pi
        Case Else
            rotateAng = (endAng + firstAng) / 2
    End Select
    
    If rotateAng > (2 * Pi) Then rotateAng = rotateAng - (2 * Pi)
    If rotateAng < 0 Then rotateAng = rotateAng + (2 * Pi)
    
    defAng = firstAng + Pi - endAng
    pull = Math.Round(Math.Abs(100 * Math.Sin(defAng / 2)))
    
    If pull < 3 Then
        PlaceGuy = ""
        Exit Function
    End If
    
    If (rotateAng > (Pi / 2)) And (rotateAng <= (3 * Pi / 2)) Then
        str = "ExGuyOL"
        str2 = "ExAncOL"
    Else
        str = "ExGuyOR"
        str2 = "ExAncOR"
    End If
    
    'insertPnt = ThisDrawing.Utility.GetPoint(, "Place Guy:")
    insertPnt(0) = X0
    insertPnt(1) = Y0
    insertPnt(2) = 0#
    
    If pull >= 50 Then  '<------------------------------------- Get strPull
        strPull = "DE"
        
        dTemp = Abs(firstAng - endAng)
        
        If dTemp < 0.0002 Then
            Call AddAnchorGuy(insertPnt, CStr(str2), CStr(str), CStr(strPull), CDbl(rotateAng))
        
            strTemp = "+PE1-3G=1;;+PF1-5A=1;;+PM11=1"
        Else
            Call AddAnchorGuy(insertPnt, CStr(str2), CStr(str), CStr(strPull), (firstAng + Pi))
            Call AddAnchorGuy(insertPnt, CStr(str2), CStr(str), CStr(strPull), (endAng + Pi))
        
            strTemp = "+PM2A=1;;+PE1-3G=2;;+PF1-5A=2;;+PM11=2"
        End If
    Else
        strPull = pull
        Call AddAnchorGuy(insertPnt, CStr(str2), CStr(str), CStr(strPull), CDbl(rotateAng))
        
        strTemp = "+PE1-3G=1;;+PF1-5A=1;;+PM11=1"
    End If
    
Exit_Sub:
    PlaceGuy = strTemp
End Function

Private Sub AddAnchorGuy(vInsert As Variant, strAnc As String, strGuy As String, strPull As String, dRotate As Double)
    Dim objBlock As AcadBlockReference
    Dim vAttList As Variant
    Dim dScale As Double
    Dim dInsert(2) As Double
    
    dInsert(0) = vInsert(0)
    dInsert(1) = vInsert(1)
    dInsert(2) = vInsert(2)
    dScale = CDbl(cbScale.Value) / 100
    
    'MsgBox strGuy & vbCr & dScale & vbCr & dRotate
    
    'Set layerObj = ThisDrawing.Layers.Add("Integrity Proposed")
    'ThisDrawing.ActiveLayer = layerObj
        
    Set objBlock = ThisDrawing.ModelSpace.InsertBlock(dInsert, strGuy, dScale, dScale, dScale, dRotate)
    objBlock.Layer = "Integrity Proposed"
    vAttList = objBlock.GetAttributes
    vAttList(2).TextString = "PE1-3G"
    objBlock.Update

    Set objBlock = ThisDrawing.ModelSpace.InsertBlock(dInsert, strAnc, dScale, dScale, dScale, dRotate)
    objBlock.Layer = "Integrity Proposed"
    vAttList = objBlock.GetAttributes
    vAttList(0).TextString = "PF1-5A"
    If strPull = "DE" Then
        vAttList(1).TextString = "P= DE"
    Else
        vAttList(1).TextString = "P= " & strPull
    End If
    objBlock.Update
End Sub

Private Sub tbCoilCable_Change()
    If tbCoilCable.Value = "" Then
        cbClosure.Value = ""
        Exit Sub
    End If
    
    Dim strPath As String
    
    strPath = LCase(ThisDrawing.Path)
    
    If InStr(strPath, "united") > 0 Then
        Select Case CInt(tbCoilCable.Value)
            Case Is < 49
                cbClosure.Value = "FOSC A"
            Case Is > 96
                cbClosure.Value = "FOSC D"
            Case Else
                cbClosure.Value = "FOSC B"
        End Select
    Else
        Select Case CInt(tbCoilCable.Value)
            Case Is < 25
                cbClosure.Value = "G4"
            Case Is > 144
                cbClosure.Value = "G6"
            Case Else
                cbClosure.Value = "G5"
        End Select
    End If
End Sub

Private Sub tbStrandCable_Change()
    If tbStrandCable.Value = "" Then
        tbCoilCable.Value = ""
        cbGuy.Value = False
        Exit Sub
    End If
    
    tbCoilCable.Value = tbStrandCable.Value
    cbGuy.Value = True
End Sub

Private Sub UserForm_Initialize()
    cbClosure.AddItem ""
    cbClosure.AddItem "#1413"
    cbClosure.AddItem "FOSC A"
    cbClosure.AddItem "FOSC B"
    cbClosure.AddItem "FOSC D"
    cbClosure.AddItem "G4"
    cbClosure.AddItem "G5"
    cbClosure.AddItem "G6"
    cbClosure.AddItem "G6S"
    
    cbCoilType.AddItem ""
    cbCoilType.AddItem "FEED"
    cbCoilType.AddItem "12F"
    cbCoilType.AddItem "24F"
    cbCoilType.AddItem "36F"
    cbCoilType.AddItem "48F"
    cbCoilType.AddItem "72F"
    cbCoilType.AddItem "96F"
    cbCoilType.AddItem "144F"
    cbCoilType.AddItem "216F"
    cbCoilType.AddItem "288F"
    cbCoilType.AddItem "432F"
    
    cbClosureType.AddItem ""
    cbClosureType.AddItem "Aerial"
    cbClosureType.AddItem "Buried"
    cbClosureType.AddItem "UG"
    cbClosureType.Value = "Aerial"
    
    cbScale.AddItem "50"
    cbScale.AddItem "75"
    cbScale.AddItem "100"
    cbScale.Value = "100"
    
    cbStatus.AddItem "Proposed"
    cbStatus.AddItem "Existing"
    cbStatus.AddItem "Removed"
    cbStatus.Value = "Proposed"
End Sub

Private Sub PlaceClosure(vInfo As Variant)
    Dim dDist, dScale, dRotate As Double
    Dim dInsertPnt(2) As Double
    Dim dBackPnt(2) As Double
    
    dDist = vInfo(0)
    dScale = vInfo(1)
    dRotate = vInfo(2)
    
    dInsertPnt(0) = vInfo(3)
    dInsertPnt(1) = vInfo(4)
    dInsertPnt(2) = 0#
    
    dBackPnt(0) = vInfo(5)
    dBackPnt(1) = vInfo(6)
    dBackPnt(2) = 0#
    
    
    
    Dim obrMClosure As AcadBlockReference
    Dim obrMCoil As AcadBlockReference
    'Dim objBlock, obrGP3 As AcadBlockReference
    'Dim vReturnPnt, vEndPnt As Variant
    Dim vAttList As Variant
    Dim dDiff(0 To 3) As Double
    Dim strBlockName, strTermType As String
    'Dim layerObj As AcadLayer
    'Dim returnPnt, vPoleCoords As Variant
    Dim str, strLayer As String
    Dim vBlockCoords(0 To 2) As Double
    Dim i As Integer

    Me.Hide

    strTermType = ""

  On Error Resume Next

    str = ""
    Err = 0

    dDiff(0) = dBackPnt(0) - dInsertPnt(0)
    dDiff(1) = dBackPnt(1) - dInsertPnt(1)
    dDiff(2) = Math.Sqr(dDiff(0) * dDiff(0) + (dDiff(1) * dDiff(1)))

    dInsertPnt(0) = dInsertPnt(0) + 15 * dScale * dDiff(0) / dDiff(2)
    dInsertPnt(1) = dInsertPnt(1) + 15 * dScale * dDiff(1) / dDiff(2)
    dInsertPnt(2) = 0#

    strLayer = "Integrity Map Splices-Aerial"

    strBlockName = "Map splice"
    Set obrMClosure = ThisDrawing.ModelSpace.InsertBlock(dInsertPnt, strBlockName, dScale, dScale, dScale, dRotate)
    obrMClosure.Layer = strLayer
    vAttList = obrMClosure.GetAttributes

    If Not cbClosure.Value = "" Then vAttList(0).TextString = cbClosure.Value
    'vAttList(1).TextString = str
    obrMClosure.Update

place_coil:

    dInsertPnt(0) = dInsertPnt(0) + 15 * dScale * dDiff(0) / dDiff(2)
    dInsertPnt(1) = dInsertPnt(1) + 15 * dScale * dDiff(1) / dDiff(2)

    If dDiff(0) > 0 Then
        dInsertPnt(0) = dInsertPnt(0) + 9 * dScale * dDiff(1) / dDiff(2)
        dInsertPnt(1) = dInsertPnt(1) - 9 * dScale * dDiff(0) / dDiff(2)
    Else
        dInsertPnt(0) = dInsertPnt(0) - 9 * dScale * dDiff(1) / dDiff(2)
        dInsertPnt(1) = dInsertPnt(1) + 9 * dScale * dDiff(0) / dDiff(2)
    End If

    strLayer = "Integrity Map Coils-Aerial"   'Replace(strLayer, "Splices", "Coils")

    Set obrMCoil = ThisDrawing.ModelSpace.InsertBlock(dInsertPnt, "Map coil", dScale, dScale, dScale, 0#)
    obrMCoil.Layer = strLayer
    vAttList = obrMCoil.GetAttributes
    If Not tbCoil.Value = "" Then vAttList(0).TextString = tbCoil.Value & "'"
    vAttList(1).TextString = tbCoilCable.Value & "F"
    obrMCoil.Update

Exit_Sub:
    
End Sub

Attribute VB_Name = "PlaceBuriedData"
Attribute VB_Base = "0{F725F9D4-37EF-48FD-8EEF-A4698FF12024}{4DF26F06-EE46-426A-8606-D5BBE22B7F60}"
Attribute VB_GlobalNameSpace = False
Attribute VB_Creatable = False
Attribute VB_PredeclaredId = True
Attribute VB_Exposed = False
Attribute VB_TemplateDerived = False
Attribute VB_Customizable = False
Dim objBlock As AcadBlockReference
Dim strRoute As String
Dim iNumber As Integer
    
Private Sub cbAddUnit_Click()
    If cbAddUnit.Caption = "Update" Then
        lbUnits.List(lbUnits.ListIndex, 0) = tbUnit.Value
        lbUnits.List(lbUnits.ListIndex, 1) = tbQuantity.Value
        lbUnits.List(lbUnits.ListIndex, 2) = tbUNote.Value
        
        cbAddUnit.Caption = "Add Unit"
        GoTo Exit_Sub
    End If
    
    lbUnits.AddItem tbUnit.Value
    lbUnits.List(lbUnits.ListCount - 1, 1) = tbQuantity.Value
    lbUnits.List(lbUnits.ListCount - 1, 2) = tbUNote.Value
    
Exit_Sub:
    
    tbUnit.Value = ""
    tbQuantity.Value = ""
    tbUNote.Value = ""
End Sub

Private Sub cbGetBlock_Click()
    Dim objObject As AcadObject
    Dim vBasePnt, vAttList As Variant
    Dim vLine, vItem, vTemp As Variant
    Dim strTemp, strType, strGround As String
    
    Me.Hide
  On Error Resume Next
    
    ThisDrawing.Utility.GetEntity objObject, vBasePnt, "Select Buried Plant: "
    If TypeOf objObject Is AcadBlockReference Then
        Set objBlock = objObject
    Else
        MsgBox "Not a valid object."
        Me.show
        Exit Sub
    End If
    
    cbStatus.Value = "PROPOSED"
    If InStr(LCase(objBlock.Layer), "existing") > 0 Then cbStatus.Value = "EXISTING"
    If InStr(LCase(objBlock.Layer), "future") > 0 Then cbStatus.Value = "FUTURE"
    
    Select Case objBlock.Name
        Case "sPed", "sHH", "sFP", "sPanel", "sMH"
        Case Else
            MsgBox "Not a valid block."
            Me.show
            Exit Sub
    End Select
    
    'tbNumber.Value = ""
    'tbStatus.Value = ""
    'cbType.Value = ""
    'tbLL.Value = ""
    'cbGround.Value = ""
    
    strType = cbType.Value
    strGround = cbGround.Value
    
    vAttList = objBlock.GetAttributes
    
    Select Case vAttList(0).TextString
        Case "PED", "HH", "FP", "PANEL", "MH"
            tbNumber.Value = strRoute & iNumber
        Case Else
            tbNumber.Value = vAttList(0).TextString
        
            Dim v00, v01 As Variant
            Dim strLine As String
            Dim iLen As Integer
    
            strLine = tbNumber.Value
    
            If Right(strLine, 1) = "X" Then
                strRoute = strLine
                iNumber = 1
            Else
                v01 = Split(strLine, "/")
                v00 = Split(v01(UBound(v01)), "L")
                v01 = Split(v00(UBound(v00)), "R")
                v00 = Split(v01(UBound(v01)), "-")
                strTemp = v00(UBound(v00))
        
                iLen = Len(strLine) - Len(strTemp)
        
                strRoute = Left(strLine, iLen)
                iNumber = Int(strTemp) + 1
            End If
    End Select
    
    tbStatus.Value = vAttList(1).TextString
    
    cbType.Value = vAttList(2).TextString
    
    If vAttList(3).TextString = "" Then
        Dim dN, dE As Double
        Dim vLL As Variant
        
        dE = objBlock.InsertionPoint(0)
        dN = objBlock.InsertionPoint(1)
        vLL = TN83FtoLL(CDbl(dN), CDbl(dE))
        
        tbLL.Value = vLL(0) & "," & vLL(1)
    Else
        tbLL.Value = vAttList(3).TextString
    End If
    
    cbGround.Value = vAttList(4).TextString
    
    '<---------------------------------------------------------------- Add Units
    
    lbUnits.Clear
    lbCables.Clear
    lbSplices.Clear
    
    If Not vAttList(7).TextString = "" Then
        vAttList(7).TextString = Replace(vAttList(7).TextString, vbLf, "")
        vLine = Split(vAttList(7).TextString, ";;")
        For i = 0 To UBound(vLine)
            vItem = Split(vLine(i), "=")
            lbUnits.AddItem vItem(0)
            If InStr(vItem(1), "  ") > 0 Then
                vTemp = Split(vItem(1), "  ")
                lbUnits.List(lbUnits.ListCount - 1, 1) = vTemp(0)
                lbUnits.List(lbUnits.ListCount - 1, 2) = vTemp(1)
            Else
                lbUnits.List(lbUnits.ListCount - 1, 1) = vItem(1)
                lbUnits.List(lbUnits.ListCount - 1, 2) = ""
            End If
        Next i
    End If
    
    If cbType.Value = "" Then cbType.Value = strType
    If cbGround.Value = "" Then cbGround.Value = strGround
    
    
    'att 25
    If Not vAttList(5).TextString = "" Then
        vAttList(5).TextString = Replace(vAttList(5).TextString, vbLf, "")
        vLine = Split(vAttList(5).TextString, vbCr)
        For i = 0 To UBound(vLine)
            vItem = Split(vLine(i), " / ")
            lbCables.AddItem vItem(0)
            lbCables.List(lbCables.ListCount - 1, 1) = vItem(1)
        Next i
    End If
    
    'att 26
    If Not vAttList(6).TextString = "" Then
        vAttList(6).TextString = Replace(vAttList(6).TextString, vbLf, "")
        'If InStr(vAttList(6).TextString, " + ") > 0 Then vAttList(6).TextString = Replace(vAttList(6).TextString, " + ", vbCr)
        
        vLine = Split(vAttList(6).TextString, vbCr)
        For i = 0 To UBound(vLine)
            lbSplices.AddItem vLine(i)
        Next i
    End If
    
    cbUpdateBlock.Enabled = True
    cbPlaceData.SetFocus
    
    Me.show
End Sub

Private Sub cbGetCables_Click()
    Dim objEntity As AcadEntity
    Dim objBlock As AcadBlockReference
    Dim vAttList, vBasePnt As Variant
    Dim strLine As String
    
    Me.Hide
    On Error Resume Next
    
    ThisDrawing.Utility.GetEntity objEntity, vBasePnt, "Get Cable Callout: "
    
    If Not Err = 0 Then GoTo Exit_Sub
    
    If Not TypeOf objEntity Is AcadBlockReference Then
        MsgBox "Invalid selection"
        GoTo Exit_Sub
    End If
    
    Set objBlock = objEntity
    
    If Not objBlock.Name = "CableCounts" Then
        MsgBox "Invalid block"
        Me.show
        Exit Sub
    End If
    
    vAttList = objBlock.GetAttributes
    
    lbCables.AddItem vAttList(1).TextString
    lbCables.List(lbCables.ListCount - 1, 1) = Replace(vAttList(0).TextString, "\P", " + ")
    
Exit_Sub:
    Me.show
End Sub

Private Sub cbGetClosures_Click()
    Dim objEntity As AcadEntity
    Dim objBlock As AcadBlockReference
    Dim vAttList, vBasePnt As Variant
    Dim vLine As Variant
    Dim strLine As String
    
    Me.Hide
    On Error Resume Next
    
    ThisDrawing.Utility.GetEntity objEntity, vBasePnt, "Get Closure Callout: "
    
    If Not Err = 0 Then GoTo Exit_Sub
    
    If Not TypeOf objEntity Is AcadBlockReference Then
        MsgBox "Invalid selection"
        GoTo Exit_Sub
    End If
    
    Set objBlock = objEntity
    
    If Not objBlock.Name = "terminal" Then
        MsgBox "Invalid block"
        GoTo Exit_Sub
    End If
    
    vAttList = objBlock.GetAttributes
    
    strLine = Replace(vAttList(0).TextString, "\P", " + ")
    lbSplices.AddItem strLine
    
Exit_Sub:
    Me.show
End Sub

Private Sub cbGetUnits_Click()
    Dim objSS As AcadSelectionSet
    Dim objEntity As AcadEntity
    Dim objBlock As AcadBlockReference
    Dim vAttList, vLine, vItem As Variant
    Dim strTemp, strLine As String
    Dim iFeet, iInch, iTotal, iRL As Integer
    
    Me.Hide
    
  On Error Resume Next
    
    Set objSS = ThisDrawing.SelectionSets.Add("objSS")
    If Not Err = 0 Then Set objSS = ThisDrawing.SelectionSets.Item("objSS")
        
    objSS.SelectOnScreen
    For Each objEntity In objSS
        If Not TypeOf objEntity Is AcadBlockReference Then GoTo Next_objEntity
        
        Set objBlock = objEntity
        If objBlock.Name = "pole_unit" Then
            vAttList = objBlock.GetAttributes
            
            vLine = Split(vAttList(3).TextString, "=")
            lbUnits.AddItem vLine(0), 0
            
            vLine(1) = Replace(vLine(1), "  ", " ")
            vItem = Split(vLine(1), " ")
            lbUnits.List(0, 1) = vItem(0)
            If UBound(vItem) < 1 Then
                lbUnits.List(0, 2) = ""
            Else
                lbUnits.List(0, 2) = vItem(1)
            End If
        End If
Next_objEntity:
    Next objEntity
    
    objSS.Clear
    objSS.Delete
    
    Me.show
End Sub

Private Sub cbGround_Change()
    If cbGround.Value = "" Then Exit Sub
    Select Case cbStatus.Value
        Case "EXISTING", "FUTURE", ""
            Exit Sub
    End Select
    
    Dim strTemp As String
    
    If lbUnits.ListCount > -1 Then
        For i = 0 To lbUnits.ListCount - 1
            If InStr(lbUnits.List(i, 0), "+BM2(") > 0 Then
                lbUnits.RemoveItem i
                GoTo Exit_For
            End If
            If lbUnits.List(i, 0) = "+BM2A" Then
                lbUnits.RemoveItem i
                GoTo Exit_For
            End If
        Next i
    End If
Exit_For:

    Select Case cbGround.Value
        Case "TGB"
            strTemp = "+BM2(5/8)(8)"
        Case "MGN", "MGNV", "OTHER"
            strTemp = "+BM2A"
        Case Else
            Exit Sub
    End Select
        
    lbUnits.AddItem strTemp
    lbUnits.List(lbUnits.ListCount - 1, 1) = 1
End Sub

Private Sub cbPlaceData_Click()
    Dim insertionPnt(0 To 2) As Double
    Dim lwpPnt(0 To 3) As Double
    Dim dScale As Double
    Dim objPoint As AcadEntity
    Dim blockRefObj As AcadBlockReference
    Dim obrUnit As AcadBlockReference
    Dim lineObj As AcadLWPolyline
    Dim returnPoint, attList As Variant
    Dim attArray() As Variant
    Dim str, str1, str2, str3 As String
    Dim strArray() As String
    Dim strPoleNum, strPosition As String
    Dim strBlock, strLine As String
    Dim n, counter As Integer
    Dim layerObj As AcadLayer
    Dim vTemp As Variant
    Dim dLat, dLong As Double
    
  On Error Resume Next
  
    If cbScale.Value = "" Then
        dScale = 1#
    Else
        dScale = CDbl(cbScale.Value) / 100
    End If
    
    strPoleNum = tbNumber.Value
    str = "pole_info"
    
    Select Case cbStatus.Value
        Case "FUTURE"
            strLayer = "Integrity Future"
        Case "EXISTING"
            strLayer = "Integrity Existing"
        Case Else
            strLayer = "Integrity Proposed"
    End Select
    
    Me.Hide

    returnPoint = ThisDrawing.Utility.GetPoint(, "Select point:")
    n = 0
    For Each Item In returnPoint
        insertionPnt(n) = Item
        n = n + 1
    Next Item
    
    Set blockRefObj = ThisDrawing.ModelSpace.InsertBlock(insertionPnt, str, dScale, dScale, dScale, 0)
        
    attList = blockRefObj.GetAttributes
    attList(0).TextString = strPoleNum
    attList(1).TextString = "0.0"
    attList(2).TextString = strPoleNum
    attList(3).TextString = ""
    
    blockRefObj.Layer = strLayer
    
    blockRefObj.Update
    insertionPnt(1) = insertionPnt(1) - (9 * dScale)
    
    If Not cbType.Value = "" Then
        Set blockRefObj = ThisDrawing.ModelSpace.InsertBlock(insertionPnt, str, dScale, dScale, dScale, 0)
        
        attList = blockRefObj.GetAttributes
        attList(0).TextString = strPoleNum
        attList(1).TextString = "0.1"
        attList(2).TextString = cbType.Value
        attList(3).TextString = ""
    
        blockRefObj.Layer = strLayer
        
        blockRefObj.Update
        insertionPnt(1) = insertionPnt(1) - (9 * dScale)
    End If
    
    If Not cbGround.Value = "" Then
        Set blockRefObj = ThisDrawing.ModelSpace.InsertBlock(insertionPnt, str, dScale, dScale, dScale, 0)
        
        If cbGround.Value = "NONE" Then cbGround.Value = "NO GRD"
        
        attList = blockRefObj.GetAttributes
        attList(0).TextString = strPoleNum
        attList(1).TextString = "0.2"
        attList(2).TextString = cbGround.Value
        attList(3).TextString = ""
    
        blockRefObj.Layer = strLayer
        
        blockRefObj.Update
        insertionPnt(1) = insertionPnt(1) - (9 * dScale)
    End If
    
    If cbLL.Value = True Then
        If Not tbLL.Value = "" Then
            vTemp = Split(tbLL.Value, ",")
            dLat = CLng(CDbl(vTemp(0)) * 10000000) / 10000000
            dLong = CLng(CDbl(vTemp(1)) * 10000000) / 10000000
            
            Set blockRefObj = ThisDrawing.ModelSpace.InsertBlock(insertionPnt, str, dScale, dScale, dScale, 0)
        
            attList = blockRefObj.GetAttributes
            attList(0).TextString = strPoleNum
            attList(1).TextString = "0.99"
            attList(2).TextString = dLat & "," & dLong
            attList(3).TextString = ""
    
            blockRefObj.Layer = strLayer
        
            blockRefObj.Update
            insertionPnt(1) = insertionPnt(1) - (9 * dScale)
        End If
    End If
    
    lwpPnt(0) = insertionPnt(0) - (4 * dScale)
    lwpPnt(1) = insertionPnt(1) + (7 * dScale)
    lwpPnt(2) = lwpPnt(0) + (100 * dScale)
    lwpPnt(3) = lwpPnt(1)
    
    Set lineObj = ThisDrawing.ModelSpace.AddLightWeightPolyline(lwpPnt)
    
    lineObj.Layer = blockRefObj.Layer
    
    lineObj.Update
    
    insertionPnt(1) = insertionPnt(1) - (1 * dScale)
    
    str = "pole_unit"
    If cbAddUnits.Value = False Then
        Me.show
        Exit Sub
    End If
    
    If Not strLayer = "Integrity Future" Then strLayer = "Integrity Pole-Units"
    
    For i = 0 To (lbUnits.ListCount - 1)
        Set obrUnit = ThisDrawing.ModelSpace.InsertBlock(insertionPnt, str, dScale, dScale, dScale, 0)
        
        strLine = lbUnits.List(i, 0) & "=" & lbUnits.List(i, 1)
        If Not lbUnits.List(i, 2) = "" Then strLine = strLine & "  " & lbUnits.List(i, 2)
        
        attList = obrUnit.GetAttributes
        attList(0).TextString = strPoleNum
        attList(1).TextString = "2"     '<------------------ add i if needed
        attList(2).TextString = "N/A"
        attList(3).TextString = strLine
        obrUnit.Layer = strLayer
        obrUnit.Update
        
        insertionPnt(1) = insertionPnt(1) - (9 * dScale)
    Next i
    
    Me.show
End Sub

Private Sub cbPlacePlant_Click()
    If tbNumber.Value = "" Then
        MsgBox "Need a Buried Plant Number."
        Exit Sub
    End If
    
    If cbType.Value = "" Then
        MsgBox "Need a Type."
        Exit Sub
    End If
    
    If cbGround.Value = "" Then
        MsgBox "Need a Ground Source."
        Exit Sub
    End If
    
    Dim objNew As AcadBlockReference
    Dim strBlock, strRoute, strShort As String
    Dim strCables, strUnits, strSplices As String
    Dim strChar, strLayer As String
    Dim vInsertPnt, vAttList As Variant
    Dim vSlash, vDash, vL, vR As Variant
    Dim dScale As Double
    
    dScale = CDbl(cbScale.Value) / 100
    
    tbNumber.Value = UCase(tbNumber.Value)
    
    vSlash = Split(tbNumber.Value, "/")
    vDash = Split(vSlash(UBound(vSlash)), "-")
    vL = Split(vDash(UBound(vDash)), "L")
    vR = Split(vL(UBound(vL)), "R")
    strShort = vR(UBound(vR))
    strRoute = Left(tbNumber.Value, Len(tbNumber.Value) - Len(strShort))
    
    If lbCables.ListCount > 0 Then
        strCables = lbCables.List(0, 0) & " / " & lbCables.List(0, 1)
        If lbCables.ListCount > 1 Then
            For i = 1 To lbCables.ListCount - 1
                strCables = strCables & vbCr & lbCables.List(i, 0) & " / " & lbCables.List(i, 1)
            Next i
        End If
    Else
        strCables = ""
    End If
    
    If lbUnits.ListCount > 0 Then
        strUnits = lbUnits.List(0, 0) & "=" & lbUnits.List(0, 1)
        If Not lbUnits.List(0, 2) = "" Then strUnits = strUnits & "  " & lbUnits.List(0, 2)
        If lbUnits.ListCount > 1 Then
            For i = 1 To lbUnits.ListCount - 1
                strUnits = strUnits & ";;" & lbUnits.List(i, 0) & "=" & lbUnits.List(i, 1)
                If Not lbUnits.List(i, 2) = "" Then strUnits = strUnits & "  " & lbUnits.List(i, 2)
            Next i
        End If
    Else
        strUnits = ""
    End If
    
    If lbSplices.ListCount > 0 Then
        strSplices = lbSplices.List(0)
        If lbSplices.ListCount > 1 Then
            For i = 1 To lbSplices.ListCount - 1
                strSplices = strSplices & vbCr & lbSplices.List(i)
            Next i
        End If
    Else
        strSplices = ""
    End If
    
    strBlock = "sPed"
    
    If InStr(cbType.Value, "UHF") > 0 Then strBlock = "sHH"
    If InStr(cbType.Value, "BHF") > 0 Then strBlock = "sHH"
    If InStr(cbType.Value, "FP") > 0 Then strBlock = "sFP"
    If InStr(cbType.Value, "FIBER") > 0 Then strBlock = "sPanel"
    If InStr(cbType.Value, "BUDI") > 0 Then strBlock = "sPanel"
    
    Me.Hide

On Error Resume Next
    
Add_Another:
    
    vInsertPnt = ThisDrawing.Utility.GetPoint(, vbCr & "Selct Insertion Point: ")
    If Not Err = 0 Then
        Me.show
        Exit Sub
    End If
    
    Set objNew = ThisDrawing.ModelSpace.InsertBlock(vInsertPnt, strBlock, dScale, dScale, dScale, 0#)
    vAttList = objNew.GetAttributes
    
    Dim dN, dE As Double
    Dim vLL As Variant
        
    dE = objNew.InsertionPoint(0)
    dN = objNew.InsertionPoint(1)
    vLL = TN83FtoLL(CDbl(dN), CDbl(dE))
        
    tbLL.Value = vLL(0) & "," & vLL(1)
    
    vAttList(0).TextString = tbNumber.Value
    
    Select Case tbStatus.Value
        Case ""
            Case "EXISTING"
    End Select
    If Not tbStatus.Value = "" Then vAttList(1).TextString = tbStatus.Value
    vAttList(2).TextString = cbType.Value
    vAttList(3).TextString = tbLL.Value
    vAttList(4).TextString = cbGround.Value
    vAttList(5).TextString = strCables
    vAttList(6).TextString = strSplices
    vAttList(7).TextString = strUnits
    
    If strBlock = "sFP" Then vAttList(1).TextString = strShort
    
    Select Case cbStatus.Value
        Case "EXISTING"
            strLayer = "Integrity Existing-Buried"
        Case "FUTURE"
            strLayer = "Integrity Future"
        Case Else
            strLayer = "Integrity Proposed-Buried"
    End Select
    objNew.Layer = strLayer
    
    objNew.Update
    
    If IsNumeric(strShort) Then
        strShort = CInt(strShort) + 1
        tbNumber.Value = strRoute & strShort
    Else
        strChar = Chr(Asc(Right(strShort, 1)) + 1)
        strShort = Left(strShort, Len(strShort) - 1) & strChar
        tbNumber.Value = strRoute & strShort
    End If
    
    GoTo Add_Another
    
    Me.show
End Sub

Private Sub cbQuit_Click()
    Me.Hide
End Sub

Private Sub cbRoatateAtt_Click()
    Dim objEntity As AcadEntity
    Dim objBlock As AcadBlockReference
    Dim vAttList, vReturnPnt As Variant
    'Dim vLine As Variant
    
    Me.Hide
    
    On Error Resume Next
Get_Another:
    
    ThisDrawing.Utility.GetEntity objEntity, vReturnPnt, vbCr & "Select Callout:"
    If Not Err = 0 Then GoTo Exit_Sub
    
    If Not TypeOf objEntity Is AcadBlockReference Then GoTo Exit_Sub
    
    Set objBlock = objEntity
    
    Select Case objBlock.Name
        Case "sPole", "sPed", "sHH"
        Case Else
            GoTo Exit_Sub
    End Select
    
    vAttList = objBlock.GetAttributes
    
    For i = 0 To UBound(vAttList)
        vAttList(i).Rotation = 0#
    Next i
    objBlock.Update
    
    GoTo Get_Another
Exit_Sub:
    Me.show
End Sub

Private Sub cbType_Change()
    If cbType.Value = "" Then Exit Sub
    Select Case cbStatus.Value
        Case "EXISTING", "FUTURE", ""
            Exit Sub
    End Select
    
    Dim strTemp As String
    
    strTemp = "+" & cbType.Value
    
    If lbUnits.ListCount > -1 Then
        For i = 0 To lbUnits.ListCount - 1
            If InStr(lbUnits.List(i, 0), "+BDO") > 0 Then
                lbUnits.RemoveItem i
                GoTo Exit_For
            End If
            If InStr(lbUnits.List(i, 0), "+BHF") > 0 Then
                lbUnits.RemoveItem i
                GoTo Exit_For
            End If
            If InStr(lbUnits.List(i, 0), "+UHF") > 0 Then
                lbUnits.RemoveItem i
                GoTo Exit_For
            End If
            If InStr(lbUnits.List(i, 0), "+FP") > 0 Then
                lbUnits.RemoveItem i
                GoTo Exit_For
            End If
            If InStr(lbUnits.List(i, 0), "+FIBER") > 0 Then
                lbUnits.RemoveItem i
                GoTo Exit_For
            End If
            If InStr(lbUnits.List(i, 0), "+BUDI") > 0 Then
                lbUnits.RemoveItem i
                GoTo Exit_For
            End If
        Next i
    End If
Exit_For:
        
    lbUnits.AddItem strTemp
    lbUnits.List(lbUnits.ListCount - 1, 1) = 1
End Sub

Private Sub cbUpdateBlock_Click()
    Dim vAttList As Variant
    Dim strLine As String
    
    vAttList = objBlock.GetAttributes
    
    vAttList(0).TextString = tbNumber.Value
    If Not tbStatus.Value = "" Then vAttList(1).TextString = tbStatus.Value
    If Not cbType.Value = "" Then vAttList(2).TextString = cbType.Value
    If Not tbLL.Value = "" Then vAttList(3).TextString = tbLL.Value
    If Not cbGround.Value = "" Then vAttList(4).TextString = cbGround.Value
    
    If lbUnits.ListCount > 0 Then
        strLine = lbUnits.List(0, 0) & "=" & lbUnits.List(0, 1)
        If Not lbUnits.List(0, 2) = "" Then strLine = strLine & "  " & lbUnits.List(0, 2)
        
        If lbUnits.ListCount > 1 Then
            For i = 1 To lbUnits.ListCount - 1
                strLine = strLine & ";;" & lbUnits.List(i, 0) & "=" & lbUnits.List(i, 1)
                If Not lbUnits.List(i, 2) = "" Then strLine = strLine & "  " & lbUnits.List(i, 2)
            Next i
        End If
        
        vAttList(7).TextString = strLine
    End If
    
    strLine = ""
    
    If lbCables.ListCount > 0 Then
        For i = 0 To lbCables.ListCount - 1
            If strLine = "" Then
                strLine = lbCables.List(i, 0) & " / " & lbCables.List(i, 1)
            Else
                strLine = strLine & vbCr & lbCables.List(i, 0) & " / " & lbCables.List(i, 1)
            End If
        Next i
        
        vAttList(5).TextString = strLine
    End If
    
    strLine = ""
    
    If lbSplices.ListCount > 0 Then
        For i = 0 To lbSplices.ListCount - 1
            If strLine = "" Then
                strLine = lbSplices.List(i, 0)
            Else
                strLine = strLine & " + " & lbSplices.List(i, 0)
            End If
        Next i
        
        vAttList(6).TextString = strLine
    End If
    
    objBlock.Update
    
    'Dim v00, v01 As Variant
    'Dim strTemp As String
    'Dim iLen As Integer
    
    'strLine = tbNumber.Value
    
    'If Right(strLine, 1) = "X" Then
        'strRoute = strLine
        'iNumber = 1
    'Else
        'v01 = Split(strLine, "/")
        'v00 = Split(v01(UBound(v01)), "L")
        'v01 = Split(v00(UBound(v00)), "R")
        'v00 = Split(v01(UBound(v01)), "-")
        'strTemp = v00(UBound(v00))
        
        'iLen = Len(strLine) - Len(strTemp)
        
        'strRoute = Left(strLine, iLen)
        'iNumber = Int(strTemp) + 1
    'End If
End Sub

Private Sub Label13_Click()
    Dim objEntity As AcadEntity
    Dim objTemp As AcadBlockReference
    Dim vAttList, vReturnPnt As Variant
    
    Me.Hide
    
    ThisDrawing.Utility.GetEntity objEntity, vReturnPnt, vbCr & "Select Plant Number: "
    
    If TypeOf objEntity Is AcadBlockReference Then
        Set objTemp = objEntity
        vAttList = objTemp.GetAttributes
        
        tbNumber.Value = vAttList(0).TextString
    End If
    
    Me.show
End Sub

Private Sub Label38_Click()
    If cbUpdateBlock.Enabled = False Then Exit Sub
    
    Dim dN, dE As Double
    Dim vLL As Variant
        
    dE = objBlock.InsertionPoint(0)
    dN = objBlock.InsertionPoint(1)
    vLL = TN83FtoLL(CDbl(dN), CDbl(dE))
        
    tbLL.Value = vLL(0) & "," & vLL(1)
End Sub

Private Sub lbCables_DblClick(ByVal Cancel As MSForms.ReturnBoolean)
    If lbSplices.ListCount < 1 Then Exit Sub
    
    Dim objCO As AcadBlockReference
    'Dim objEntity As AcadEntity
    Dim returnPnt As Variant
    Dim vBlockCoords(0 To 2) As Double
    Dim lwpCoords(0 To 3) As Double
    Dim dPrevious(0 To 2) As Double
    Dim dOrigin(0 To 2) As Double
    Dim dScale As Double
    Dim lineObj As AcadLWPolyline
    Dim objCircle As AcadCircle
    Dim objCircle2 As AcadCircle
    Dim objText As AcadText
    Dim objText2 As AcadText
    Dim vLine, vCounts, vTemp As Variant
    Dim strLetter, strCounts, strHO1 As String
    Dim strSegment As String
    Dim iHO1, iIndex As Integer
    
  'On Error Resume Next
    iIndex = lbCables.ListIndex
    
    dOrigin(0) = 0
    dOrigin(1) = 0
    dOrigin(2) = 0
    
    Me.Hide
    returnPnt = ThisDrawing.Utility.GetPoint(, "Select Point: ")
    
    lwpCoords(0) = returnPnt(0)
    lwpCoords(1) = returnPnt(1)
    dPrevious(0) = returnPnt(0)
    dPrevious(1) = returnPnt(1)
    dPrevious(2) = 0#
    
    returnPnt = ThisDrawing.Utility.GetPoint(dPrevious, "Select Point: ")
    vBlockCoords(0) = returnPnt(0)
    vBlockCoords(1) = returnPnt(1)
    vBlockCoords(2) = returnPnt(2)
    lwpCoords(2) = vBlockCoords(0)
    lwpCoords(3) = vBlockCoords(1)
    
    If cbPlacement.Value = "Leader" Then
        Set lineObj = ThisDrawing.ModelSpace.AddLightWeightPolyline(lwpCoords)
        lineObj.Layer = "Integrity Proposed"
        lineObj.Update
    Else
        Set objCircle = ThisDrawing.ModelSpace.AddCircle(dPrevious, 8)
        objCircle.Layer = "Integrity Proposed"
        objCircle.Update
        Set objCircle2 = ThisDrawing.ModelSpace.AddCircle(returnPnt, 8)
        objCircle2.Layer = "Integrity Proposed"
        objCircle2.Update
        
        strLetter = UCase(ThisDrawing.Utility.GetString(0, "Enter Callout Letter:"))
        Set objText = ThisDrawing.ModelSpace.AddText(strLetter, dOrigin, 8)
        Set objText2 = ThisDrawing.ModelSpace.AddText(strLetter, dOrigin, 8)
        objText.Layer = "Integrity Proposed"
        objText.Alignment = acAlignmentMiddle
        objText.TextAlignmentPoint = dPrevious
        objText2.Layer = "Integrity Proposed"
        objText2.Alignment = acAlignmentMiddle
        objText2.TextAlignmentPoint = vBlockCoords
        objText.Update
        objText2.Update
        
        vBlockCoords(0) = vBlockCoords(0) + 8
        lwpCoords(0) = 0
    End If
    
    dScale = CDbl(cbScale.Value) / 100
    If dScale = 0 Then dScale = 0.75
    
    vLine = Split(lbCables.List(iIndex, 0), ": ")
    strSegment = tbNumber.Value & ": " & vLine(0)
    strHO1 = vLine(1)
    
    vLine = Split(lbCables.List(iIndex, 1), " + ")
    'vCounts = Split(vLine(0), "] ")
    vTemp = Split(vLine(0), ": ")
    strCounts = vTemp(0) & ": " & vTemp(1)
    
    If UBound(vLine) > 0 Then
        For i = 1 To UBound(vLine)
            vTemp = Split(vLine(i), ": ")
            strCounts = strCounts & "\P" & vTemp(0) & ": " & vTemp(1)
        Next i
    End If
    
    'MsgBox strSegment & vbCr & strHO1 & vbCr & strCounts
    
        
    Set objCO = ThisDrawing.ModelSpace.InsertBlock(vBlockCoords, "Callout", dScale, dScale, dScale, 0)
    
    objCO.Layer = "Integrity Proposed"
    attItem = objCO.GetAttributes
    attItem(0).TextString = strSegment
    attItem(1).TextString = strHO1
    attItem(2).TextString = strCounts
    
    If cbPlacement.Value = "Leader" Then
        If lwpCoords(2) < lwpCoords(0) Then
            vBlockCoords(0) = vBlockCoords(0) - (75 * dScale)
            objCO.InsertionPoint = vBlockCoords
        End If
    End If
    objCO.Update
    
    Me.show
End Sub

Private Sub lbSplices_DblClick(ByVal Cancel As MSForms.ReturnBoolean)
    If lbSplices.ListCount < 1 Then Exit Sub
    
    Dim objCO As AcadBlockReference
    'Dim objEntity As AcadEntity
    Dim returnPnt As Variant
    Dim vBlockCoords(0 To 2) As Double
    Dim lwpCoords(0 To 3) As Double
    Dim dPrevious(0 To 2) As Double
    Dim dOrigin(0 To 2) As Double
    Dim dScale As Double
    Dim lineObj As AcadLWPolyline
    'Dim objCircle As AcadCircle
    'Dim objCircle2 As AcadCircle
    'Dim objText As AcadText
    'Dim objText2 As AcadText
    Dim vLine, vCounts, vTemp As Variant
    Dim strLetter, strCounts, strHO1 As String
    Dim strSegment As String
    Dim iHO1 As Integer
    
  'On Error Resume Next
    dOrigin(0) = 0
    dOrigin(1) = 0
    dOrigin(2) = 0
    
    Me.Hide
    'returnPnt = ThisDrawing.Utility.GetPoint(, "Select Point: ")
    returnPnt = objBlock.InsertionPoint
    
    lwpCoords(0) = returnPnt(0)
    lwpCoords(1) = returnPnt(1)
    dPrevious(0) = returnPnt(0)
    dPrevious(1) = returnPnt(1)
    dPrevious(2) = 0#
    
    returnPnt = ThisDrawing.Utility.GetPoint(dPrevious, "Select Point: ")
    vBlockCoords(0) = returnPnt(0)
    vBlockCoords(1) = returnPnt(1)
    vBlockCoords(2) = returnPnt(2)
    lwpCoords(2) = vBlockCoords(0)
    lwpCoords(3) = vBlockCoords(1)
    
    'If cbPlacement.Value = "Leader" Then
        Set lineObj = ThisDrawing.ModelSpace.AddLightWeightPolyline(lwpCoords)
        lineObj.Layer = "Integrity Proposed"
        lineObj.Update
    'Else
        'Set objCircle = ThisDrawing.ModelSpace.AddCircle(dPrevious, 8)
        'objCircle.Layer = "Integrity Proposed"
        'objCircle.Update
        'Set objCircle2 = ThisDrawing.ModelSpace.AddCircle(returnPnt, 8)
        'objCircle2.Layer = "Integrity Proposed"
        'objCircle2.Update
        
        'strLetter = UCase(ThisDrawing.Utility.GetString(0, "Enter Callout Letter:"))
        'Set objText = ThisDrawing.ModelSpace.AddText(strLetter, dOrigin, 8)
        'Set objText2 = ThisDrawing.ModelSpace.AddText(strLetter, dOrigin, 8)
        'objText.Layer = "Integrity Proposed"
        'objText.Alignment = acAlignmentMiddle
        'objText.TextAlignmentPoint = dPrevious
        'objText2.Layer = "Integrity Proposed"
        'objText2.Alignment = acAlignmentMiddle
        'objText2.TextAlignmentPoint = vBlockCoords
        'objText.Update
        'objText2.Update
        
        'vBlockCoords(0) = vBlockCoords(0) + 8
        'lwpCoords(0) = 0
    'End If
    
    dScale = CDbl(cbScale.Value) / 100
    If dScale = 0 Then dScale = 0.75
    
    vLine = Split(lbSplices.List(lbSplices.ListIndex), "] ")
    strSegment = tbNumber.Value & ": " & Replace(vLine(0), "[", "")
    
    vLine = Split(lbSplices.List(lbSplices.ListIndex), " + ")
    vCounts = Split(vLine(0), "] ")
    vTemp = Split(vCounts(1), ": ")
    strCounts = vTemp(0) & ": " & vTemp(1)
    
    vCounts = Split(vTemp(1), "-")
    
    If UBound(vCounts) = 0 Then
        iHO1 = 1
    Else
        iHO1 = CInt(vCounts(1)) - CInt(vCounts(0)) + 1
    End If
    
    If UBound(vLine) > 0 Then
        For i = 1 To UBound(vCounts)
            vTemp = Split(vLine(i), ": ")
            strCounts = strCounts & "\P" & vTemp(0) & ": " & vTemp(1)
            
            vCounts = Split(vTemp(1), "-")
    
            If UBound(vCounts) = 0 Then
                iHO1 = iHO1 + 1
            Else
                iHO1 = iHO1 + CInt(vCounts(1)) - CInt(vCounts(0)) + 1
            End If
        Next i
    End If
    
    strHO1 = "+HO1B=" & iHO1
    
    'MsgBox strSegment & vbCr & strHO1 & vbCr & strCounts
    
        
    Set objCO = ThisDrawing.ModelSpace.InsertBlock(vBlockCoords, "Callout", dScale, dScale, dScale, 0)
    
    objCO.Layer = "Integrity Proposed"
    attItem = objCO.GetAttributes
    attItem(0).TextString = strSegment
    attItem(1).TextString = strHO1
    attItem(2).TextString = strCounts
    
    If lwpCoords(2) < lwpCoords(0) Then
        vBlockCoords(0) = vBlockCoords(0) - (75 * dScale)
        objCO.InsertionPoint = vBlockCoords
    End If
    objCO.Update
    
    Me.show
End Sub

Private Sub UserForm_Initialize()
    lbUnits.ColumnCount = 3
    lbUnits.ColumnWidths = "96;36;48"
    
    lbCables.ColumnCount = 2
    lbCables.ColumnWidths = "96;285"
    
    cbStatus.AddItem "EXISTING"
    cbStatus.AddItem "PROPOSED"
    cbStatus.AddItem "FUTURE"
    
    cbScale.AddItem "50"
    cbScale.AddItem "75"
    cbScale.AddItem "100"
    cbScale.Value = "100"
    
    cbType.AddItem "BDO3"
    cbType.AddItem "BDO5"
    cbType.AddItem "BDO7"
    cbType.AddItem "BDO(OP10106)"
    cbType.AddItem "BDO(OP12126)"
    cbType.AddItem "BHF(30X48X36)T"
    cbType.AddItem "UHF(17X30X18)"
    cbType.AddItem "UHF(24X36X24)"
    cbType.AddItem "UHF(30X48X24)T"
    cbType.AddItem "UHF(30X48X36)"
    cbType.AddItem "UHF(48X96X48)TIER22"
    cbType.AddItem "FP"
    cbType.AddItem "BUDI BOX"
    cbType.AddItem "FIBER PANEL"
    'cbType.AddItem "FP (Future)"
    
    cbGround.AddItem "TGB"
    cbGround.AddItem "MGN"
    cbGround.AddItem "MGNV"
    cbGround.AddItem "OTHER"
    cbGround.AddItem "NO GRD"
    'cbGround.Value = "NONE"
    
    cbPlacement.AddItem "Leader"
    cbPlacement.AddItem "Away"
    cbPlacement.Value = "Leader"
    
    strRoute = "01A/"
    iNumber = 1
    
    cbGetBlock.SetFocus
End Sub

Private Function TN83FtoLL(dNorth As Double, dEast As Double)
    Dim dLat, dLong, dDLat As Double
    Dim dDiffE, dEast0 As Double
    Dim dDiffN, dNorth0 As Double
    Dim dR, dCAR, dCA, dU, dK As Double
    Dim LL(2) As Double
    
    dEast = dEast * 0.3048006096
    dNorth = dNorth * 0.3048006096
    
    dDiffE = dEast - 600000
    dDiffN = dNorth - 166504.1691
    
    dR = 8842127.1422 - dDiffN
    dCAR = Atn(dDiffE / dR)
    dCA = dCAR * 180 / 3.14159265359
    dLong = -86 + dCA / 0.585439726459
    
    dU = dDiffN - dDiffE * Tan(dCAR / 2)
    dDLat = dU * (0.00000901305249 + dU * (-6.77268E-15 + dU * (-3.72351E-20 + dU * -9.2828E-28)))
    dLat = 35.8340607459 + dDLat
    
    dK = 0.999948401424 + (1.23188E-14 * dU * dU) + (4.54E-22 * dU * dU * dU)
    
    LL(0) = dLat
    LL(1) = dLong
    LL(2) = dK
    
    TN83FtoLL = LL
End Function

Attribute VB_Name = "PlaceCableCCounts"
Attribute VB_Base = "0{23CFCD51-AEAB-407E-AA15-83ED037F7F53}{C3C5ED6D-7B06-40F1-B200-25FA9E442F42}"
Attribute VB_GlobalNameSpace = False
Attribute VB_Creatable = False
Attribute VB_PredeclaredId = True
Attribute VB_Exposed = False
Attribute VB_TemplateDerived = False
Attribute VB_Customizable = False
Private Sub cbAddUpdate_Click()
    Dim iIndex As Integer
    
    If cbAddUpdate.Caption = "Update" Then
        iIndex = lbCounts.ListIndex
        lbCounts.List(iIndex, 0) = tbName.Value
        lbCounts.List(iIndex, 1) = tbCounts.Value
        lbCounts.List(iIndex, 2) = tbSource.Value
        lbCounts.List(iIndex, 3) = cbStatus.Value
        
        GoTo Exit_Sub
    End If
    
    lbCounts.AddItem tbName.Value
    iIndex = lbCounts.ListCount - 1
    lbCounts.List(iIndex, 1) = tbCounts.Value
    lbCounts.List(iIndex, 2) = tbSource.Value
    lbCounts.List(iIndex, 3) = cbStatus.Value
    
Exit_Sub:
    cbAddUpdate.Caption = "Add New Line"
End Sub

Private Sub cbCancel_Click()
    Me.Hide
End Sub

Private Sub cbGetLine_Click()
    If lbCounts.ListCount < 1 Then Exit Sub
    
    Dim vCounts As Variant
    Dim iFrom, iTo As Integer
    
    For i = 0 To lbCounts.ListCount - 1
        If lbCounts.Selected(i) = True Then
            vCounts = Split(lbCounts.List(i, 1), "-")
            If UBound(vCounts) = 0 Then Exit Sub
            
            tbFromFirst.Value = vCounts(0)
            tbToLast.Value = vCounts(1)
        End If
    Next i
    
    cbSplit.Enabled = True
    tbTo.SetFocus
End Sub

Private Sub cbQuit_Click()
    Dim strLine, strTemp As String
    
    strLine = ""
    
    For i = 0 To lbCounts.ListCount - 1
        strTemp = lbCounts.List(i, 0) & ":" & vbTab & lbCounts.List(i, 1) & ":" & vbTab & lbCounts.List(i, 2)
        'If lbCounts.List(i, 3) = "Old" Then strTemp = "(" & strTemp & ")"
        
        If strLine = "" Then
            strLine = strTemp
        Else
            strLine = strLine & vbCr & strTemp
        End If
    Next i
    
    PlaceCountCallouts.tbCableCounts.Value = strLine
    
    Me.Hide
End Sub

Private Sub cbSplit_Click()
    If tbTo.Value = "" Then
        tbFrom.Value = ""
        Exit Sub
    End If
    
    Dim iCurrent, iFrom, iTo As Integer
    
    iFrom = CInt(tbFromFirst.Value)
    iTo = CInt(tbToLast.Value)
    iCurrent = CInt(tbTo.Value)
    
    If iCurrent < iFrom + 1 Then Exit Sub
    If iCurrent > iTo - 1 Then Exit Sub
    
    Dim iIndex, iNext As Integer
    Dim strName, strLine, strSource As String
    
    iNext = iCurrent + 1
    iIndex = lbCounts.ListIndex
    lbCounts.List(iIndex, 1) = iFrom & "-" & iCurrent
    
    iIndex = iIndex + 1
    lbCounts.AddItem lbCounts.List(iIndex - 1, 0), iIndex
    lbCounts.List(iIndex, 1) = iNext & "-" & iTo
    lbCounts.List(iIndex, 2) = lbCounts.List(iIndex - 1, 2)
    lbCounts.List(iIndex, 3) = lbCounts.List(iIndex - 1, 3)
    
    tbFromFirst.Value = ""
    tbTo.Value = ""
    tbFrom.Value = ""
    tbToLast.Value = ""
End Sub

Private Sub lbCounts_DblClick(ByVal Cancel As MSForms.ReturnBoolean)
    Dim iIndex As Integer
    
    iIndex = lbCounts.ListIndex
    
    tbName.Value = lbCounts.List(iIndex, 0)
    tbCounts.Value = lbCounts.List(iIndex, 1)
    tbSource.Value = lbCounts.List(iIndex, 2)
    cbStatus.Value = lbCounts.List(iIndex, 3)
    
    cbAddUpdate.Caption = "Update"
End Sub

Private Sub lbCounts_KeyDown(ByVal KeyCode As MSForms.ReturnInteger, ByVal Shift As Integer)
    If lbCounts.ListCount < 1 Then Exit Sub
    
    Dim str1, str2, str3, str4 As String
    Dim i, i2 As Integer
    
    Select Case KeyCode
        Case vbKeyDown
            If lbCounts.ListIndex = (lbCounts.ListCount - 1) Then Exit Sub
            i = lbCounts.ListIndex
            i2 = i + 1
            
            str1 = lbCounts.List(i, 0)
            str2 = lbCounts.List(i, 1)
            str3 = lbCounts.List(i, 2)
            str4 = lbCounts.List(i, 3)
            
            
            lbCounts.List(i, 0) = lbCounts.List(i2, 0)
            lbCounts.List(i, 1) = lbCounts.List(i2, 1)
            lbCounts.List(i, 2) = lbCounts.List(i2, 2)
            lbCounts.List(i, 3) = lbCounts.List(i2, 3)
            
            lbCounts.List(i2, 0) = str1
            lbCounts.List(i2, 1) = str2
            lbCounts.List(i2, 2) = str3
            lbCounts.List(i2, 3) = str4
            'lbUnits.ListIndex = i2
        Case vbKeyUp
            If lbCounts.ListIndex = 0 Then Exit Sub
            i = lbCounts.ListIndex
            i2 = i - 1
            
            str1 = lbCounts.List(i, 0)
            str2 = lbCounts.List(i, 1)
            str3 = lbCounts.List(i, 2)
            str4 = lbCounts.List(i, 3)
            
            lbCounts.List(i, 0) = lbCounts.List(i2, 0)
            lbCounts.List(i, 1) = lbCounts.List(i2, 1)
            lbCounts.List(i, 2) = lbCounts.List(i2, 2)
            lbCounts.List(i, 3) = lbCounts.List(i2, 3)
            
            lbCounts.List(i2, 0) = str1
            lbCounts.List(i2, 1) = str2
            lbCounts.List(i2, 2) = str3
            lbCounts.List(i2, 3) = str4
            'lbUnits.ListIndex = i2
        Case vbKeyDelete
            lbCounts.RemoveItem (lbCounts.ListIndex)
    End Select
End Sub

Private Sub tbTo_Change()
    If tbTo.Value = "" Then
        tbFrom.Value = ""
        Exit Sub
    End If
    
    Dim iCurrent, iFrom, iTo As Integer
    
    iFrom = CInt(tbFromFirst.Value)
    iTo = CInt(tbToLast.Value)
    iCurrent = CInt(tbTo.Value)
    
    If iCurrent < iFrom + 1 Then Exit Sub
    If iCurrent > iTo - 1 Then Exit Sub
    
    tbFrom.Value = iCurrent + 1
End Sub

Private Sub UserForm_Initialize()
    cbStatus.AddItem "Current"
    cbStatus.AddItem "Old"
    cbStatus.AddItem "New"
    
    lbCounts.ColumnCount = 4
    lbCounts.ColumnWidths = "96;48;96;38"
    
    Dim vCount, vItem As Variant
    Dim strCounts As String
    
    strCounts = PlaceCountCallouts.tbCableCounts.Value
    strCounts = Replace(strCounts, vbLf, "")
    strCounts = Replace(strCounts, vbTab, " ")
    vCount = Split(strCounts, vbCr)
    
    For i = 0 To UBound(vCount)
        If Not vCount(i) = "" Then
            vItem = Split(vCount(i), ": ")
            lbCounts.AddItem vItem(0)
            lbCounts.List(lbCounts.ListCount - 1, 1) = vItem(1)
            lbCounts.List(lbCounts.ListCount - 1, 2) = vItem(2)
            If InStr(vCount(i), "(") > 0 Then
                lbCounts.List(lbCounts.ListCount - 1, 3) = "Old"
            Else
                lbCounts.List(lbCounts.ListCount - 1, 3) = "Current"
            End If
        End If
    Next i
End Sub

Attribute VB_Name = "PlaceCountCallouts"
Attribute VB_Base = "0{65D0B557-D223-407B-8FC3-F43EB76EB19B}{CED0CA00-218F-48BF-9419-79CF05FFBDD0}"
Attribute VB_GlobalNameSpace = False
Attribute VB_Creatable = False
Attribute VB_PredeclaredId = True
Attribute VB_Exposed = False
Attribute VB_TemplateDerived = False
Attribute VB_Customizable = False
Dim objStructure As AcadBlockReference
Dim strMainCC, strMainSC As String

Private Sub cbBreakLines_Click()
    Me.Hide
    
    ThisDrawing.SendCommand "_break" & vbCr
    Me.show
End Sub

Private Sub cbConsolidateCable_Click()
    If tbCableCounts.Value = "" Then Exit Sub
    
    Dim vLine, vItem, vCounts As Variant
    Dim strLine As String
    Dim strPrevious, strCurrent, strRef As String
    Dim iCurrent As Integer
    Dim iStart, iEnd As Integer
    Dim iTempS, iTempE As Integer
    
    iCurrent = 0
    strRef = ""
    
    strLine = Replace(tbCableCounts.Value, vbLf, "")
    strLine = Replace(strLine, vbTab, " ")
    vLine = Split(strLine, vbCr)
    
    vItem = Split(vLine(0), ": ")
    If UBound(vItem) > 1 Then
        vCounts = Split(vItem(1), "-")
        iStart = CInt(vCounts(0))
        If UBound(vCounts) = 0 Then
            iEnd = iStart
        Else
            iEnd = CInt(vCounts(1))
        End If
        strPrevious = vItem(0)
        strRef = vItem(2)
    'Else
        '
    End If
    
    If UBound(vLine) > 0 Then
        For i = 1 To UBound(vLine)
            If vLine(i) = "" Then GoTo Next_line
            
            vItem = Split(vLine(i), ": ")
            vCounts = Split(vItem(1), "-")
            iTempS = CInt(vCounts(0))
            If UBound(vCounts) = 0 Then
                iTempE = iTempS
            Else
                iTempE = CInt(vCounts(1))
            End If
            strCurrent = vItem(0)
            
            If strCurrent = strPrevious Then
                If iTempS = iEnd + 1 Then
                    iEnd = iTempE
                    vLine(iCurrent) = strPrevious & ": " & iStart & "-" & iEnd & ": " & strRef
                    vLine(i) = ""
                Else
                    iStart = iTempS
                    iEnd = iTempE
                    strRef = vItem(2)
                End If
            Else
                iCurrent = i
                iStart = iTempS
                iEnd = iTempE
                strPrevious = strCurrent
                strRef = vItem(2)
            End If
Next_line:
        Next i
    End If
    
    strLine = ""
    For i = 0 To UBound(vLine)
        If Not vLine(i) = "" Then
            If strLine = "" Then
                strLine = vLine(i)
            Else
                strLine = strLine & vbCr & vLine(i)
            End If
        End If
    Next i
    
    strLine = Replace(strLine, " ", vbTab)
    tbCableCounts.Value = strLine
End Sub

Private Sub cbGet_Click()
    Dim objEntity As AcadEntity
    Dim vAttList, vReturnPnt As Variant
    Dim vLine, vItem, vCounts As Variant
    Dim vCable, vSplice As Variant
    Dim strText, strBack As String
    Dim strCables, strSplices, strTemp As String
    Dim result, iAtt As Integer
    Dim bTest As Boolean
    
    bTest = False
    
    If Not tbCableCounts.Value = strMainCC Then bTest = True
    If Not tbClosure.Value = strMainSC Then bTest = True
    If strMainCC = "empty" Then
        If strMainSC = "empty" Then bTest = False
    End If
    If bTest = True Then
        result = MsgBox("Save count changes to Block?", vbYesNo, "Save Changes")
        If result = vbYes Then Call UpdateBlock(CStr(tbPosition.Value))
    End If
    
    Me.Hide
    
    On Error Resume Next
    
    Err = 0
    ThisDrawing.Utility.GetEntity objEntity, vReturnPnt, vbCr & "Select Structure:"
    If Not Err = 0 Then
        MsgBox Err.Description
        GoTo Exit_Sub
    End If
    
    If Not TypeOf objEntity Is AcadBlockReference Then
        MsgBox objEntity.ObjectName
        GoTo Exit_Sub
    End If
    
    Set objStructure = objEntity
    
    Select Case objStructure.Name
        Case "sPole"
            iAtt = 25
            tbType.Value = "POLE"
        Case "sPed"
            iAtt = 5
            tbType.Value = "PED"
        Case "sHH"
            iAtt = 5
            tbType.Value = "HH"
        Case "sMH"
            iAtt = 5
            tbType.Value = "MH"
        Case "sPanel"
            iAtt = 5
            tbType.Value = "PANEL"
        Case "sFP"
            iAtt = 5
            tbType.Value = "FP"
        Case Else
            GoTo Exit_Sub
    End Select
    
    cbScale.Value = GetScale(objStructure.InsertionPoint) * 100
    
    vAttList = objStructure.GetAttributes
    
    'MsgBox vAttList(iAtt).TextString
    strCables = Replace(vAttList(iAtt).TextString, vbLf, "")
    strCables = Replace(strCables, "\P", vbCr)
    vCable = Split(strCables, vbCr)
    
    cbPosition.Clear
    For i = 0 To UBound(vCable)
        vCounts = Split(vCable(i), ": ")
        cbPosition.AddItem vCounts(0)
    Next i
    cbPosition.Value = cbPosition.List(0)
        
    Call GetPositionData(cbPosition.Value)
    
    If tbNumber.Value = "" Then tbNumber.Value = vAttList(0).TextString
        
Exit_Sub:
    
    Me.show
End Sub

Private Sub cbGetCCallout_Click()
    Dim objEntity As AcadEntity
    Dim objBlock As AcadBlockReference
    Dim vAttList, vReturnPnt As Variant
    
    Dim vLine As Variant
    Dim strLine, strSource As String
    Dim strTemp As String
    
    Me.Hide
    
    On Error Resume Next
    
    ThisDrawing.Utility.GetEntity objEntity, vReturnPnt, vbCr & "Select Callout:"
    If Not Err = 0 Then GoTo Exit_Sub
    
    If Not TypeOf objEntity Is AcadBlockReference Then GoTo Exit_Sub
    
    Set objBlock = objEntity
    
    Select Case objBlock.Name
        Case "Callout"
            vAttList = objBlock.GetAttributes
            
            strLine = UCase(vAttList(2).TextString)
            If strLine = "" Then GoTo Exit_Sub
            
            tbCableType.Value = vAttList(1).TextString
            vLine = Split(vAttList(0).TextString, ": ")
            tbPosition.Value = vLine(1)
        Case "CableCounts"
            vAttList = objBlock.GetAttributes
            
            strLine = UCase(vAttList(0).TextString)
            If strLine = "" Then GoTo Exit_Sub
            
            tbCableType.Value = vAttList(1).TextString
            tbPosition.Value = "A1"
        Case Else
            GoTo Exit_Sub
    End Select
    
    strLine = Replace(strLine, "\P", vbCr)
    strLine = Replace(strLine, ") ", ")" & vbCr)
    strLine = Replace(strLine, ": ", ":" & vbTab)
    
    'GoTo Skip_This
    
    Err = 0
    ThisDrawing.Utility.GetEntity objEntity, vReturnPnt, vbCr & "Select Source Block:"
    If Err = 0 Then
        If Not TypeOf objEntity Is AcadBlockReference Then
            strSource = "UNKNOWN"
            GoTo No_Error
        End If
        
        Set objBlock = objEntity
        
        Select Case objBlock.Name
            Case "sPole", "sPed", "sHH", "sPanel", "sMH"
                vAttList = objBlock.GetAttributes
                strSource = vAttList(0).TextString
                GoTo No_Error
            Case Else
                strSource = "UNKNOWN"
                GoTo No_Error
        End Select
    End If
    
    Err = 0
    strSource = "UNKNOWN"
    
No_Error:
    
    vLine = Split(strLine, vbCr)
    For i = 0 To UBound(vLine)
        strTemp = Replace(vLine(i), ")", "")
        strTemp = strTemp & ":" & vbTab & strSource
        
        If Left(strTemp, 1) = "(" Then strTemp = strTemp & ")"
        
        vLine(i) = strTemp
    Next i
    
    strLine = vLine(0)
    If UBound(vLine) > 0 Then
        For i = 1 To UBound(vLine)
            strLine = strLine & vbCr & vLine(i)
        Next i
    End If
    
Skip_This:
    
    tbCableCounts.Value = strLine
    
Exit_Sub:
    Me.show
End Sub

Private Sub cbPan_Click()
    Dim objEntity As AcadEntity
    Dim vReturn As Variant
    
    On Error Resume Next
    
    Me.Hide
    
    ThisDrawing.Utility.GetEntity objEntity, vReturn, vbCr & "Right Click to Exit:"
    
    Me.show
End Sub

Private Sub cbPlaceCblCallout_Click()
    If tbCableCounts.Value = "" Then Exit Sub
    
    Dim objCallout As AcadBlockReference
    Dim returnPnt As Variant
    Dim vBlockCoords(0 To 2) As Double
    Dim lwpCoords(0 To 3) As Double
    Dim dPrevious(0 To 2) As Double
    Dim dOrigin(0 To 2) As Double
    Dim dScale As Double
    Dim lineObj As AcadLWPolyline
    Dim objCircle As AcadCircle
    Dim objCircle2 As AcadCircle
    Dim objText As AcadText
    Dim objText2 As AcadText
    'Dim str1, str2, str3, strLetter As String
    'Dim lowNum, highNum, strArray() As String
    'Dim mainStatus, tempStatus As String
    Dim vLine, vItem, vTemp As Variant
    
    Dim strAtt0, strAtt1, strAtt2 As String
    Dim strLayer As String
    
    'vLine = Split(lbCables.List(iIndex, 0), ": ")
    strAtt0 = tbNumber.Value & ": " & tbPosition.Value
    strAtt1 = tbCableType.Value
    strAtt2 = Replace(tbCableCounts.Value, vbCr, "\P")
    strAtt2 = Replace(strAtt2, vbLf, "")
    strAtt2 = Replace(strAtt2, vbTab, " ")
    
    vLine = Split(strAtt2, "\P")
    
    For i = 0 To UBound(vLine)
        If vLine(i) = "" Then GoTo Next_line
        
        vItem = Split(vLine(i), ": ")
        vTemp = Split(vItem(1), "-")
        If UBound(vTemp) > 0 Then
            If vTemp(0) = vTemp(1) Then vItem(1) = vTemp(0)
        End If
        vLine(i) = vItem(0) & ": " & vItem(1)
        If Left(vLine(i), 1) = "(" Then vLine(i) = vLine(i) & ")"
Next_line:
    Next i
    
    Dim strTemp As String
    
    strTemp = vLine(0)
    For i = 1 To UBound(vLine)
        strTemp = strTemp & vbCr & vLine(i)
    Next i
    
    'MsgBox strTemp
    
    vLine = Split(strTemp, vbCr)
    strAtt2 = vLine(0)
    If Right(strAtt2, 1) = ")" Then strAtt2 = strAtt2 & " "
    
    If UBound(vLine) > 0 Then
        For i = 1 To UBound(vLine)
            
            If Right(strAtt2, 2) = ") " Then
                strAtt2 = strAtt2 & vLine(i)
            Else
                strAtt2 = strAtt2 & "\P" & vLine(i)
            End If
            
            If Right(strAtt2, 1) = ")" Then strAtt2 = strAtt2 & " "
        Next i
    End If
    
    If Left(tbCableType.Value, 2) = "CO" Then
        strLayer = "Integrity Proposed-Aerial"
    Else
        strLayer = "Integrity Proposed-Buried"
    End If
    
  'On Error Resume Next
    dOrigin(0) = 0
    dOrigin(1) = 0
    dOrigin(2) = 0
    
    Me.Hide
    
    returnPnt = ThisDrawing.Utility.GetPoint(, "Select Point: ")
    lwpCoords(0) = returnPnt(0)
    lwpCoords(1) = returnPnt(1)
    dPrevious(0) = returnPnt(0)
    dPrevious(1) = returnPnt(1)
    dPrevious(2) = 0#
    
    returnPnt = ThisDrawing.Utility.GetPoint(dPrevious, "Select Point: ")
    vBlockCoords(0) = returnPnt(0)
    vBlockCoords(1) = returnPnt(1)
    vBlockCoords(2) = returnPnt(2)
    lwpCoords(2) = vBlockCoords(0)
    lwpCoords(3) = vBlockCoords(1)
    
    dScale = CDbl(cbScale.Value) / 100
    
    If cbPlacement.Value = "Leader" Then
        Set lineObj = ThisDrawing.ModelSpace.AddLightWeightPolyline(lwpCoords)
        lineObj.Layer = strLayer
        lineObj.Update
    Else
        Set objCircle = ThisDrawing.ModelSpace.AddCircle(dPrevious, 8 * dScale)
        objCircle.Layer = strLayer
        objCircle.Update
        Set objCircle2 = ThisDrawing.ModelSpace.AddCircle(returnPnt, 8 * dScale)
        objCircle2.Layer = strLayer
        objCircle2.Update
        
        strLetter = UCase(ThisDrawing.Utility.GetString(0, "Enter Callout Letter:"))
        Set objText = ThisDrawing.ModelSpace.AddText(strLetter, dOrigin, 8 * dScale)
        Set objText2 = ThisDrawing.ModelSpace.AddText(strLetter, dOrigin, 8 * dScale)
        objText.Layer = strLayer
        objText.Alignment = acAlignmentMiddle
        objText.TextAlignmentPoint = dPrevious
        objText2.Layer = strLayer
        objText2.Alignment = acAlignmentMiddle
        objText2.TextAlignmentPoint = vBlockCoords
        objText.Update
        objText2.Update
        
        vBlockCoords(0) = vBlockCoords(0) + 8 * dScale
        lwpCoords(0) = 0
    End If
    
    'dScale = 0.75
        
    Set objCallout = ThisDrawing.ModelSpace.InsertBlock(vBlockCoords, "Callout", dScale, dScale, dScale, 0)
    attItem = objCallout.GetAttributes
    
    attItem(0).TextString = strAtt0
    attItem(1).TextString = strAtt1
    attItem(2).TextString = strAtt2
    
    objCallout.Layer = strLayer
    
    If lwpCoords(2) < lwpCoords(0) Then
        vBlockCoords(0) = vBlockCoords(0) - (75 * dScale)
        objCallout.InsertionPoint = vBlockCoords
    End If
    objCallout.Update
    
    Me.show
End Sub

Private Sub cbPlaceClosureCallout_Click()
    If tbClosure.Value = "" Then Exit Sub
    
    Dim objCO As AcadBlockReference
    Dim returnPnt, vAttList As Variant
    Dim vBlockCoords(0 To 2) As Double
    Dim lwpCoords(0 To 3) As Double
    Dim dPrevious(0 To 2) As Double
    Dim dOrigin(0 To 2) As Double
    Dim dScale As Double
    Dim lineObj As AcadLWPolyline
    Dim vLine, vCounts, vTemp, vItem As Variant
    Dim strCounts, strHO1 As String
    Dim strSegment As String
    Dim iHO1 As Integer
    
  'On Error Resume Next
    Select Case Left(tbCableType.Value, 2)
        Case "CO"
            strHO1 = "+HO1A="
        Case Else
            strHO1 = "+HO1B="
    End Select
    
    dOrigin(0) = 0
    dOrigin(1) = 0
    dOrigin(2) = 0
    
    Me.Hide
    returnPnt = objStructure.InsertionPoint
    
    lwpCoords(0) = returnPnt(0)
    lwpCoords(1) = returnPnt(1)
    dPrevious(0) = returnPnt(0)
    dPrevious(1) = returnPnt(1)
    dPrevious(2) = 0#
    
    returnPnt = ThisDrawing.Utility.GetPoint(dPrevious, "Select Point: ")
    vBlockCoords(0) = returnPnt(0)
    vBlockCoords(1) = returnPnt(1)
    vBlockCoords(2) = returnPnt(2)
    lwpCoords(2) = vBlockCoords(0)
    lwpCoords(3) = vBlockCoords(1)
    
    Set lineObj = ThisDrawing.ModelSpace.AddLightWeightPolyline(lwpCoords)
    lineObj.Layer = "Integrity Proposed"
    lineObj.Update
    
    'dScale = 0.75
    dScale = CDbl(cbScale.Value) / 100
    
    strSegment = tbNumber.Value & ": " & tbPosition.Value
    
    strCounts = Replace(tbClosure.Value, vbLf, "")
    strCounts = Replace(strCounts, vbTab, " ")
    vLine = Split(strCounts, vbCr)
    vTemp = Split(vLine(0), ": ")
    vItem = Split(vTemp(1), "-")
    If UBound(vItem) > 0 Then
        If vItem(0) = vItem(1) Then vTemp(1) = vItem(0)
    End If
    strCounts = vTemp(0) & ": " & vTemp(1)
    
    If InStr(vTemp(1), " FUTURE") < 1 Then
        vCounts = Split(vTemp(1), "-")
    
        If UBound(vCounts) = 0 Then
            iHO1 = 1
        Else
            iHO1 = CInt(vCounts(1)) - CInt(vCounts(0)) + 1
        End If
    End If
    
    If UBound(vLine) > 0 Then
        For i = 1 To UBound(vLine)
            If vLine(i) = "" Then GoTo Next_line
            
            vTemp = Split(vLine(i), ": ")
            vItem = Split(vTemp(1), "-")
            If UBound(vItem) > 0 Then
                If vItem(0) = vItem(1) Then vTemp(1) = vItem(0)
            End If
            strCounts = strCounts & "\P" & vTemp(0) & ": " & vTemp(1)
    
            If InStr(vTemp(1), " FUTURE") < 1 Then
                vCounts = Split(vTemp(1), "-")
    
                If UBound(vCounts) = 0 Then
                    iHO1 = iHO1 + 1
                Else
                    iHO1 = iHO1 + CInt(vCounts(1)) - CInt(vCounts(0)) + 1
                End If
            End If
            
Next_line:
        Next i
    End If
    
    strHO1 = strHO1 & iHO1
        
    Set objCO = ThisDrawing.ModelSpace.InsertBlock(vBlockCoords, "Callout", dScale, dScale, dScale, 0)
    
    objCO.Layer = "Integrity Proposed"
    vAttItem = objCO.GetAttributes
    vAttItem(0).TextString = strSegment
    vAttItem(1).TextString = strHO1
    vAttItem(2).TextString = strCounts
    
    If lwpCoords(2) < lwpCoords(0) Then
        vBlockCoords(0) = vBlockCoords(0) - (75 * dScale)
        objCO.InsertionPoint = vBlockCoords
    End If
    objCO.Update
    
    Me.show
End Sub

Private Sub cbQuit_Click()
    Me.Hide
End Sub

Private Sub SortWL()
    Dim strText As String
    Dim vLine, vB, vB1 As Variant
    Dim iCount As Integer
    Dim strAtt As String
    
    strText = Replace(tbWL.Value, vbLf, "")
    vLine = Split(strText, vbCr)
    iCount = UBound(vLine)
    
    If iCount < 1 Then Exit Sub
    
    On Error Resume Next
    
    For a = iCount To 0 Step -1
        For b = 0 To a - 1
            'vB = Split(vLine(b), " ")
            'vB1 = Split(vLine(b + 1), " ")
            vB = Split(vLine(b), vbTab)
            vB1 = Split(vLine(b + 1), vbTab)
            
                'MsgBox vB(1) & vbCr & vB1(1)
            
            If vB(0) > vB1(0) Then
            'If CInt(vB(0)) > CInt(vB1(0)) Then
                strAtt = vLine(b + 1)
                
                vLine(b + 1) = vLine(b)
                
                vLine(b) = strAtt
            End If
        Next b
    Next a
    
    strText = vLine(0)
    
    For i = 1 To UBound(vLine)
        If Not vLine(i) = vLine(i - 1) Then
            strText = strText & vbCr & vLine(i)
        End If
    Next i
    
    tbWL.Value = strText
End Sub

Private Sub cbSort_Click()
    Dim vLine, vItem, vCounts As Variant
    Dim vTemp, vItem1, vCounts1 As Variant
    Dim strLine As String
    Dim iFiber, iFiber1 As Integer
    Dim iCount As Integer
    
    strLine = Replace(tbClosure.Value, vbLf, "")
    strLine = Replace(strLine, vbTab, " ")
    vLine = Split(strLine, vbCr)
    
    iCount = UBound(vLine)
    If iCount = 0 Then Exit Sub
    
    For a = iCount To 0 Step -1
        For b = 0 To a - 1
            vItem = Split(vLine(b), ": ")
            vItem1 = Split(vLine(b + 1), ": ")
            If vItem(0) > vItem1(0) Then
                strLine = vLine(b + 1)
                vLine(b + 1) = vLine(b)
                vLine(b) = strLine
            ElseIf vItem(0) = vItem1(0) Then
                vCounts = Split(vItem(1), "-")
                vTemp = Split(vCounts(1), " ")
                iFiber = CInt(vTemp(0))
                vCounts1 = Split(vItem1(1), "-")
                vTemp = Split(vCounts1(1), " ")
                iFiber1 = CInt(vTemp(0))
                
                If iFiber > iFiber1 Then
                    strLine = vLine(b + 1)
                    vLine(b + 1) = vLine(b)
                    vLine(b) = strLine
                End If
            End If
        Next b
    Next a
    
    strLine = vLine(0)
    
    For i = 1 To iCount
        strLine = strLine & vbCr & vLine(i)
    Next i
    
    strLine = Replace(strLine, " ", vbTab)
    tbClosure.Value = strLine
End Sub

Private Sub cbSwitchPositions_Click()
    If cbPosition.Value = tbPosition.Value Then Exit Sub
    
    'tbCableCounts.Value = ""
    'tbClosure.Value = ""
    
    Call GetPositionData(cbPosition.Value)
End Sub

Private Sub cbTest_Click()
    Dim objEntity As AcadEntity
    Dim objBlock As AcadBlockReference
    Dim vAttList, vReturnPnt As Variant
    'Dim vLine As Variant
    
    Me.Hide
    
    On Error Resume Next
    
    ThisDrawing.Utility.GetEntity objEntity, vReturnPnt, vbCr & "Select Callout:"
    If Not Err = 0 Then GoTo Exit_Sub
    
    If Not TypeOf objEntity Is AcadBlockReference Then GoTo Exit_Sub
    
    Set objBlock = objEntity
    
    Select Case objBlock.Name
        Case "sPole", "sPed", "sHH"
        Case Else
            GoTo Exit_Sub
    End Select
    
    vAttList = objBlock.GetAttributes
    
    vAttList(0).Rotation = 0#
    objBlock.Update
Exit_Sub:
    Me.show
End Sub

Private Sub cbUpdate_Click()
    Call UpdateBlock(CStr(tbPosition.Value))
    
    For i = 0 To cbPosition.ListCount - 1
        If cbPosition.Value = tbPosition.Value Then GoTo Found_Position
    Next i
    
    cbPosition.AddItem tbPosition.Value
    cbPosition.Value = tbPosition.Value
    
Found_Position:
    
End Sub

Private Sub cbUpdateCblCallout_Click()
    Dim objSS As AcadSelectionSet
    Dim objBlock As AcadBlockReference
    Dim vAttList As Variant
    Dim filterType, filterValue As Variant
    Dim grpCode(0) As Integer
    Dim grpValue(0) As Variant
    Dim strSearch As String
    
    strSearch = tbNumber.Value & ": " & tbPosition.Value

    grpCode(0) = 2
    grpValue(0) = "Callout"
    filterType = grpCode
    filterValue = grpValue
    
  On Error Resume Next
    
    Set objSS = ThisDrawing.SelectionSets.Add("objSS")
    If Not Err = 0 Then
        Set objSS = ThisDrawing.SelectionSets.Item("objSS")
        Err = 0
    End If
    
    objSS.Select acSelectionSetAll, , , filterType, filterValue
    
    For Each objBlock In objSS
        vAttList = objBlock.GetAttributes
        
        If vAttList(0).TextString = strSearch Then
            If InStr(vAttList(1).TextString, "+HO1") < 1 Then GoTo Found_Callout
        End If
    Next objBlock
    
    MsgBox "No Callout found for structure."
    GoTo Exit_Sub
    
Found_Callout:
    
    Dim strAtt0, strAtt1, strAtt2 As String
    Dim vLine As Variant
    
    'strAtt0 = tbNumber.Value & ": " & tbPosition.Value
    strAtt1 = tbCableType.Value
    strAtt2 = Replace(tbCableCounts.Value, vbCr, "\P")
    strAtt2 = Replace(strAtt2, vbLf, "")
    strAtt2 = Replace(strAtt2, vbTab, " ")
    
    vLine = Split(strAtt2, "\P")
    
    For i = 0 To UBound(vLine)
        If vLine(i) = "" Then GoTo Next_line
        
        vItem = Split(vLine(i), ": ")
        vLine(i) = vItem(0) & ": " & vItem(1)
        If Left(vLine(i), 1) = "(" Then vLine(i) = vLine(i) & ")"
Next_line:
    Next i
    
    Dim strTemp As String
    
    strTemp = vLine(0)
    For i = 1 To UBound(vLine)
        strTemp = strTemp & vbCr & vLine(i)
    Next i
    
    'MsgBox strTemp
    
    vLine = Split(strTemp, vbCr)
    strAtt2 = vLine(0)
    If Right(strAtt2, 1) = ")" Then strAtt2 = strAtt2 & " "
    
    If UBound(vLine) > 0 Then
        For i = 1 To UBound(vLine)
            
            If Right(strAtt2, 2) = ") " Then
                strAtt2 = strAtt2 & vLine(i)
            Else
                strAtt2 = strAtt2 & "\P" & vLine(i)
            End If
            
            If Right(strAtt2, 1) = ")" Then strAtt2 = strAtt2 & " "
        Next i
    End If
    
    vAttList(1).TextString = strAtt1
    vAttList(2).TextString = strAtt2
    objBlock.Update
    
Exit_Sub:
    objSS.Clear
    objSS.Delete
End Sub

Private Sub cbUpdateClosureCallout_Click()
    Dim objSS As AcadSelectionSet
    Dim objBlock As AcadBlockReference
    Dim vAttList As Variant
    Dim filterType, filterValue As Variant
    Dim grpCode(0) As Integer
    Dim grpValue(0) As Variant
    Dim strSearch As String
    
    strSearch = tbNumber.Value & ": " & tbPosition.Value

    grpCode(0) = 2
    grpValue(0) = "Callout"
    filterType = grpCode
    filterValue = grpValue
    
  On Error Resume Next
    
    Set objSS = ThisDrawing.SelectionSets.Add("objSS")
    If Not Err = 0 Then
        Set objSS = ThisDrawing.SelectionSets.Item("objSS")
        Err = 0
    End If
    
    objSS.Select acSelectionSetAll, , , filterType, filterValue
    
    For Each objBlock In objSS
        vAttList = objBlock.GetAttributes
        
        If vAttList(0).TextString = strSearch Then
            If InStr(vAttList(1).TextString, "+HO1") > 0 Then GoTo Found_Callout
        End If
    Next objBlock
    
    MsgBox "No Callout found for structure."
    GoTo Exit_Sub
    
Found_Callout:
    
    Dim vLine, vTemp As Variant
    Dim strCounts, strHO1 As String
    Dim strSegment As String
    Dim iHO1 As Integer
    
    Select Case Left(tbCableType.Value, 2)
        Case "CO"
            strHO1 = "+HO1A="
        Case Else
            strHO1 = "+HO1B="
    End Select
    
    strCounts = Replace(tbClosure.Value, vbLf, "")
    strCounts = Replace(strCounts, vbTab, " ")
    vLine = Split(strCounts, vbCr)
    vTemp = Split(vLine(0), ": ")
    strCounts = vTemp(0) & ": " & vTemp(1)
    
    If InStr(vTemp(1), " FUTURE") < 1 Then
        vCounts = Split(vTemp(1), "-")
    
        If UBound(vCounts) = 0 Then
            iHO1 = 1
        Else
            iHO1 = CInt(vCounts(1)) - CInt(vCounts(0)) + 1
        End If
    End If
    
    If UBound(vLine) > 0 Then
        For i = 1 To UBound(vLine)
            If vLine(i) = "" Then GoTo Next_line
            
            vTemp = Split(vLine(i), ": ")
            strCounts = strCounts & "\P" & vTemp(0) & ": " & vTemp(1)
    
            If InStr(vTemp(1), " FUTURE") < 1 Then
                vCounts = Split(vTemp(1), "-")
    
                If UBound(vCounts) = 0 Then
                    iHO1 = iHO1 + 1
                Else
                    iHO1 = iHO1 + CInt(vCounts(1)) - CInt(vCounts(0)) + 1
                End If
            End If
            
Next_line:
        Next i
    End If
    
    strHO1 = strHO1 & iHO1
    
    vAttList(1).TextString = strHO1
    vAttList(2).TextString = strCounts
    
    objBlock.Update
    
Exit_Sub:
    objSS.Clear
    objSS.Delete
End Sub

Private Sub Label23_Click()
    If tbCableCounts.Value = "" Then Exit Sub
    
    Dim vLine, vItem, vCount As Variant
    Dim strLine As String
    Dim iStart, iEnd, iCount As Integer
    
    iCount = 0
    strLine = Replace(tbCableCounts.Value, vbLf, "")
    strLine = Replace(strLine, vbTab, " ")
    
    vLine = Split(strLine, vbCr)
    For i = 0 To UBound(vLine)
        If vLine(i) = "" Then GoTo Next_line
        If Left(vLine(i), 1) = "(" Then GoTo Next_line
        
        vItem = Split(vLine(i), ": ")
        vCounts = Split(vItem(1), "-")
        
        If UBound(vCounts) = 0 Then
            iCount = iCount + 1
        Else
            iStart = CInt(vCounts(0))
            iEnd = CInt(vCounts(1))
            
            If iStart = iEnd Then
                iCount = iCount + 1
            Else
                iCount = iCount + 1 + iEnd - iStart
            End If
        End If
Next_line:
    Next i
    
    tbTotal.Value = iCount
End Sub

Private Sub tbCableCounts_DblClick(ByVal Cancel As MSForms.ReturnBoolean)
    Me.Hide
    
    Load PlaceCableCCounts
    PlaceCableCCounts.show
    Unload PlaceCableCCounts
    
    Me.show
End Sub

Private Sub tbTotal_Enter()
    Dim vLine, vItem, vCount As Variant
    Dim strLine As String
    Dim iStart, iEnd, iCount As Integer
    
    iCount = 0
    strLine = Replace(tbCableCounts.Value, vbLf, "")
    strLine = Replace(strLine, vbTab, " ")
    
    vLine = Split(strLine, vbCr)
    For i = 0 To UBound(vLine)
        If vLine(i) = "" Then GoTo Next_line
        
        vItem = Split(vLine(i), ": ")
        vCounts = Split(vItem(1), "-")
        
        If UBound(vCounts) = 0 Then
            iCount = iCount + 1
        Else
            iStart = CInt(vCounts(0))
            iEnd = CInt(vCounts(1))
            
            If iStart = iEnd Then
                iCount = iCount + 1
            Else
                iCount = iCount + 1 + iEnd - iStart
            End If
        End If
Next_line:
    Next i
    
    tbTotal.Value = iCount
End Sub

Private Sub UserForm_Initialize()
    cbScale.AddItem "50"
    cbScale.AddItem "75"
    cbScale.AddItem "100"
    cbScale.Value = "100"
    
    cbPlacement.AddItem "Leader"
    cbPlacement.AddItem "Away"
    cbPlacement.Value = "Leader"
    
    strMainCC = "empty"
    strMainSC = "empty"
End Sub

Private Sub UpdateBlock(strPosition As String)
    Dim vAttList As Variant
    Dim vCable, vSplice As Variant
    Dim strCables, strSplices, strTemp As String
    Dim strText, strCable, strClosure As String
    Dim iAtt As Integer
    
    Select Case objStructure.Name
        Case "sPole"
            iAtt = 25
        Case Else
            iAtt = 5
    End Select
    
    If tbCableCounts.Value = "" Then
        strCable = ""
        strText = ""
    Else
        strCable = tbPosition.Value & ": " & tbCableType.Value & " / "
        strText = Replace(tbCableCounts.Value, vbLf, "")
        strText = Replace(strText, vbCr, " + ")
        strText = Replace(strText, vbTab, " ")
    
        If Right(strText, 3) = " + " Then strText = Left(strText, Len(strText) - 3)
        If Left(strText, 3) = " + " Then strText = Right(strText, Len(strText) - 3)
        strCable = strCable & strText
    End If
    
    If tbClosure.Value = "" Then
        strClosure = ""
    Else
        strClosure = Replace(tbClosure.Value, vbLf, "")
        strClosure = Replace(strClosure, vbCr, " + ")
        strClosure = Replace(strClosure, vbTab, " ")
        strClosure = "[" & tbPosition.Value & "] " & strClosure
        If Right(strClosure, 3) = " + " Then strClosure = Left(strClosure, Len(strClosure) - 3)
    End If
    
    
    vAttList = objStructure.GetAttributes
    If vAttList(iAtt).TextString = "" Then
        strCables = strCable
        GoTo Found_Cable
    End If
    
    'MsgBox vAttList(iAtt).TextString
    strCables = Replace(vAttList(iAtt).TextString, vbLf, "")
    If Left(strCables, 1) = vbCr Then strCables = Right(strCables, Len(strCables) - 1)
    strCables = Replace(strCables, "\P", vbCr)
    'MsgBox strCables
    
    If strCables = "" Then
        strCables = strCable
        GoTo Found_Cable
    End If
    
    vCable = Split(strCables, vbCr)
    
    For i = 0 To UBound(vCable)
        vItem = Split(vCable(i), ": ")
        If vItem(0) = strPosition Then
            vCable(i) = strCable
            
            strCables = ""
            For j = 0 To UBound(vCable)
                If Not vCable(j) = "" Then
                    If strCables = "" Then
                        strCables = vCable(j)
                    Else
                        strCables = strCables & vbCr & vCable(j)
                    End If
                End If
            Next j
            GoTo Found_Cable
        End If
    Next i
    
    If strCables = "" Then
        strCables = strCable
    Else
        strCables = strCables & vbCr & strCable
    End If
    
Found_Cable:
    If Not strCable = "" Then vAttList(iAtt).TextString = strCables
    
Cables_Empty:
    
    If strClosure = "" Then GoTo No_Closure
        
    strSplices = Replace(vAttList(iAtt + 1).TextString, vbLf, "")
    strSplices = Replace(strSplices, "\P", vbCr)
    
    'If strSplices = "" Then GoTo Splices_Empty
    vSplice = Split(strSplices, vbCr)
    
    For i = 0 To UBound(vSplice)
        vItem = Split(vSplice(i), "] ")
        strTemp = Replace(vItem(0), "[", "")
        
        If strTemp = strPosition Then
            vSplice(i) = strClosure
            
            strSplices = ""
            For j = 0 To UBound(vSplice)
                If Not vSplice(j) = "" Then
                    If strSplices = "" Then
                        strSplices = vSplice(j)
                    Else
                        strSplices = strSplices & vbCr & vSplice(j)
                    End If
                End If
            Next j
            GoTo Found_Splice
        End If
    Next i
    
    If strSplices = "" Then
        strSplices = strClosure
    Else
        strSplices = strSplices & vbCr & strClosure
    End If
    
    
Found_Splice:
    vAttList(iAtt + 1).TextString = strSplices
    
Splices_Empty:
    
No_Closure:
    objStructure.Update
    
    strMainCC = tbCableCounts.Value
    strMainSC = tbClosure.Value
End Sub

Private Sub GetPositionData(strPosition As String)
    Dim vAttList As Variant
    Dim vLine, vItem, vCounts As Variant
    Dim vCable, vSplice As Variant
    Dim strText, strBack As String
    Dim strCables, strSplices, strTemp As String
    Dim iAtt As Integer
    
    On Error Resume Next
    
    tbCableCounts.Value = ""
    tbClosure.Value = ""
    tbWL.Value = ""
    
    Select Case objStructure.Name
        Case "sPole"
            iAtt = 25
            tbType.Value = "POLE"
        Case "sPed"
            iAtt = 5
            tbType.Value = "PED"
        Case "sHH"
            iAtt = 5
            tbType.Value = "HH"
        Case "sPanel"
            iAtt = 5
            tbType.Value = "PANEL"
        Case "sMH"
            iAtt = 5
            tbType.Value = "MH"
        Case "sFP"
            iAtt = 5
            tbType.Value = "FP"
        Case Else
            MsgBox objStructure.Name & vbCr & "Why?"
            GoTo Exit_Sub
    End Select
    
    vAttList = objStructure.GetAttributes
    
    strCables = Replace(vAttList(iAtt).TextString, vbLf, "")
    strCables = Replace(strCables, "\P", vbCr)
    vCable = Split(strCables, vbCr)
    
    For i = 0 To UBound(vCable)
        vItem = Split(vCable(i), ": ")
        If vItem(0) = strPosition Then GoTo Found_Cable
    Next i
    
    'MsgBox "No Cable found at that Position."
    GoTo Find_Splice
    
Found_Cable:
    vLine = Split(vCable(i), " / ")
    vItem = Split(vLine(0), ": ")
    tbNumber.Value = vAttList(0).TextString
    tbPosition.Value = vItem(0)
    tbCableType.Value = vItem(1)
            
    strText = Replace(vLine(1), " + ", vbCr)
    strText = Replace(strText, " ", vbTab)
    tbCableCounts.Value = strText
    
Find_Splice:
            
    strSplices = Replace(vAttList(iAtt + 1).TextString, vbLf, "")
    
    If Left(strSplices, 1) = vbCrLf Then strSplices = Right(strSplices, Len(strSplices) - 1)
    If Left(strSplices, 1) = vbCr Then strSplices = Right(strSplices, Len(strSplices) - 1)
    If Left(strSplices, 1) = vbLf Then strSplices = Right(strSplices, Len(strSplices) - 1)
    
    If Right(strSplices, 1) = vbCrLf Then strSplices = Left(strSplices, Len(strSplices) - 1)
    If Right(strSplices, 1) = vbCr Then strSplices = Left(strSplices, Len(strSplices) - 1)
    If Right(strSplices, 1) = vbLf Then strSplices = Left(strSplices, Len(strSplices) - 1)
    
    strSplices = Replace(strSplices, "\P", vbCr)
    
    vAttList(iAtt + 1).TextString = strSplices
    objStructure.Update
    
    vSplice = Split(strSplices, vbCr)
    
    For i = 0 To UBound(vSplice)
        If vSplice(i) = "" Then GoTo Next_I
        
        vItem = Split(vSplice(i), "] ")
        strTemp = Replace(vItem(0), "[", "")
        If tbPosition.Value = "" Then tbPosition.Value = strTemp
        If strTemp = strPosition Then GoTo Found_Splice
Next_I:
    Next i
    
    'MsgBox "No Splice found at that Position."
    GoTo Get_Wiring_Limits
    
Found_Splice:
    
    If Not vSplice(0) = "" Then
        For i = 0 To UBound(vSplice)
            vCounts = Split(vSplice(i), "] ")
            strTemp = Replace(vCounts(0), "[", "")
            If strTemp = strPosition Then
                strText = Replace(vCounts(1), " + ", vbCr)
                strText = Replace(strText, " ", vbTab)
                tbClosure.Value = strText
                
                GoTo Get_Wiring_Limits
            End If
        Next i
    End If
    
Get_Wiring_Limits:

    tbWL.Value = ""
    
    Dim filterType, filterValue As Variant
    Dim grpCode(0) As Integer
    Dim grpValue(0) As Variant
    Dim objSS As AcadSelectionSet
    Dim objBlock As AcadBlockReference
    
    grpCode(0) = 2
    grpValue(0) = "Customer,SG"
    filterType = grpCode
    filterValue = grpValue
    
    Err = 0
    Set objSS = ThisDrawing.SelectionSets.Add("objSS")
    If Not Err = 0 Then
        Set objSS = ThisDrawing.SelectionSets.Item("objSS")
        objSS.Clear
    End If
    
    objSS.Select acSelectionSetAll, , , filterType, filterValue
    
    For Each objBlock In objSS
        vAttList = objBlock.GetAttributes
        
        Select Case objBlock.Name
            Case "SG"
                If vAttList(2).TextString = "" Then GoTo Next_objBlock
                vLine = Split(vAttList(2).TextString, " - ")
                strText = vLine(1) & vbTab & "SG - " & vAttList(1).TextString
            Case Else
                If vAttList(4).TextString = "" Then GoTo Next_objBlock
                vLine = Split(vAttList(4).TextString, " - ")
                strText = vLine(1) & vbTab & vAttList(1).TextString & " " & vAttList(2).TextString
        End Select
        
        If vLine(0) = tbNumber.Value Then
            'vItem = Split(vLine(1), ": ")
            'strText = Replace(vItem(1), ")", "")
            
            If tbWL.Value = "" Then
                'tbWL.Value = strText & vbTab & vAttList(1).TextString & " " & vAttList(2).TextString
                tbWL.Value = strText
            Else
                'tbWL.Value = tbWL.Value & vbCr & strText & vbTab & vAttList(1).TextString & " " & vAttList(2).TextString
                tbWL.Value = tbWL.Value & vbCr & strText
            End If
            
        End If
Next_objBlock:
    Next objBlock
    
    Call SortWL
    
Clear_objSS:
    objSS.Clear
    objSS.Delete
        
Exit_Sub:
    cbUpdate.Enabled = True
    
    strMainCC = tbCableCounts.Value
    strMainSC = tbClosure.Value
End Sub

Private Function GetScale(vCoords As Variant)
    Dim filterType, filterValue As Variant
    Dim grpCode(0) As Integer
    Dim grpValue(0) As Variant
    Dim objSS As AcadSelectionSet
    Dim objBlock As AcadBlockReference
    Dim vAttList As Variant
    Dim dMinX, dMaxX, dMinY, dMaxY As Double
    Dim dScale As Double
    
    On Error Resume Next
    
    grpCode(0) = 2
    grpValue(0) = "SS-11x17"
    filterType = grpCode
    filterValue = grpValue
    
    Set objSS = ThisDrawing.SelectionSets.Add("objSS")
    If Not Err = 0 Then
        Set objSS = ThisDrawing.SelectionSets.Item("objSS")
        objSS.Clear
    End If
    
    objSS.Select acSelectionSetAll, , , filterType, filterValue
    
    For Each objBlock In objSS
        dScale = objBlock.XScaleFactor
        dMinX = objBlock.InsertionPoint(0)
        dMaxX = dMinX + (1652 * dScale)
        
        dMinY = objBlock.InsertionPoint(1)
        dMaxY = dMinY + (1052 * dScale)
        
        If vCoords(0) > dMinX And vCoords(0) < dMaxX Then
            If vCoords(1) > dMinY And vCoords(1) < dMaxY Then
                dScale = dScale * 1.333333333
                GoTo Exit_Sub
            End If
        End If
    Next objBlock
    
    dScale = 1#
    
Exit_Sub:
    objSS.Clear
    objSS.Delete
    'MsgBox dScale
    GetScale = dScale
End Function

Attribute VB_Name = "PlacePoleData"
Attribute VB_Base = "0{DF7213D5-9CEF-4FFF-BC6E-6EEC1D1D64D1}{A8F38DD6-A54C-4EC5-B6ED-C2F6CD32BB06}"
Attribute VB_GlobalNameSpace = False
Attribute VB_Creatable = False
Attribute VB_PredeclaredId = True
Attribute VB_Exposed = False
Attribute VB_TemplateDerived = False
Attribute VB_Customizable = False
Dim objPole As AcadBlockReference
Dim iUpdate As Integer

Private Sub cbAddAttach_Click()
    Dim strMR As String
    
    If Not tbEAttach.Value = "" Then
        If InStr(tbEAttach.Value, "-") = 0 Then tbEAttach.Value = tbEAttach.Value & "-0"
    End If
    If Not tbPAttach.Value = "" Then
        If InStr(tbPAttach.Value, "-") = 0 Then tbPAttach.Value = tbPAttach.Value & "-0"
    End If
    
    If cbAddAttach.Caption = "Update" Then
        lbAttach.List(lbAttach.ListIndex, 0) = cbAttachment.Value
        lbAttach.List(lbAttach.ListIndex, 1) = tbEAttach.Value
        lbAttach.List(lbAttach.ListIndex, 2) = tbPAttach.Value
        
        cbAddAttach.Caption = "Add Data"
        lbAttach.Enabled = True
        GoTo Exit_Sub
    End If
    
    lbAttach.AddItem cbAttachment.Value
    lbAttach.List(lbAttach.ListCount - 1, 1) = tbEAttach.Value
    lbAttach.List(lbAttach.ListCount - 1, 2) = tbPAttach.Value
    
    lbAttach.ListIndex = lbAttach.ListCount - 1
    
Exit_Sub:
    If tbPAttach.Value = "" Then
        strMR = ""
    Else
        strMR = GetMR(CStr(tbEAttach.Value), CStr(tbPAttach.Value))
    End If
    
    lbAttach.List(lbAttach.ListIndex, 3) = strMR
    
    cbAttachment.Value = ""
    tbEAttach.Value = ""
    tbPAttach.Value = ""
    
    Call SortAttachments
End Sub

Private Sub cbAddData_Click()
    If cbAddData.Caption = "Update" Then
        lbData.List(lbData.ListIndex, 1) = tbDValue.Value
        
        cbDType.Value = ""
        cbDType.Enabled = True
        tbDValue.Value = ""
        
        cbAddData.Caption = "Add Data"
        iUpdate = 1
        Exit Sub
    End If
    
    Select Case cbDType.Value
        Case "Type"
            lbData.AddItem "1  Type"
        Case "Owner #"
            lbData.AddItem "2  Owner #"
        Case "Other #"
            lbData.AddItem "3  Other #"
        Case "Ground"
            lbData.AddItem "9  Ground"
    End Select
    lbData.List(lbData.ListCount - 1, 1) = tbDValue.Value
    
    cbDType.Value = ""
    tbDValue.Value = ""
    iUpdate = 1
End Sub

Private Sub cbAddUnit_Click()
    If cbAddUnit.Caption = "Update" Then
        lbUnits.List(lbUnits.ListIndex, 0) = tbUnit.Value
        lbUnits.List(lbUnits.ListIndex, 1) = tbQuantity.Value
        lbUnits.List(lbUnits.ListIndex, 2) = tbUNote.Value
        
        lbUnits.Enabled = True
        cbAddUnit.Caption = "Add Unit"
        GoTo Exit_Sub
    End If
    
    lbUnits.AddItem tbUnit.Value
    lbUnits.List(lbUnits.ListCount - 1, 1) = tbQuantity.Value
    lbUnits.List(lbUnits.ListCount - 1, 2) = tbUNote.Value
    
Exit_Sub:
    
    tbUnit.Value = ""
    tbQuantity.Value = ""
    tbUNote.Value = ""
    iUpdate = 1
End Sub

Private Sub cbCombine_Click()
    If lbUnits.ListCount < 2 Then Exit Sub
    
    Dim vCurrent, vOther, vItem As Variant
    Dim strCurrent As String
    
    For i = lbUnits.ListCount - 1 To 0 Step -1
        strCurrent = lbUnits.List(i, 0)
        If lbUnits.List(i, 1) = "" Then lbUnits.List(i, 1) = 1
        
        For j = 0 To i - 1
            If lbUnits.List(j, 0) = strCurrent Then
                If lbUnits.List(j, 1) = "" Then lbUnits.List(j, 1) = 1
                lbUnits.List(j, 1) = CInt(lbUnits.List(j, 1)) + CInt(lbUnits.List(i, 1))
                lbUnits.RemoveItem i
                GoTo Next_I
            End If
        Next j
Next_I:
    Next i
End Sub

Private Sub cbDeleteCallout_Click()
    Dim objDelete As AcadSelectionSet
    
    On Error Resume Next
    Me.Hide
    
    Set objDelete = ThisDrawing.SelectionSets.Add("objDelete")
    objDelete.SelectOnScreen
    
    objDelete.Erase
    objDelete.Delete
    
    Me.show
End Sub

Private Sub cbGetsPole_Click()
    If iUpdate = 1 Then
        Dim result As Integer
        
        result = MsgBox("Save changes to Structure?", vbYesNo, "Save Changes")
        If result = vbYes Then
            If objPole.Name = "sPole" Then
                Call SaveAttachments
            Else
                Call SaveBuried
            End If
    
            MsgBox objPole.Name & "  Updated."
        End If
        
        iUpdate = 0
    End If
    
    Dim objObject As AcadObject
    'Dim objBlock As AcadBlockReference
    Dim vBasePnt, vAttList As Variant
    Dim vLine, vItem, vTemp As Variant
    Dim strTemp As String
    Dim dTemp As Double
    
    lbData.Clear
    lbAttach.Clear
    lbUnits.Clear
    tbNotes.Value = ""
    'lbCables.Clear
    'lbSplices.Clear
    
    'cbUpdatePole.Enabled = True
    
    Me.Hide
  On Error Resume Next
    
    ThisDrawing.Utility.GetEntity objObject, vBasePnt, "Select Pole: "
    If TypeOf objObject Is AcadBlockReference Then
        Set objPole = objObject
    Else
        MsgBox "Not a valid object."
        Me.show
        Exit Sub
    End If
    
    Select Case objPole.Name
        Case "sPole"
        Case "sPed", "sHH", "sMH", "sPanel", "sFP"
            Call GetBuriedPlant
            Me.show
            Exit Sub
        Case Else
            MsgBox "Not a valid pole."
            Me.show
            Exit Sub
    End Select
    
    dTemp = GetScale(objPole.InsertionPoint)
    If dTemp > 0 Then cbScale.Value = dTemp * 100
    
    vAttList = objPole.GetAttributes
    
    tbPoleNumber.Value = vAttList(0).TextString
    tbOwner.Value = vAttList(2).TextString
    
    lbData.AddItem "1  Type"
    If vAttList(5).TextString = "" Then
        lbData.List(lbData.ListCount - 1, 1) = "?-?"
    Else
        lbData.List(lbData.ListCount - 1, 1) = vAttList(5).TextString
    End If
    
    
    
    Select Case vAttList(3).TextString
        Case ""
            lbData.AddItem "2  Owner #"
            lbData.List(lbData.ListCount - 1, 1) = "NA"
        Case "NO TAG"
            lbData.AddItem "2  Owner #"
            lbData.List(lbData.ListCount - 1, 1) = "NO TAG"
        Case Else
            vLine = Split(vAttList(3).TextString, " ")
            For j = 0 To UBound(vLine)
                If j = 0 Then
                    lbData.AddItem "2  Owner #"
                    lbData.List(lbData.ListCount - 1, 1) = vLine(j)
                Else
                    lbData.AddItem "3  Other #"
                    lbData.List(lbData.ListCount - 1, 1) = vLine(j)
                End If
            Next j
    End Select
    
    'If vAttList(3).TextString = "" Then
        'lbData.AddItem "2  Owner #"
        'lbData.List(lbData.ListCount - 1, 1) = "NA"
    'Else
        'vLine = Split(vAttList(3).TextString, " ")
        'For j = 0 To UBound(vLine)
            'If j = 0 Then
                'lbData.AddItem "2  Owner #"
                'lbData.List(lbData.ListCount - 1, 1) = vLine(j)
            'Else
                'lbData.AddItem "3  Other #"
                'lbData.List(lbData.ListCount - 1, 1) = vLine(j)
            'End If
        'Next j
    'End If
    
    
    
    If Not vAttList(4).TextString = "" Then
        vLine = Split(vAttList(4).TextString, " ")
        
        For i = 0 To UBound(vLine)
            vItem = Split(vLine(i), "=")
            
            If UBound(vItem) = 0 Then
                lbData.AddItem "3  Other #"
                lbData.List(lbData.ListCount - 1, 1) = tbOwner.Value & "=" & vLine(i)
            Else
                For j = 1 To UBound(vItem)
                    Select Case vItem(0)
                        Case "A"
                            vItem(0) = "ATT"
                        Case "CH"
                            vItem(0) = "CHARTER"
                        Case "CO"
                            vItem(0) = "COMCAST"
                        Case "D"
                            vItem(0) = "DREMC"
                        Case "M"
                            vItem(0) = "MTEMC"
                        Case "N"
                            vItem(0) = "NES"
                        Case "T"
                            vItem(0) = "TDS"
                    End Select
                    
                    lbData.AddItem "3  Other #"
                    lbData.List(lbData.ListCount - 1, 1) = vItem(0) & "=" & vItem(j)
                Next j
            End If
        Next i
    End If
    
    
    lbData.AddItem "9  Ground"
    Select Case UCase(vAttList(8).TextString)
        Case "", "N"
            lbData.List(lbData.ListCount - 1, 1) = "NO GRD"
        Case "M"
            lbData.List(lbData.ListCount - 1, 1) = "MGNV"
        Case "T"
            lbData.List(lbData.ListCount - 1, 1) = "TGB"
        Case "B"
            lbData.List(lbData.ListCount - 1, 1) = "BROKEN GRD"
        Case Else
            lbData.List(lbData.ListCount - 1, 1) = vAttList(8).TextString
    End Select
    
    If cbAddCoords.Value = True Then
        If Not vAttList(7).TextString = "" Then
            vLine = Split(vAttList(7).TextString, ",")
            
            dTemp = CLng(CDbl(vLine(0)) * 10000000) / 10000000
            strTemp = dTemp & ","
            
            dTemp = CLng(CDbl(vLine(1)) * 10000000) / 10000000
            strTemp = strTemp & dTemp
            
            lbData.AddItem "99  Lat,Long"
            lbData.List(lbData.ListCount - 1, 1) = strTemp
        End If
    End If
    
    '<---------------------------------------------------------------- Add Attachments
    
    For n = 9 To 23
        If vAttList(n).TextString = "" Then GoTo Next_N
        
        
        Select Case n
            Case Is = 9
                vLine = Split(vAttList(n).TextString, " ")
                For k = 0 To UBound(vLine)
                    lbAttach.AddItem "NEUTRAL"
                    
                    If InStr(vLine(k), ")") > 0 Then
                        vTemp = Split(vLine(k), ")")
                        vTemp(0) = Replace(vTemp(0), "(", "")
                        
                        lbAttach.List(lbAttach.ListCount - 1, 1) = vTemp(0)
                        lbAttach.List(lbAttach.ListCount - 1, 2) = vTemp(1)
                        lbAttach.List(lbAttach.ListCount - 1, 3) = GetMR(CStr(vTemp(0)), CStr(vTemp(1)))
                    Else
                        lbAttach.List(lbAttach.ListCount - 1, 1) = vLine(k)
                        lbAttach.List(lbAttach.ListCount - 1, 2) = ""
                        lbAttach.List(lbAttach.ListCount - 1, 3) = ""
                    End If
                Next k
            Case Is = 10
                vLine = Split(vAttList(n).TextString, " ")
                For k = 0 To UBound(vLine)
                    lbAttach.AddItem "TRANSFORMER"
                    
                    If InStr(vLine(k), ")") > 0 Then
                        vTemp = Split(vLine(k), ")")
                        vTemp(0) = Replace(vTemp(0), "(", "")
                        
                        lbAttach.List(lbAttach.ListCount - 1, 1) = vTemp(0)
                        lbAttach.List(lbAttach.ListCount - 1, 2) = vTemp(1)
                        lbAttach.List(lbAttach.ListCount - 1, 3) = GetMR(CStr(vTemp(0)), CStr(vTemp(1)))
                    Else
                        lbAttach.List(lbAttach.ListCount - 1, 1) = vLine(k)
                        lbAttach.List(lbAttach.ListCount - 1, 2) = ""
                        lbAttach.List(lbAttach.ListCount - 1, 3) = ""
                    End If
                Next k
            Case Is = 11, Is = 12, Is = 13
                vLine = Split(vAttList(n).TextString, " ")
                For k = 0 To UBound(vLine)
                    
                    Select Case n
                        Case Is = 11
                            lbAttach.AddItem "LOW POWER"
                        Case Is = 12
                            lbAttach.AddItem "ANTENNA"
                        Case Is = 13
                            lbAttach.AddItem "ST LT CIR"
                    End Select
                    
                    If InStr(vLine(k), ")") > 0 Then
                        vTemp = Split(vLine(k), ")")
                        vTemp(0) = Replace(vTemp(0), "(", "")
                        
                        lbAttach.List(lbAttach.ListCount - 1, 1) = vTemp(0)
                        lbAttach.List(lbAttach.ListCount - 1, 2) = vTemp(1)
                        lbAttach.List(lbAttach.ListCount - 1, 3) = GetMR(CStr(vTemp(0)), CStr(vTemp(1)))
                    Else
                        lbAttach.List(lbAttach.ListCount - 1, 1) = vLine(k)
                        lbAttach.List(lbAttach.ListCount - 1, 2) = ""
                        lbAttach.List(lbAttach.ListCount - 1, 3) = ""
                    End If
                Next k
            Case Is = 14
                vLine = Split(vAttList(n).TextString, " ")
                For k = 0 To UBound(vLine)
                    lbAttach.AddItem "ST LT"
                    
                    If InStr(vLine(k), ")") > 0 Then
                        vTemp = Split(vLine(k), ")")
                        vTemp(0) = Replace(vTemp(0), "(", "")
                        
                        lbAttach.List(lbAttach.ListCount - 1, 1) = vTemp(0)
                        lbAttach.List(lbAttach.ListCount - 1, 2) = vTemp(1)
                        lbAttach.List(lbAttach.ListCount - 1, 3) = GetMR(CStr(vTemp(0)), CStr(vTemp(1)))
                    Else
                        lbAttach.List(lbAttach.ListCount - 1, 1) = vLine(k)
                        lbAttach.List(lbAttach.ListCount - 1, 2) = ""
                        lbAttach.List(lbAttach.ListCount - 1, 3) = ""
                    End If
                Next k
            Case Is = 15
                vLine = Split(UCase(vAttList(n).TextString), " ")
                For k = 0 To UBound(vLine)
                    lbAttach.AddItem "NEW 6M"
                    lbAttach.List(lbAttach.ListCount - 1, 1) = ""
                    lbAttach.List(lbAttach.ListCount - 1, 3) = "NEW"
                    
                    If InStr(vLine(k), "T") > 0 Then
                        vLine(k) = Replace(vLine(k), "T", "")
                        lbAttach.List(lbAttach.ListCount - 1, 3) = "MTE TAG"
                    End If
                    
                    If InStr(vLine(k), "O") > 0 Then
                        vLine(k) = Replace(vLine(k), "O", "")
                        lbAttach.List(lbAttach.ListCount - 1, 0) = "NEW 6M OHG"
                    End If
                    
                    If InStr(vLine(k), "P") > 0 Then
                        vLine(k) = Replace(vLine(k), "P", "")
                        lbAttach.List(lbAttach.ListCount - 1, 0) = "NEW 6M TAP"
                    End If
                    
                    If InStr(vLine(k), "F") > 0 Then
                        vLine(k) = Replace(vLine(k), "F", "")
                        lbAttach.List(lbAttach.ListCount - 1, 3) = "FUTURE"
                    End If
                    
                    lbAttach.List(lbAttach.ListCount - 1, 2) = vLine(k)
                Next k
            Case Is > 15
                vLine = Split(UCase(vAttList(n).TextString), "=")
                vItem = Split(vLine(1), " ")
                For k = 0 To UBound(vItem)
                    strTemp = vLine(0)
                    
                    If InStr(vItem(k), "C") > 0 Then
                        strTemp = strTemp & " C-WIRE"
                        vItem(k) = Replace(vItem(k), "C", "")
                    End If
                    
                    If InStr(vItem(k), "D") > 0 Then
                        strTemp = strTemp & " DROP"
                        vItem(k) = Replace(vItem(k), "D", "")
                    End If
                    
                    If InStr(vItem(k), "O") > 0 Then
                        strTemp = strTemp & " OHG"
                        vItem(k) = Replace(vItem(k), "O", "")
                    End If
                    
                    If InStr(vItem(k), "P") > 0 Then
                        strTemp = strTemp & " TAP"
                        vItem(k) = Replace(vItem(k), "P", "")
                    End If
                    
                    If InStr(vItem(k), "S") > 0 Then
                        strTemp = strTemp & " SS"
                        vItem(k) = Replace(vItem(k), "S", "")
                    End If
                    
                    If InStr(vItem(k), "V") > 0 Then
                        strTemp = "LASH TO " & strTemp
                        vItem(k) = Replace(vItem(k), "V", "")
                    End If
                    
                    lbAttach.AddItem strTemp
                    
                    lbAttach.List(lbAttach.ListCount - 1, 3) = ""
                    
                    If InStr(vItem(k), "X") > 0 Then
                        lbAttach.List(lbAttach.ListCount - 1, 3) = "ATTACH"
                        vItem(k) = Replace(vItem(k), "X", "")
                        lbAttach.List(lbAttach.ListCount - 1, 1) = ""
                        lbAttach.List(lbAttach.ListCount - 1, 2) = vItem(k)
                        
                        GoTo Next_K
                    End If
                    
                    If InStr(vItem(k), "E") > 0 Then
                        lbAttach.List(lbAttach.ListCount - 1, 3) = "EXTEND"
                        vItem(k) = Replace(vItem(k), "E", "")
                        lbAttach.List(lbAttach.ListCount - 1, 1) = vItem(k)
                        lbAttach.List(lbAttach.ListCount - 1, 2) = ""
                        
                        GoTo Next_K
                    End If
                    
                    If InStr(vItem(k), ")") > 0 Then
                        vTemp = Split(vItem(k), ")")
                        vTemp(0) = Replace(vTemp(0), "(", "")
                        
                        lbAttach.List(lbAttach.ListCount - 1, 1) = vTemp(0)
                        lbAttach.List(lbAttach.ListCount - 1, 2) = vTemp(1)
                        lbAttach.List(lbAttach.ListCount - 1, 3) = GetMR(CStr(vTemp(0)), CStr(vTemp(1)))
                    Else
                        lbAttach.List(lbAttach.ListCount - 1, 1) = vItem(k)
                        lbAttach.List(lbAttach.ListCount - 1, 2) = ""
                    End If
Next_K:
                Next k
        End Select
Next_N:
    Next n
    
    'att 25
    'If Not vAttList(25).TextString = "" Then
        'vAttList(25).TextString = Replace(vAttList(25).TextString, vbLf, "")
        'vLine = Split(vAttList(25).TextString, vbCr)
        'For i = 0 To UBound(vLine)
            'vItem = Split(vLine(i), " / ")
            'lbCables.AddItem vItem(0)
            'lbCables.List(lbCables.ListCount - 1, 1) = vItem(1)
        'Next i
    'End If
    
    'att 26
    'If Not vAttList(26).TextString = "" Then
        'vAttList(26).TextString = Replace(vAttList(26).TextString, vbLf, "")
        ''If InStr(vAttList(26).TextString, " + ") > 0 Then vAttList(26).TextString = Replace(vAttList(26).TextString, " + ", vbCr)
        
        'vLine = Split(vAttList(26).TextString, vbCr)
        'For i = 0 To UBound(vLine)
            'lbSplices.AddItem vLine(i)
        'Next i
    'End If
    
    'att 24
    If Not vAttList(24).TextString = "" Then
        tbNotes.Value = ""
        
        vAttList(24).TextString = Replace(vAttList(24).TextString, vbLf, "")
        vAttList(24).TextString = Replace(vAttList(24).TextString, vbCr, "")
        vLine = Split(vAttList(24).TextString, ";")
        
        tbNotes.Value = vLine(0)
        If UBound(vLine) > 0 Then
            For i = 1 To UBound(vLine)
                If Not vLine(i) = "" Then tbNotes.Value = tbNotes.Value & vbCr & vLine(i)
            Next i
        End If
    End If
    
    'att 27
    If Not vAttList(27).TextString = "" Then
        vAttList(27).TextString = Replace(vAttList(27).TextString, vbLf, "")
        vLine = Split(vAttList(27).TextString, ";;")
        For i = 0 To UBound(vLine)
            If InStr(vLine(i), "=") = 0 Then vLine(i) = vLine(i) & "=1"
                
            vItem = Split(vLine(i), "=")
            lbUnits.AddItem vItem(0)
            If InStr(vItem(1), "  ") > 0 Then
                vTemp = Split(vItem(1), "  ")
                lbUnits.List(lbUnits.ListCount - 1, 1) = vTemp(0)
                lbUnits.List(lbUnits.ListCount - 1, 2) = vTemp(1)
            Else
                lbUnits.List(lbUnits.ListCount - 1, 1) = vItem(1)
                lbUnits.List(lbUnits.ListCount - 1, 2) = ""
            End If
        Next i
    End If
    
    Call SortAttachments
    
    cbUpdate.Enabled = True
    cbPlaceData.Enabled = True
    
    cbPlaceData.SetFocus
    
    Me.show
End Sub

Private Sub cbPlaceData_Click()
    'If lbWorkspace.ListCount = 0 Then GoTo Exit_Sub
    If tbPoleNumber.Value = "" Then GoTo Exit_Sub
    
    If Not objPole.Name = "sPole" Then
        Call PlaceBuriedData
        Exit Sub
    End If
    
    Dim returnPoint As Variant
    Dim insertionPnt(0 To 2) As Double
    Dim dRevCloud(0 To 5) As Double
    Dim dNote(0 To 2) As Double
    Dim dScale As Double
    Dim dPosition As Double
    Dim objBlock As AcadBlockReference
    Dim layerObj As AcadLayer
    Dim vAttList, vELine, vPLine As Variant
    Dim iPI, iEI As Integer
    Dim iMR, iNote As Integer
    Dim strAtt0, strAtt1, strAtt2, strAtt3, strAtt4 As String
    Dim strLayer As String
    
    Dim vStr As Variant
    Dim str, str1, strCommand As String
    Dim lwpPnt(0 To 3) As Double
    Dim lineObj As AcadLWPolyline
    Dim n, counter As Integer
    
  On Error Resume Next
    
    strAtt0 = tbPoleNumber.Value
    
    iMR = 0
    iNote = 0
    dPosition = 1#
    
    Me.Hide
    dScale = CInt(cbScale.Value) / 100
    
    Err = 0
    returnPoint = ThisDrawing.Utility.GetPoint(, "Select point:")
    If Not Err = 0 Then GoTo Exit_Sub
    
    n = 0
    For Each Item In returnPoint
        insertionPnt(n) = Item
        n = n + 1
    Next Item
    
    If lbAttach.ListCount < 1 Then GoTo Place_Info
    If cbAttachments.Value = False Then GoTo Place_Info
    
    dRevCloud(0) = insertionPnt(0) - (4 * dScale)
    dRevCloud(1) = insertionPnt(1) + (20 * dScale)
    dRevCloud(2) = 0#
    
    str = "pole_attach_title"
    Set objBlock = ThisDrawing.ModelSpace.InsertBlock(insertionPnt, str, dScale, dScale, dScale, 0)
    objBlock.Layer = "Integrity Attachments-Existing"
    vAttList = objBlock.GetAttributes
    vAttList(0).TextString = strAtt0
    
    objBlock.Update
    
    insertionPnt(0) = insertionPnt(0) + (78 * dScale)
    insertionPnt(1) = insertionPnt(1) - (4.5 * dScale)
    
    str = "pole_attach"
    If lbAttach.ListCount < 1 Then GoTo Place_Info
    
    For i = 0 To (lbAttach.ListCount - 1)
        dPosition = dPosition + 0.01
        strAtt1 = dPosition
        strAtt2 = lbAttach.List(i, 0)
        iPI = 0: iEI = 0
        
        If lbAttach.List(i, 2) = "" Then
            strAtt3 = lbAttach.List(i, 1)
            If lbAttach.List(i, 3) = "EXTEND" Then
                strLayer = "Integrity Attachments-MR"
                iNote = 2
            Else
                strLayer = "Integrity Attachments-Existing"
            End If
        Else
            strAtt3 = lbAttach.List(i, 2)
            If InStr(lbAttach.List(i, 0), "NEW") > 0 Then
                strLayer = "Integrity Attachments-New"
                If iNote < 1 Then iNote = 1
                If lbAttach.List(i, 3) = "MTE TAG" Then iNote = 4
            Else
                strLayer = "Integrity Attachments-MR"
                iNote = 2
            End If
        End If
        
        strAtt3 = Replace(UCase(strAtt3), "-", "'") & """"
        If lbAttach.List(i, 3) = "" Then
            strAtt4 = ""
        Else
            If lbAttach.List(i, 3) = Null Then
                strAtt4 = ""
            Else
                strAtt4 = lbAttach.List(i, 3)
            End If
        End If
        
        
        If InStr(lbAttach.List(i, 0), "NEW") > 0 Then
            strLayer = "Integrity Attachments-New"
            If iNote < 1 Then iNote = 1
        End If
        
Place_Attachment:
        
        Set objBlock = ThisDrawing.ModelSpace.InsertBlock(insertionPnt, str, dScale, dScale, dScale, 0)
        objBlock.Layer = strLayer
        
        vAttList = objBlock.GetAttributes
        vAttList(0).TextString = strAtt0
        vAttList(1).TextString = strAtt1
        vAttList(2).TextString = strAtt2
        vAttList(3).TextString = strAtt3
        If strAtt4 = "" Then
            vAttList(4).TextString = ""
        Else
            vAttList(4).TextString = strAtt4
        End If
        objBlock.Update
        
        insertionPnt(1) = insertionPnt(1) - (9 * dScale)
    Next i
    
    vAttList = objPole.GetAttributes
        
    Select Case vAttList(2).TextString
        Case "ATT", "BST"
            If iNote = 1 Then iNote = 3
    End Select
               
    Select Case iNote
        Case 0
            Set layerObj = ThisDrawing.Layers.Add("Integrity Attachments-Existing")
            ThisDrawing.ActiveLayer = layerObj
            dRevCloud(3) = insertionPnt(0) + (30 * dScale)
        Case 1
            Set layerObj = ThisDrawing.Layers.Add("Integrity Attachments-New")
            ThisDrawing.ActiveLayer = layerObj
            dRevCloud(3) = insertionPnt(0) + (58 * dScale)
        Case 2
            Set layerObj = ThisDrawing.Layers.Add("Integrity Attachments-MR")
            ThisDrawing.ActiveLayer = layerObj
            dRevCloud(3) = insertionPnt(0) + (84 * dScale)
        Case 3
            Set layerObj = ThisDrawing.Layers.Add("Integrity Attachments-MR")
            ThisDrawing.ActiveLayer = layerObj
            dRevCloud(3) = insertionPnt(0) + (58 * dScale)
        Case 4
            Set layerObj = ThisDrawing.Layers.Add("Integrity Attachments-New")
            ThisDrawing.ActiveLayer = layerObj
            dRevCloud(3) = insertionPnt(0) + (84 * dScale)
    End Select
    dRevCloud(4) = insertionPnt(1) + (3 * dScale)
    dRevCloud(5) = 0#
    
    strCommand = "revcloud r " & dRevCloud(0) & "," & dRevCloud(1)
    strCommand = strCommand & " " & dRevCloud(3) & "," & dRevCloud(4) & " " & vbCr
    ThisDrawing.SendCommand strCommand
    
    Set layerObj = ThisDrawing.Layers.Add("0")
    ThisDrawing.ActiveLayer = layerObj
    
    '<---------------------------------------------------------------------------------------------
Place_Info:
    
    str = "pole_info"
    strLayer = "Integrity Pole-Info"

    insertionPnt(0) = insertionPnt(0) - (74 * dScale)
    insertionPnt(1) = insertionPnt(1) - (12 * dScale)
    
    dPosition = 0#
    
    
    Set objBlock = ThisDrawing.ModelSpace.InsertBlock(insertionPnt, str, dScale, dScale, dScale, 0)
    objBlock.Layer = strLayer
        
    vAttList = objBlock.GetAttributes
    vAttList(0).TextString = strAtt0
    vAttList(1).TextString = "0.0"
    vAttList(2).TextString = tbPoleNumber.Value
    objBlock.Update
    
    insertionPnt(1) = insertionPnt(1) - (9 * dScale)
    
    
    Dim vText, vLine As Variant
    
    For w = 0 To lbData.ListCount - 1
        If lbData.List(w, 0) = "" Then GoTo Next_W
        
        vText = Split(lbData.List(w, 0), " ")
        strAtt1 = dPosition & "." & vText(0)
        
        Select Case vText(0)
            Case "1", "2"
                strAtt2 = tbOwner.Value
                strAtt3 = lbData.List(w, 1)
            Case "3"
                vLine = Split(lbData.List(w, 1), "=")
                
                If UBound(vLine) > 0 Then
                    strAtt2 = vLine(0)
                    strAtt3 = vLine(1)
                Else
                    strAtt2 = tbOwner.Value
                    strAtt3 = lbData.List(w, 1)
                End If
            Case "9", "99"
                strAtt2 = lbData.List(w, 1)
                strAtt3 = ""
            Case Else
                GoTo Next_W
        End Select
    
        Set objBlock = ThisDrawing.ModelSpace.InsertBlock(insertionPnt, str, dScale, dScale, dScale, 0)
        objBlock.Layer = strLayer
        If vText(0) = "1" Then
            If InStr(lbData.List(w, 1), ")") > 0 Then objBlock.Layer = "Integrity Notes"
        End If
        
        vAttList = objBlock.GetAttributes
        vAttList(0).TextString = strAtt0
        vAttList(1).TextString = strAtt1
        vAttList(2).TextString = strAtt2
        vAttList(3).TextString = strAtt3
        objBlock.Update
    
        insertionPnt(1) = insertionPnt(1) - (9 * dScale)
Next_W:
    Next w
    
    lwpPnt(0) = insertionPnt(0) - (4 * dScale)
    lwpPnt(1) = insertionPnt(1) + (7 * dScale)
    lwpPnt(2) = lwpPnt(0) + (100 * dScale)
    lwpPnt(3) = lwpPnt(1)
    
    Set lineObj = ThisDrawing.ModelSpace.AddLightWeightPolyline(lwpPnt)
    lineObj.Layer = strLayer
    lineObj.Update
    
    '<---------------------------------------------------------------------------------------------
Place_Units:
    If cbPlaceUnits.Value = False Then GoTo Place_Note
    If lbUnits.ListCount < 1 Then GoTo Place_Note
    
    str = "pole_unit"
    strLayer = "Integrity Pole-Units"
    
    dPosition = 2#
    
    insertionPnt(1) = insertionPnt(1) - (1 * dScale)
    
    For v = 0 To lbUnits.ListCount - 1
        strAtt1 = dPosition
        strAtt2 = "N/A"
        strAtt3 = lbUnits.List(v, 0) & "=" & lbUnits.List(v, 1)
        If Not lbUnits.List(v, 2) = "" Then strAtt3 = strAtt3 & "  " & lbUnits.List(v, 2)
    
        Set objBlock = ThisDrawing.ModelSpace.InsertBlock(insertionPnt, str, dScale, dScale, dScale, 0)
        objBlock.Layer = strLayer
        
        vAttList = objBlock.GetAttributes
        vAttList(0).TextString = strAtt0
        vAttList(1).TextString = strAtt1
        vAttList(2).TextString = strAtt2
        vAttList(3).TextString = strAtt3
        objBlock.Update
    
        insertionPnt(1) = insertionPnt(1) - (9 * dScale)
    Next v
    
    'GoTo Exit_Sub
    
Place_Note:
    If cbPlaceNotes.Value = False Then GoTo Exit_Sub
    If tbNotes.Value = "" Then GoTo Exit_Sub
    
    Dim objCircle As AcadCircle
    Dim dRadius As Double
    Dim iOffset As Integer
    'Dim dNote(0 To 2) As Double
    
    dRadius = 20#
    iOffset = 0
    
    str = Replace(tbNotes.Value, vbLf, "")
    vStr = Split(str, vbCr)
    
    dNote(0) = (dRevCloud(0) + dRevCloud(3)) / 2
    dNote(1) = dRevCloud(1) - 20
    dNote(2) = 0#
    
    For i = 0 To UBound(vStr)
        Select Case vStr(i)
            Case "OCALC"
                Set objCircle = ThisDrawing.ModelSpace.AddCircle(objPole.InsertionPoint, dRadius)
                objCircle.Layer = "Integrity Notes"
                objCircle.Update
                
                GoTo Next_I
            Case "NOTE-TALL"
                str = "Notes-TallerPole5"
                iOffset = 30
            Case "NOTE-TALL10"
                str = "Notes-TALL10"
                iOffset = 30
            Case "NOTE-DEF"
                str = "Notes-DefectivePole"
                iOffset = 30
            Case "NOTE-PRA"
                str = "Notes-PRA"
                iOffset = 30
            Case "NOTE-UEH"
                str = "Notes-UEH"
                iOffset = 30
            Case "NOTE-EC"
                str = "Notes-EC"
                iOffset = 40
            Case "NOTE-OTHER"
                str = "Notes-Other"
                iOffset = 30
            Case Else
                str = ""
        End Select
        
        If str = "" Then GoTo Next_I
        
        dNote(1) = dNote(1) + iOffset
        
        Set objBlock = ThisDrawing.ModelSpace.InsertBlock(dNote, str, dScale, dScale, dScale, 0#)
        objBlock.Layer = "Integrity Notes"
        objBlock.Update
        
Next_I:
    Next i
    
Exit_Sub:
    cbGetSPole.SetFocus
    Me.show
End Sub

Private Sub cbQuit_Click()
    If iUpdate = 1 Then
        Dim result As Integer
        
        result = MsgBox("Save changes to Structure?", vbYesNo, "Save Changes")
        If result = vbYes Then
            If objPole.Name = "sPole" Then
                Call SaveAttachments
            Else
                Call SaveBuried
            End If
    
            MsgBox objPole.Name & "  Updated."
        End If
        
        iUpdate = 0
    End If
    
    Me.Hide
End Sub

Private Sub cbUpdate_Click()
    If objPole.Name = "sPole" Then
        Call SaveAttachments
    Else
        Call SaveBuried
    End If
    
    MsgBox objPole.Name & "  Updated."
    iUpdate = 0
End Sub

Private Sub lbAttach_DblClick(ByVal Cancel As MSForms.ReturnBoolean)
    If lbAttach.ListCount < 0 Then Exit Sub
    
    Dim iIndex As Integer
    
    iIndex = lbAttach.ListIndex
    If iIndex < 0 Then Exit Sub
    
    cbAttachment.Value = lbAttach.List(iIndex, 0)
    tbEAttach.Value = lbAttach.List(iIndex, 1)
    tbPAttach.Value = lbAttach.List(iIndex, 2)
    
    lbAttach.Enabled = False
    cbAddAttach.Caption = "Update"
    
    iUpdate = 1
End Sub

Private Sub lbAttach_KeyDown(ByVal KeyCode As MSForms.ReturnInteger, ByVal Shift As Integer)
    If lbAttach.ListIndex < 0 Then Exit Sub
    
    Dim iIndex As Integer
    
    iIndex = lbAttach.ListIndex
    
    Select Case KeyCode
        Case vbKeyDelete
            cbAttachment.Value = lbAttach.List(iIndex, 0)
            tbEAttach.Value = lbAttach.List(iIndex, 1)
            tbPAttach.Value = lbAttach.List(iIndex, 2)
            
            lbAttach.RemoveItem iIndex
            iUpdate = 1
    End Select
End Sub

Private Sub lbData_DblClick(ByVal Cancel As MSForms.ReturnBoolean)
    Dim vLine As Variant
    
    vLine = Split(lbData.List(lbData.ListIndex, 0), "  ")
    cbDType.Value = vLine(1)
    tbDValue.Value = lbData.List(lbData.ListIndex, 1)
    
    cbAddData.Caption = "Update"
End Sub

Private Sub lbData_KeyDown(ByVal KeyCode As MSForms.ReturnInteger, ByVal Shift As Integer)
    If lbData.ListCount < 1 Then Exit Sub
    
    Select Case KeyCode
        Case vbKeyDelete
            lbData.RemoveItem lbData.ListIndex
        End Select
End Sub

Private Sub lbUnits_DblClick(ByVal Cancel As MSForms.ReturnBoolean)
    tbUnit.Value = lbUnits.List(lbUnits.ListIndex, 0)
    tbQuantity.Value = lbUnits.List(lbUnits.ListIndex, 1)
    tbUNote.Value = lbUnits.List(lbUnits.ListIndex, 2)
    
    lbUnits.Enabled = False
    cbAddUnit.Caption = "Update"
End Sub

Private Sub lbUnits_KeyDown(ByVal KeyCode As MSForms.ReturnInteger, ByVal Shift As Integer)
    If lbUnits.ListCount < 1 Then Exit Sub
    
    Dim iIndex As Integer
    iIndex = lbUnits.ListIndex
    
    Select Case KeyCode
        Case vbKeyDelete
            tbUnit.Value = lbUnits.List(iIndex, 0)
            tbQuantity.Value = lbUnits.List(iIndex, 1)
            tbUNote.Value = lbUnits.List(iIndex, 2)
            
            lbUnits.RemoveItem lbUnits.ListIndex
            iUpdate = 1
    End Select
End Sub

Private Sub UserForm_Initialize()
    iUpdate = 0
    
    lbData.ColumnCount = 2
    lbData.ColumnWidths = "60;180"
    
    lbAttach.ColumnCount = 4
    lbAttach.ColumnWidths = "84;36;36;84"
    
    lbUnits.ColumnCount = 3
    lbUnits.ColumnWidths = "96;36;48"
    
    cbDType.AddItem "Type"
    cbDType.AddItem "Owner #"
    cbDType.AddItem "Other #"
    cbDType.AddItem "Ground"
    
    cbAttachment.AddItem "NEUTRAL"
    cbAttachment.AddItem "TRANSFORMER"
    cbAttachment.AddItem "LOW POWER"
    cbAttachment.AddItem "ANTENNA"
    cbAttachment.AddItem "ST LT CIR"
    cbAttachment.AddItem "ST LT"
    cbAttachment.AddItem "NEW 6M"
    cbAttachment.AddItem "NEW 10M"
    cbAttachment.AddItem "CLEC"
    cbAttachment.AddItem "XO"
    cbAttachment.AddItem "ZAYO"
    cbAttachment.AddItem "LEVEL3"
    cbAttachment.AddItem "ATT"
    cbAttachment.AddItem "TDS"
    cbAttachment.AddItem "PWR OHG"
    cbAttachment.AddItem "NEW OHG"
    cbAttachment.AddItem "CLEC OHG"
    cbAttachment.AddItem "TELCO OHG"
    cbAttachment.AddItem "ATT OHG"
    cbAttachment.AddItem "TDS OHG"
    cbAttachment.AddItem "UTC OHG"
    cbAttachment.AddItem "OHG"
    
    cbScale.AddItem "50"
    cbScale.AddItem "75"
    cbScale.AddItem "100"
    cbScale.Value = "100"
    
    cbGetSPole.SetFocus
    
    If InStr(UCase(ThisDrawing.Path), "\NES") > 0 Then cbAttachments.Value = False
End Sub

Private Function GetMR(strE As String, strP As String)
    Dim vLine, vItem As Variant
    Dim strMR As String
    Dim iEF, iEI, iPF, iPI, iMR As Integer
    
    Select Case strE
        Case ""
            If InStr(cbAttachment.Value, "NEW") > 0 Then
                strMR = "NEW"
            Else
                strMR = "ATTACH"
            End If
        Case strP
            strMR = "TRANSFER"
        Case Else
            If strP = "" Then
                strMR = ""
            Else
                vLine = Split(strE, "-")
                iEF = CInt(vLine(0))
                iEI = CInt(vLine(1))
                iEI = iEF * 12 + iEI
            
                vLine = Split(strP, "-")
                iPF = CInt(vLine(0))
                iPI = CInt(vLine(1))
                iPI = iPF * 12 + iPI
            
                iMR = iPI - iEI
            
                If iMR > 0 Then
                    strMR = "RAISE " & iMR & """"
                Else
                    strMR = "LOWER " & Abs(iMR) & """"
                End If
            End If
    End Select
    
    GetMR = strMR
End Function

Private Sub SortAttachments()
    Dim strArrayList(), strArraySorted(), strData() As String
    Dim strListItem() As String     '<---------------------------------------------Sort
    'Dim attArray, attItem As Variant
    'Dim str1, str2 As String
    'Dim i, iDWGNum, test1, place1, temp1 As Integer
    Dim vLine As Variant
    Dim strTemp As String
    Dim iFeet, iInch As Integer
    'Dim tempFt, tempIn As Integer
    'Dim iNewFt, iNewIn As Integer
    Dim i As Integer
    
    'test1 = 0
    
    ReDim strData(0 To lbAttach.ListCount - 1)
    ReDim strListItem(0 To lbAttach.ListCount - 1)
    ReDim strArraySorted(0 To lbAttach.ListCount - 1)
    
    For i = 0 To UBound(strListItem)
        strListItem(i) = i
    Next i
    
    For i = 0 To UBound(strData)
        If lbAttach.List(i, 2) = "" Then
            vLine = Split(lbAttach.List(i, 1), "-")
        Else
            vLine = Split(lbAttach.List(i, 2), "-")
        End If
        
        iFeet = CInt(vLine(0))
        iInch = CInt(vLine(1)) + iFeet * 12
        
        strData(i) = iInch
    Next i
    
    'test1 = UBound(strData) - 1

    For i = UBound(strData) To (LBound(strData) + 1) Step -1
        For j = LBound(strData) To (i - 1)
            If CInt(strData(j)) < CInt(strData(j + 1)) Then
                strTemp = strData(j + 1)
                strData(j + 1) = strData(j)
                strData(j) = strTemp
                
                strTemp = strListItem(j + 1)
                strListItem(j + 1) = strListItem(j)
                strListItem(j) = strTemp
            End If
        Next j
    Next i
    
    For i = LBound(strListItem) To UBound(strListItem)
        strArraySorted(i) = lbAttach.List(strListItem(i), 0) & vbTab & lbAttach.List(strListItem(i), 1) & vbTab & lbAttach.List(strListItem(i), 2) & vbTab & lbAttach.List(strListItem(i), 3)
    Next i
        
    lbAttach.Clear
    For i = LBound(strListItem) To UBound(strListItem)
        vLine = Split(strArraySorted(i), vbTab)
        
        lbAttach.AddItem vLine(0)
        lbAttach.List(lbAttach.ListCount - 1, 1) = vLine(1)
        lbAttach.List(lbAttach.ListCount - 1, 2) = vLine(2)
        lbAttach.List(lbAttach.ListCount - 1, 3) = vLine(3)
    Next i
End Sub

Private Sub SaveBuried()
    Dim vAttList, vLine, vItem As Variant
    Dim strUnits As String
    
    vAttList = objPole.GetAttributes
    
    If lbData.ListCount > -1 Then
        For i = 0 To lbData.ListCount - 1
            'vLine = Split("", "=")
            Select Case lbData.List(i, 0)
                Case "1  Type"
                    vAttList(2).TextString = lbData.List(i, 1)
                Case "9  Ground"
                    vAttList(4).TextString = lbData.List(i, 1)
            End Select
        Next i
    End If
    
    strUnits = ""
    
    If lbUnits.ListCount > 0 Then
        strLine = "+" & lbUnits.List(0, 0) & "=" & lbUnits.List(0, 1)
        
        For i = 0 To lbUnits.ListCount - 1
            strLine = lbUnits.List(i, 0) & "=" & lbUnits.List(i, 1)
            If Not lbUnits.List(i, 2) = "" Then strLine = strLine & "  " & lbUnits.List(i, 2)
            
            If strUnits = "" Then
                strUnits = strLine
            Else
                strUnits = strUnits & ";;" & strLine
            End If
        Next i
    End If
    
    vAttList(7).TextString = strUnits
    
Exit_Sub:
    objPole.Update

End Sub

Private Sub SaveAttachments()
    If lbAttach.ListCount < 1 Then Exit Sub
    
    Dim strComm(8) As String
    Dim strLine, strExtra, strCO As String
    Dim strUnits As String
    Dim vAttList, vLine, vItem As Variant
    
    For i = 0 To 8
        strComm(i) = ""
    Next i
    
    vAttList = objPole.GetAttributes
    
    For i = 9 To 23
        vAttList(i).TextString = ""
    Next i
    
    For i = 0 To lbAttach.ListCount - 1
        strCO = lbAttach.List(i, 0)
        strLine = lbAttach.List(i, 1)
        If Not lbAttach.List(i, 2) = "" Then strLine = "(" & strLine & ")" & lbAttach.List(i, 2)
                   
        Select Case strCO
            Case "NEUTRAL"
                If vAttList(9).TextString = "" Then
                    vAttList(9).TextString = strLine
                Else
                    vAttList(9).TextString = vAttList(9).TextString & " " & strLine
                End If
            Case "TRANSFORMER"
                If vAttList(10).TextString = "" Then
                    vAttList(10).TextString = strLine
                Else
                    vAttList(10).TextString = vAttList(10).TextString & " " & strLine
                End If
            Case "LOW POWER"
                If vAttList(11).TextString = "" Then
                    vAttList(11).TextString = strLine
                Else
                    vAttList(11).TextString = vAttList(10).TextString & " " & strLine
                End If
            Case "ANTENNA"
                If vAttList(12).TextString = "" Then
                    vAttList(12).TextString = strLine
                Else
                    vAttList(12).TextString = vAttList(10).TextString & " " & strLine
                End If
            Case "ST LT CIRCUIT"
                If vAttList(13).TextString = "" Then
                    vAttList(13).TextString = strLine
                Else
                    vAttList(13).TextString = vAttList(10).TextString & " " & strLine
                End If
            Case "ST LT"
                If vAttList(14).TextString = "" Then
                    vAttList(14).TextString = strLine
                Else
                    vAttList(14).TextString = vAttList(10).TextString & " " & strLine
                End If
            Case Else
                If InStr(strCO, "NEW ") > 0 Then
                    If vAttList(15).TextString = "" Then
                        vAttList(15).TextString = lbAttach.List(i, 2)
                    Else
                        vAttList(15).TextString = vAttList(15).TextString & " " & lbAttach.List(i, 2)
                    End If
                    
                    If lbAttach.List(i, 3) = "MTE TAG" Then
                        vAttList(15).TextString = vAttList(15).TextString & "T"
                    End If
                    If lbAttach.List(i, 0) = "NEW OHG" Then
                        vAttList(15).TextString = vAttList(15).TextString & "O"
                    End If
                    If lbAttach.List(i, 3) = "FUTURE" Then
                        vAttList(15).TextString = vAttList(15).TextString & "F"
                    End If
                Else
                    If InStr(strCO, "C-WIRE") > 0 Then
                        strExtra = "c"
                        strCO = Replace(strCO, " C-WIRE", "")
                    End If
                
                    If InStr(strCO, "DROP") > 0 Then
                        strExtra = "d"
                        strCO = Replace(strCO, " DROP", "")
                    End If
                
                    If lbAttach.List(i, 3) = "EXTEND" Then
                        If strExtra = "" Then
                            strExtra = "e"
                        Else
                            strExtra = strExtra & "e"
                        End If
                    End If
                
                    If InStr(strCO, "OHG") > 0 Then
                        If strExtra = "" Then
                            strExtra = "o"
                        Else
                            strExtra = strExtra & "o"
                        End If
                        strCO = Replace(strCO, " OHG", "")
                    End If
                
                    If InStr(strCO, " SS") > 0 Then
                        strExtra = "s"
                        strCO = Replace(strCO, " SS", "")
                    End If
                
                    If InStr(strCO, "LASH TO ") > 0 Then
                        If strExtra = "" Then
                            strExtra = "v"
                        Else
                            strExtra = strExtra & "v"
                        End If
                        strCO = Replace(strCO, "LASH TO ", "")
                    End If
                
                    If InStr(strCO, " TAP") > 0 Then
                        If strExtra = "" Then
                            strExtra = "p"
                        Else
                            strExtra = strExtra & "p"
                        End If
                        strCO = Replace(strCO, " TAP", "")
                    End If
                
                    If Not lbAttach.List(i, 1) = "" Then
                        strLine = lbAttach.List(i, 1)
                    
                        If Not lbAttach.List(i, 2) = "" Then
                            strLine = "(" & strLine & ")" & lbAttach.List(i, 2) & strExtra
                        Else
                            strLine = strLine & strExtra
                        End If
                    
                        strExtra = ""
                    Else
                        strLine = lbAttach.List(i, 2) & strExtra & "x"
                        strExtra = ""
                    End If
                
                    For j = 1 To 8
                        vLine = Split(strComm(j), "=")
                        If strComm(j) = "" Then
                            strComm(j) = strCO & "=" & strLine
                            GoTo Found_strComm
                        End If
                    
                        If vLine(0) = strCO Then
                            strComm(j) = strComm(j) & " " & strLine
                            GoTo Found_strComm
                        End If
                    Next j
                
                    MsgBox "Comms full"
                    Exit Sub
                End If
Found_strComm:
        End Select
    Next i
    
    For i = 1 To 8
        vAttList(15 + i).TextString = strComm(i)
    Next i
    
    strCO = ""
    
    vAttList(2).TextString = tbOwner.Value
    vAttList(3).TextString = ""
    vAttList(4).TextString = ""
    
    
    If lbData.ListCount > -1 Then
        For i = 0 To lbData.ListCount - 1
            vLine = Split("", "=")
            Select Case lbData.List(i, 0)
                Case "1  Type"
                    vAttList(5).TextString = lbData.List(i, 1)
                Case "2  Owner #"
                    If vAttList(3).TextString = "" Then
                        vAttList(3).TextString = lbData.List(i, 1)
                    Else
                        vAttList(3).TextString = vAttList(3).TextString & " " & lbData.List(i, 1)
                    End If
                Case "3  Other #"
                    vLine = Split(lbData.List(i, 1), "=")
                    
                    If UBound(vLine) < 1 Then
                        vAttList(3).TextString = vAttList(3).TextString & " " & lbData.List(i, 1)
                    Else
                        If tbOwner.Value = vLine(0) Then
                            vAttList(3).TextString = vAttList(3).TextString & " " & lbData.List(i, 1)
                        Else
                            If vAttList(4).TextString = "" Then
                                vAttList(4).TextString = lbData.List(i, 1)
                            Else
                                vAttList(4).TextString = vAttList(4).TextString & " " & lbData.List(i, 1)
                            End If
                        End If
                    End If
                Case "9  Ground"
                    vAttList(8).TextString = lbData.List(i, 1)
            End Select
        Next i
    End If
    
    strUnits = ""
    
    If lbUnits.ListCount > 0 Then
        strLine = "+" & lbUnits.List(0, 0) & "=" & lbUnits.List(0, 1)
        
        For i = 0 To lbUnits.ListCount - 1
            strLine = lbUnits.List(i, 0) & "=" & lbUnits.List(i, 1)
            If Not lbUnits.List(i, 2) = "" Then strLine = strLine & "  " & lbUnits.List(i, 2)
            
            If strUnits = "" Then
                strUnits = strLine
            Else
                strUnits = strUnits & ";;" & strLine
            End If
        Next i
    End If
    
    vAttList(27).TextString = strUnits
    
Exit_Sub:
    objPole.Update
End Sub

Private Sub GetBuriedPlant()
    Dim vAttList, vLine As Variant
    Dim dTemp As Double
    
    dTemp = GetScale(objPole.InsertionPoint)
    If dTemp > 0 Then cbScale.Value = dTemp * 100
    
    vAttList = objPole.GetAttributes
    
    tbPoleNumber.Value = vAttList(0).TextString
    tbOwner.Value = "UTC"
    
    lbData.AddItem "1  Type"
    If vAttList(2).TextString = "" Then
        lbData.List(lbData.ListCount - 1, 1) = "?"
    Else
        lbData.List(lbData.ListCount - 1, 1) = vAttList(2).TextString
    End If
    
    lbData.AddItem "9  Ground"
    Select Case UCase(vAttList(4).TextString)
        Case "", "N"
            lbData.List(lbData.ListCount - 1, 1) = "NO GRD"
        Case "M"
            lbData.List(lbData.ListCount - 1, 1) = "MGN"
        Case "T"
            lbData.List(lbData.ListCount - 1, 1) = "TGB"
        Case "B"
            lbData.List(lbData.ListCount - 1, 1) = "BROKEN GRD"
        Case Else
            lbData.List(lbData.ListCount - 1, 1) = vAttList(4).TextString
    End Select
    
    If cbAddCoords.Value = True Then
        If Not vAttList(3).TextString = "" Then
            vLine = Split(vAttList(3).TextString, ",")
            
            dTemp = CLng(CDbl(vLine(0)) * 10000000) / 10000000
            strTemp = dTemp & ","
            
            dTemp = CLng(CDbl(vLine(1)) * 10000000) / 10000000
            strTemp = strTemp & dTemp
            
            lbData.AddItem "99  Lat,Long"
            lbData.List(lbData.ListCount - 1, 1) = strTemp
        End If
    End If
    
    If Not vAttList(7).TextString = "" Then
        vAttList(7).TextString = Replace(vAttList(7).TextString, vbLf, "")
        vLine = Split(vAttList(7).TextString, ";;")
        For i = 0 To UBound(vLine)
            If InStr(vLine(i), "=") = 0 Then vLine(i) = vLine(i) & "=1"
                
            vItem = Split(vLine(i), "=")
            lbUnits.AddItem vItem(0)
            If InStr(vItem(1), "  ") > 0 Then
                vTemp = Split(vItem(1), "  ")
                lbUnits.List(lbUnits.ListCount - 1, 1) = vTemp(0)
                lbUnits.List(lbUnits.ListCount - 1, 2) = vTemp(1)
            Else
                lbUnits.List(lbUnits.ListCount - 1, 1) = vItem(1)
                lbUnits.List(lbUnits.ListCount - 1, 2) = ""
            End If
        Next i
    End If
    
    cbUpdate.Enabled = True
    cbPlaceData.Enabled = True
    
    cbPlaceData.SetFocus
End Sub

Private Sub PlaceBuriedData()
    Dim returnPoint As Variant
    Dim insertionPnt(0 To 2) As Double
    Dim dRevCloud(0 To 5) As Double
    Dim dNote(0 To 2) As Double
    Dim dScale As Double
    Dim dPosition As Double
    Dim objBlock As AcadBlockReference
    Dim layerObj As AcadLayer
    Dim vAttList, vELine, vPLine As Variant
    Dim iPI, iEI As Integer
    Dim iMR, iNote As Integer
    Dim strAtt0, strAtt1, strAtt2, strAtt3, strAtt4 As String
    Dim strLayer As String
    
    Dim vStr As Variant
    Dim str, str1, strCommand As String
    Dim lwpPnt(0 To 3) As Double
    Dim lineObj As AcadLWPolyline
    Dim n, counter As Integer
    Dim vText, vLine As Variant
    
    
    strAtt0 = tbPoleNumber.Value
    'dPosition = 1#
    
    Me.Hide
    dScale = CInt(cbScale.Value) / 100
    
    returnPoint = ThisDrawing.Utility.GetPoint(, "Select point:")
    n = 0
    For Each Item In returnPoint
        insertionPnt(n) = Item
        n = n + 1
    Next Item
    
Place_Info:
    
    str = "pole_info"
    strLayer = "Integrity Pole-Info"

    'insertionPnt(0) = insertionPnt(0) - (74 * dScale)
    'insertionPnt(1) = insertionPnt(1) - (12 * dScale)
    
    dPosition = 0#
    
    Set objBlock = ThisDrawing.ModelSpace.InsertBlock(insertionPnt, str, dScale, dScale, dScale, 0)
    objBlock.Layer = strLayer
        
    vAttList = objBlock.GetAttributes
    vAttList(0).TextString = strAtt0
    vAttList(1).TextString = "0.0"
    vAttList(2).TextString = tbPoleNumber.Value
    objBlock.Update
    
    insertionPnt(1) = insertionPnt(1) - (9 * dScale)
    
    For w = 0 To lbData.ListCount - 1
        If lbData.List(w, 0) = "" Then GoTo Next_W
        
        vText = Split(lbData.List(w, 0), " ")
        strAtt1 = dPosition & "." & vText(0)
        
        Select Case vText(0)
            Case "1", "2"
                strAtt2 = lbData.List(w, 1)
                strAtt3 = ""
            'Case "3"
                'vLine = Split(lbData.List(w, 1), "=")
                
                'If UBound(vLine) > 0 Then
                    'strAtt2 = vLine(0)
                    'strAtt3 = vLine(1)
                'Else
                    'strAtt2 = tbOwner.Value
                    'strAtt3 = lbData.List(w, 1)
                'End If
            Case "9", "99"
                strAtt2 = lbData.List(w, 1)
                strAtt3 = ""
            Case Else
                GoTo Next_W
        End Select
    
        Set objBlock = ThisDrawing.ModelSpace.InsertBlock(insertionPnt, str, dScale, dScale, dScale, 0)
        objBlock.Layer = strLayer
        
        vAttList = objBlock.GetAttributes
        vAttList(0).TextString = strAtt0
        vAttList(1).TextString = strAtt1
        vAttList(2).TextString = strAtt2
        'vAttList(3).TextString = strAtt3
        vAttList(3).TextString = ""
        objBlock.Update
    
        insertionPnt(1) = insertionPnt(1) - (9 * dScale)
Next_W:
    Next w
    
    lwpPnt(0) = insertionPnt(0) - (4 * dScale)
    lwpPnt(1) = insertionPnt(1) + (7 * dScale)
    lwpPnt(2) = lwpPnt(0) + (100 * dScale)
    lwpPnt(3) = lwpPnt(1)
    
    Set lineObj = ThisDrawing.ModelSpace.AddLightWeightPolyline(lwpPnt)
    lineObj.Layer = strLayer
    lineObj.Update
    
Place_Units:
    If cbPlaceUnits.Value = False Then GoTo Exit_Sub
    If lbUnits.ListCount < 1 Then GoTo Exit_Sub
    str = "pole_unit"
    strLayer = "Integrity Pole-Units"
    
    dPosition = 2#
    
    insertionPnt(1) = insertionPnt(1) - (1 * dScale)
    
    For v = 0 To lbUnits.ListCount - 1
        strAtt1 = dPosition
        strAtt2 = "N/A"
        strAtt3 = lbUnits.List(v, 0) & "=" & lbUnits.List(v, 1)
        If Not lbUnits.List(v, 2) = "" Then strAtt3 = strAtt3 & "  " & lbUnits.List(v, 2)
    
        Set objBlock = ThisDrawing.ModelSpace.InsertBlock(insertionPnt, str, dScale, dScale, dScale, 0#)
        objBlock.Layer = strLayer
        
        vAttList = objBlock.GetAttributes
        vAttList(0).TextString = strAtt0
        vAttList(1).TextString = strAtt1
        vAttList(2).TextString = strAtt2
        vAttList(3).TextString = strAtt3
        objBlock.Update
    
        insertionPnt(1) = insertionPnt(1) - (9 * dScale)
    Next v
    
Exit_Sub:
    cbGetSPole.SetFocus
    Me.show
End Sub

Private Function GetScale(vCoords As Variant)
    Dim filterType, filterValue As Variant
    Dim grpCode(0) As Integer
    Dim grpValue(0) As Variant
    Dim objSS As AcadSelectionSet
    Dim objBlock As AcadBlockReference
    Dim vAttList As Variant
    Dim dMinX, dMaxX, dMinY, dMaxY As Double
    Dim dScale As Double
    
    On Error Resume Next
    
    grpCode(0) = 2
    grpValue(0) = "SS-11x17"
    filterType = grpCode
    filterValue = grpValue
    
    Set objSS = ThisDrawing.SelectionSets.Add("objSS")
    If Not Err = 0 Then
        Set objSS = ThisDrawing.SelectionSets.Item("objSS")
        objSS.Clear
    End If
    
    objSS.Select acSelectionSetAll, , , filterType, filterValue
    
    For Each objBlock In objSS
        dScale = objBlock.XScaleFactor
        dMinX = objBlock.InsertionPoint(0)
        dMaxX = dMinX + (1652 * dScale)
        
        dMinY = objBlock.InsertionPoint(1)
        dMaxY = dMinY + (1052 * dScale)
        
        If vCoords(0) > dMinX And vCoords(0) < dMaxX Then
            If vCoords(1) > dMinY And vCoords(1) < dMaxY Then
                dScale = dScale * 1.333333333
                GoTo Exit_Sub
            End If
        End If
    Next objBlock
    
    dScale = 0
    
Exit_Sub:
    objSS.Clear
    objSS.Delete
    'MsgBox dScale
    GetScale = dScale
End Function

Attribute VB_Name = "PlaceSPIDAPoles"
Attribute VB_Base = "0{985D4AA6-0486-4F19-AC56-9FC58F70AEF8}{A84654AF-D88F-4A4F-A4CF-5682DCA97869}"
Attribute VB_GlobalNameSpace = False
Attribute VB_Creatable = False
Attribute VB_PredeclaredId = True
Attribute VB_Exposed = False
Attribute VB_TemplateDerived = False
Attribute VB_Customizable = False
Private Sub cbGetList_Click()
    If tbPasted.Value = "" Then Exit Sub
    If cbLat.Value = "" Then Exit Sub
    If cbLong.Value = "" Then Exit Sub
    
    Dim vLine, vItem, vTemp As Variant
    Dim strLine As String
    Dim iIndex As Integer
    Dim iH, iC, iOwner, iYear, iLat, iLong, iFID As Integer
    
    iH = -1: iC = -1: iOwner = -1: iYear = -1
    iLat = -1: iLong = -1: iFID = -1
    
    If Not cbH.Value = "" Then
        vTemp = Split(cbH.Value, " - ")
        iH = CInt(vTemp(0))
    End If
    
    If Not cbC.Value = "" Then
        vTemp = Split(cbC.Value, " - ")
        iC = CInt(vTemp(0))
    End If
    
    If Not cbOwner.Value = "" Then
        vTemp = Split(cbOwner.Value, " - ")
        iOwner = CInt(vTemp(0))
    End If
    
    If Not cbYear.Value = "" Then
        vTemp = Split(cbYear.Value, " - ")
        iYear = CInt(vTemp(0))
    End If
    
    vTemp = Split(cbLat.Value, " - ")
    iLat = CInt(vTemp(0))
    
    vTemp = Split(cbLong.Value, " - ")
    iLong = CInt(vTemp(0))
    
    If Not cbFID.Value = "" Then
        vTemp = Split(cbFID.Value, " - ")
        iFID = CInt(vTemp(0))
    End If
    
    lbPoles.Clear
    
    strLine = Replace(tbPasted.Value, vbLf, "")
    vLine = Split(strLine, vbCr)
    
    For i = 0 To UBound(vLine)
        If InStr(vLine(i), ",") < 1 Then GoTo Next_line
        
        vItem = Split(vLine(i), ",")
        'If UBound(vItem) < 1 Then GoTo Next_Line
        If Not vItem(1) = "POLE" Then GoTo Next_line
        
        For j = 0 To UBound(vItem)
            vItem(j) = Replace(vItem(j), ";;", ",")
        Next j
        
        lbPoles.AddItem "POLE"
        iIndex = lbPoles.ListCount - 1
        If Not iH = -1 Or iC = -1 Then lbPoles.List(iIndex, 1) = vItem(iH) & "-" & vItem(iC)
        If Not iOwner = -1 Then lbPoles.List(iIndex, 2) = vItem(iOwner)
        If Not iYear = -1 Then lbPoles.List(iIndex, 3) = vItem(iYear)
        lbPoles.List(iIndex, 4) = vItem(iLat) & "," & vItem(iLong)
        If Not iFID = -1 Then lbPoles.List(iIndex, 5) = vItem(iFID)
        
Next_line:
    Next i
    
    tbListCount.Value = lbPoles.ListCount
End Sub

Private Sub cbPlace_Click()
    If lbPoles.ListCount < 1 Then Exit Sub
    
    Dim objBlock As AcadBlockReference
    Dim vAttList As Variant
    Dim vCoords, vNE As Variant
    Dim strLayer As String
    Dim dCoords(2) As Double
    
    For i = 0 To lbPoles.ListCount - 1
        vCoords = Split(lbPoles.List(i, 4), ",")
        vNE = LLtoTN83F(CDbl(vCoords(0)), CDbl(vCoords(1)))
        dCoords(0) = CDbl(vNE(1))
        dCoords(1) = CDbl(vNE(0))
        dCoords(2) = 0#
        
        Set objBlock = ThisDrawing.ModelSpace.InsertBlock(dCoords, "sPole", 1#, 1#, 1#, 0#)
        vAttList = objBlock.GetAttributes
        vAttList(0).TextString = lbPoles.List(i, 0)
        vAttList(1).TextString = "INCOMPLETE"
        If Not lbPoles.List(i, 2) = "" Then vAttList(2).TextString = lbPoles.List(i, 2)
        If Not lbPoles.List(i, 1) = "" Then vAttList(5).TextString = lbPoles.List(i, 1)
        If Not lbPoles.List(i, 3) = "" Then vAttList(6).TextString = lbPoles.List(i, 3)
        If Not lbPoles.List(i, 4) = "" Then vAttList(7).TextString = lbPoles.List(i, 4)
        If Not lbPoles.List(i, 5) = "" Then vAttList(24).TextString = "FID_" & lbPoles.List(i, 5)
        
        Select Case lbPoles.List(i, 2)
            Case "MTEMC", "NES"
                objBlock.Layer = "Integrity Poles-Power"
            Case Else
                objBlock.Layer = "Integrity Poles-Other"
        End Select
        
        objBlock.Update
    Next i
    
    MsgBox "Done."
End Sub

Private Sub tbPasted_Change()
    If tbPasted.Value = "" Then Exit Sub
    
    Dim vLine, vItem, vTemp As Variant
    Dim strLine As String
    Dim iIndex As Integer
    
    lbPoles.Clear
    
    tbPasted.Value = Replace(tbPasted.Value, """", "")
    strLine = Replace(tbPasted.Value, vbLf, "")
    vItem = Split(strLine, vbCr)
    vLine = Split(vItem(0), ",")
    
    For i = 0 To UBound(vLine)
        strLine = i & " - " & vLine(i)
        
        cbH.AddItem strLine
        cbC.AddItem strLine
        cbOwner.AddItem strLine
        cbYear.AddItem strLine
        cbLat.AddItem strLine
        cbLong.AddItem strLine
        cbFID.AddItem strLine
    Next i
    
    Select Case cbCompany.Value
        Case "MTE"
            If cbH.ListCount > 16 Then
                cbH.Value = cbH.List(5)
                cbC.Value = cbC.List(4)
                cbOwner.Value = cbOwner.List(12)
                cbYear.Value = cbYear.List(16)
                cbLat.Value = cbLat.List(2)
                cbLong.Value = cbH.List(3)
                cbFID.Value = cbH.List(8)
            End If
        Case Else
            If cbH.ListCount > 16 Then
                cbH.Value = cbH.List(11)
                cbC.Value = cbC.List(10)
                cbOwner.Value = cbOwner.List(12)
                cbYear.Value = ""
                cbLat.Value = cbLat.List(2)
                cbLong.Value = cbH.List(3)
                cbFID.Value = cbH.List(0)
            End If
    End Select
End Sub

Private Sub UserForm_Initialize()
    lbPoles.ColumnCount = 6
    lbPoles.ColumnWidths = "48;72;60;48;144;114"
    
    cbCompany.AddItem "MTE"
    cbCompany.AddItem "NES"
    cbCompany.Value = "NES"
End Sub

Private Function LLtoTN83F(dLat As Double, dLong As Double)
    Dim dDLat As Double
    Dim dEast, dDiffE, dEast0 As Double
    Dim dNorth, dDiffN, dNorth0 As Double
    Dim dU, dR, dCA, dK As Double
    Dim NE(2) As Double
    
    dDLat = dLat - 35.8340607459
    dU = dDLat * (110950.2019 + dDLat * (9.25072 + dDLat * (5.64572 + dDLat * 0.017374)))
    dR = 8842127.1422 - dU
    dCA = ((86 + dLong) * 0.585439726459) * 3.14159265359 / 180
    
    dDiffE = dR * Sin(dCA)
    dDiffN = dU + dDiffE * Tan(dCA / 2)
    
    dEast = (dDiffE + 600000) / 0.3048006096
    dNorth = (dDiffN + 166504.1691) / 0.3048006096
    
    dK = 0.999948401424 + (1.23188E-14 * dU * dU) + (4.54E-22 * dU * dU * dU)
    
    NE(0) = dNorth
    NE(1) = dEast
    NE(2) = dK
    
    LLtoTN83F = NE
End Function

Attribute VB_Name = "PlaceToCO"
Attribute VB_Base = "0{3FAE0674-FA46-4475-9738-E851826974F7}{2C86DAAF-F027-43C5-90EF-D4394254D120}"
Attribute VB_GlobalNameSpace = False
Attribute VB_Creatable = False
Attribute VB_PredeclaredId = True
Attribute VB_Exposed = False
Attribute VB_TemplateDerived = False
Attribute VB_Customizable = False
Private Sub cbPlaceBlock_Click()
    Dim objBlock As AcadBlockReference
    Dim vAttList As Variant
    Dim strName As String
    Dim vBasePnt, vReturnPnt As Variant
    Dim dInsert(2) As Double
    Dim dDiffX, dDiffY, dZ As Double
    Dim dRotate, dRatio As Double
    
    On Error Resume Next
    Me.Hide
    
Add_Callout:
    Err = 0
    
    vBasePnt = ThisDrawing.Utility.GetPoint(, "Select First Point: ")
    If Not Err = 0 Then GoTo Exit_Sub
    
    vReturnPnt = ThisDrawing.Utility.GetPoint(vBasePnt, "Select First Point: ")
    If Not Err = 0 Then GoTo Exit_Sub
    
    dDiffX = vReturnPnt(0) - vBasePnt(0)
    dDiffY = vReturnPnt(1) - vBasePnt(1)
    dZ = Sqr((dDiffX * dDiffX) + (dDiffY * dDiffY))
    dRatio = 40.8076 / dZ
    
    vReturnPnt(0) = vBasePnt(0) + (dDiffX * dRatio)
    vReturnPnt(1) = vBasePnt(1) + (dDiffY * dRatio)
    
    
    Select Case dDiffX
        Case Is > 0
            strName = "ToLOCr"
            dInsert(0) = vBasePnt(0)
            dInsert(1) = vBasePnt(1)
            dInsert(2) = 0#
            
            dRotate = Atn(dDiffY / dDiffX)
        Case Is = 0
            Select Case dDiffY
                Case Is > 0
                    strName = "ToLOCr"
                    dInsert(0) = vBasePnt(0)
                    dInsert(1) = vBasePnt(1)
                    dInsert(2) = 0#
            
                    dRotate = 1.5707963267949
                Case Is = 0
                    strName = "ToLOCl"
                    dInsert(0) = vBasePnt(0)
                    dInsert(1) = vBasePnt(1)
                    dInsert(2) = 0#
            
                    dRotate = 0
                Case Is < 0
                    strName = "ToLOCl"
                    dInsert(0) = vBasePnt(0)
                    dInsert(1) = vBasePnt(1)
                    dInsert(2) = 0#
            
                    dRotate = 1.5707963267949
            End Select
        Case Is < 0
            strName = "ToLOCl"
            dInsert(0) = vBasePnt(0)
            dInsert(1) = vBasePnt(1)
            dInsert(2) = 0#
            
            dDiffX = 0 - dDiffX
            dDiffY = 0 - dDiffY
            dRotate = Atn(dDiffY / dDiffX) - 3.14159265359
    End Select
    
    Set objBlock = ThisDrawing.ModelSpace.InsertBlock(dInsert, strName, 1#, 1#, 1#, dRotate)
    vAttList = objBlock.GetAttributes
    vAttList(0).TextString = "TO " & cbTo.Value
    vAttList(1).TextString = tbName.Value
    
    objBlock.Layer = "Integrity Sheets"
    objBlock.Update
    
    GoTo Add_Callout
    
Exit_Sub:
    Me.show
End Sub

Private Sub UserForm_Initialize()
    cbTo.AddItem "C.O."
    cbTo.AddItem "RST"
    cbTo.AddItem "FDH"
    cbTo.Value = "C.O."
End Sub

Attribute VB_Name = "PoleOwnerNote"
Attribute VB_Base = "0{C5AE733D-CBD1-471D-A641-7094EB220143}{A6CAF3C9-850F-4D34-8E46-9BA9B18946F7}"
Attribute VB_GlobalNameSpace = False
Attribute VB_Creatable = False
Attribute VB_PredeclaredId = True
Attribute VB_Exposed = False
Attribute VB_TemplateDerived = False
Attribute VB_Customizable = False
Dim vPnt1, vPnt2 As Variant

Private Sub cbGetPoles_Click()
    Dim objSS As AcadSelectionSet
    Dim filterType, filterValue As Variant
    Dim grpCode(0) As Integer
    Dim grpValue(0) As Variant
    'Dim vPnt1, vPnt2 As Variant
    Dim objBlock As AcadBlockReference
    Dim vAttList As Variant
    Dim vLine, vItem, vTemp As Variant

    grpCode(0) = 2
    grpValue(0) = "sPole"
    filterType = grpCode
    filterValue = grpValue
    
  On Error Resume Next
  
    Me.Hide
    
    vPnt1 = ThisDrawing.Utility.GetPoint(, "Get BL Corner: ")
    vPnt2 = ThisDrawing.Utility.GetCorner(vPnt1, vbCr & "Get UR Corner: ")
  
    Err = 0
    
    Set objSS = ThisDrawing.SelectionSets.Add("objSS")
    If Not Err = 0 Then
        Set objSS = ThisDrawing.SelectionSets.Item("objSS")
        Err = 0
    End If
    
    objSS.Select acSelectionSetWindow, vPnt1, vPnt2, filterType, filterValue
    If Not Err = 0 Then
        MsgBox "Error: " & Err.Number & vbCr & Err.Description
        Me.show
        Exit Sub
    End If
    
    For Each objBlock In objSS
        vAttList = objBlock.GetAttributes
        If vAttList(0).TextString = "" Then GoTo Next_objBlock
        If vAttList(0).TextString = "POLE" Then GoTo Next_objBlock
        If vAttList(1).TextString = "INCOMPLETE" Then GoTo Next_objBlock
        
        If lbOwner.ListCount > 0 Then
            For i = 0 To lbOwner.ListCount - 1
                If lbOwner.List(i, 0) = vAttList(2).TextString Then
                    lbOwner.List(i, 1) = CInt(lbOwner.List(i, 1)) + 1
                    GoTo Next_objBlock
                End If
            Next i
        End If
        
        lbOwner.AddItem vAttList(2).TextString
        lbOwner.List(lbOwner.ListCount - 1, 1) = "1"
        
Next_objBlock:
    Next objBlock
    
Exit_Sub:
    objSS.Clear
    objSS.Delete
    Me.show
End Sub

Private Sub cbPlaceNotes_Click()
    If lbOwner.ListIndex < 0 Then Exit Sub
    
    Dim objLayer As AcadLayer
    Dim objSSPole As AcadSelectionSet
    Dim objSSInfo As AcadSelectionSet
    Dim filterType, filterValue As Variant
    Dim grpCode(0) As Integer
    Dim grpValue(0) As Variant
    Dim objPole As AcadBlockReference
    Dim objInfo As AcadBlockReference
    Dim objMText As AcadMText
    Dim objLWP As AcadLWPolyline
    Dim vAttList As Variant
    Dim vAttPole As Variant
    Dim vAttInfo As Variant
    Dim strOwner, strNote As String
    Dim vCoords As Variant
    Dim dCoords(0 To 2) As Double
    Dim dBorder(0 To 9) As Double
    Dim dWidth, dScale As Double
    Dim vMinExt, vMaxExt As Variant
    
  On Error Resume Next
    Set objLayer = ThisDrawing.Layers.Add("Integrity Pole-Owner")
    If Err = 0 Then
        objLayer.color = acRed
    Else
        Err = 0
    End If
    
    Set objSSPole = ThisDrawing.SelectionSets.Add("objSSpole")
    If Not Err = 0 Then
        Set objSSPole = ThisDrawing.SelectionSets.Item("objSSpole")
        Err = 0
    End If

    grpCode(0) = 2
    grpValue(0) = "sPole"
    filterType = grpCode
    filterValue = grpValue
    
    objSSPole.Select acSelectionSetWindow, vPnt1, vPnt2, filterType, filterValue
    If Not Err = 0 Then
        MsgBox "Error: " & Err.Number & vbCr & Err.Description
        Me.show
        Exit Sub
    End If
    
    Set objSSInfo = ThisDrawing.SelectionSets.Add("objSSinfo")
    If Not Err = 0 Then
        Set objSSInfo = ThisDrawing.SelectionSets.Item("objSSinfo")
        Err = 0
    End If

    grpCode(0) = 2
    grpValue(0) = "pole_info"
    filterType = grpCode
    filterValue = grpValue
    
    objSSInfo.Select acSelectionSetWindow, vPnt1, vPnt2, filterType, filterValue
    If Not Err = 0 Then
        MsgBox "Error: " & Err.Number & vbCr & Err.Description
        Me.show
        Exit Sub
    End If
    
    strOwner = lbOwner.List(lbOwner.ListIndex)
    
    'MsgBox "Poles: " & objSSPole.count & vbCr & "Info: " & objSSInfo.count
    
    For Each objInfo In objSSInfo
        vAttInfo = objInfo.GetAttributes
        
        If Not vAttInfo(1).TextString = "0.1" Then GoTo Next_objInfo
        If Not vAttInfo(2).TextString = strOwner Then GoTo Next_objInfo
        
        'MsgBox vAttInfo(1).TextString & vbCr & vAttInfo(2).TextString
        
        dScale = objInfo.XScaleFactor
        vCoords = objInfo.InsertionPoint
        dCoords(0) = vCoords(0) + (90 * dScale)
        dCoords(1) = vCoords(1)
        dCoords(2) = 0#
        
        If cbFormat.Value = "POLE" Then
            strNote = strOwner & " POLE"
            GoTo Place_Note
        End If
        
        For Each objPole In objSSPole
            vAttPole = objPole.GetAttributes
            
            If vAttPole(0).TextString = vAttInfo(0).TextString Then
                If Not vAttPole(15).TextString = "" Then
                    strNote = strOwner & " NEW"
                    GoTo Place_Note
                End If
                
                If cbFormat.Value = "NEW / LASH" Then
                    strNote = strOwner & " LASH"
                    GoTo Place_Note
                End If
            End If
        Next objPole
        
        GoTo Next_objInfo
        
Place_Note:
        
        Set objMText = ThisDrawing.ModelSpace.AddMText(dCoords, 0, strNote)
        objMText.Layer = "Integrity Pole-Owner"
        objMText.Height = (6 * dScale)
        objMText.AttachmentPoint = acAttachmentPointBottomLeft
        objMText.InsertionPoint = dCoords
        objMText.Rotation = 0#
        'objMText.BackgroundFill = True
        objMText.Update
        
        If InStr(strNote, "LASH") > 0 Then GoTo Next_objInfo
        
        objMText.GetBoundingBox vMinExt, vMaxExt
        dWidth = vMaxExt(0) - vMinExt(0)
        
        dBorder(0) = dCoords(0) - (2 * dScale)
        dBorder(1) = dCoords(1) - (2 * dScale)
        dBorder(2) = dBorder(0) + dWidth + (4 * dScale)
        dBorder(3) = dBorder(1)
        dBorder(4) = dBorder(2)
        dBorder(5) = dBorder(1) + (10 * dScale)
        dBorder(6) = dBorder(0)
        dBorder(7) = dBorder(5)
        dBorder(8) = dBorder(0)
        dBorder(9) = dBorder(1)
        
    
        Set objLWP = ThisDrawing.ModelSpace.AddLightWeightPolyline(dBorder)
        objLWP.Layer = "Integrity Pole-Owner"
        objLWP.Update
        
Next_objInfo:
    Next objInfo
    
    
Exit_Sub:
    objSSPole.Clear
    objSSPole.Delete
    objSSInfo.Clear
    objSSInfo.Delete
    'Me.show
End Sub

Private Sub cbQuit_Click()
    Me.Hide
End Sub

Private Sub UserForm_Initialize()
    lbOwner.ColumnCount = 2
    lbOwner.ColumnWidths = "96;30"
    
    cbFormat.AddItem "POLE"
    cbFormat.AddItem "NEW"
    cbFormat.AddItem "NEW / LASH"
    cbFormat.Value = "NEW"
    
    tbFormat.Value = "<OWNER> NEW"
End Sub

Attribute VB_Name = "PonVHLE"
Attribute VB_Base = "0{A601148D-2465-4E27-8593-65ED6DB4A1FC}{65388EA9-2150-48FF-A748-D3D816E081A0}"
Attribute VB_GlobalNameSpace = False
Attribute VB_Creatable = False
Attribute VB_PredeclaredId = True
Attribute VB_Exposed = False
Attribute VB_TemplateDerived = False
Attribute VB_Customizable = False

Private Sub cbBGetBldg_Click()
    tbRES.Value = GetBlockCount("Integrity Building-RES")
    tbChurch.Value = GetBlockCount("Integrity Building-CHURCH") + GetBlockCount("Integrity Building-CHU")
    tbTRL.Value = GetBlockCount("Integrity Building-TRLR")
    tbMDU.Value = GetBlockCount("Integrity Building-MDU")
    tbBUS.Value = GetBlockCount("Integrity Building-BUS")
    tbSchool.Value = GetBlockCount("Integrity Building-SCH")
    tbSG.Value = GetBlockCount("Integrity SmartGrid")
    
    tbRESTot.Value = CInt(tbRES.Value) + CInt(tbChurch.Value) + CInt(tbSG.Value)
    If cbTRL Then
        tbRESTot.Value = CInt(tbRESTot.Value) + CInt(tbTRL.Value)
    End If
    If cbMDU Then
        tbRESTot.Value = CInt(tbRESTot.Value) + CInt(tbMDU.Value)
    End If
    
    tbBUSTot.Value = CInt(tbBUS.Value) + CInt(tbSchool.Value)
    tbMeters.Value = CInt(tbRESTot.Value) + CInt(tbBUSTot.Value)
End Sub

Private Sub cbClearForm_Click()
    Call ClearAll
End Sub

Private Sub cbGetInfo_Click()
    Dim iRESTotal, iBUSTotal, iTotal As Integer
    Dim lAC, lACoil, lBC, lBCoil, lATotal, lBTotal As Long
    
    iRes = 0: iChurch = 0: iTRL = 0: iMDU = 0: iBus = 0: iSchool = 0
    lAC = 0: lACoil = 0: lATotal = 0
    lBC = 0: lBCoil = 0: lBTotal = 0
        
    tbRES.Value = GetBlockCount("Integrity Building-RES")
    tbChurch.Value = GetBlockCount("Integrity Building-CHURCH") + GetBlockCount("Integrity Building-CHU")
    tbTRL.Value = GetBlockCount("Integrity Building-TRLR")
    tbMDU.Value = GetBlockCount("Integrity Building-MDU")
    tbBUS.Value = GetBlockCount("Integrity Building-BUS")
    tbSchool.Value = GetBlockCount("Integrity Building-SCH")
    tbSG.Value = GetBlockCount("Integrity SmartGrid")
    
    tbRESTot.Value = CInt(tbRES.Value) + CInt(tbChurch.Value) + CInt(tbSG.Value)
    If cbTRL Then
        tbRESTot.Value = CInt(tbRESTot.Value) + CInt(tbTRL.Value)
    End If
    If cbMDU Then
        tbRESTot.Value = CInt(tbRESTot.Value) + CInt(tbMDU.Value)
    End If
    
    tbBUSTot.Value = CInt(tbBUS.Value) + CInt(tbSchool.Value)
    tbMeters.Value = CInt(tbRESTot.Value) + CInt(tbBUSTot.Value)
    
    Call GetCables
    Call GetCoils
    
    tbACTotal.Value = CLng(tbAC.Value) + CLng(tbACE.Value) + CLng(tbACoil.Value)
    tbBCTotal.Value = CLng(tbBC.Value) + CLng(tbBCE.Value) + CLng(tbBCoil.Value)
End Sub

Private Sub cbGetPolygon_Click()
    Dim objSS As AcadSelectionSet
    Dim objEntity As AcadEntity
    Dim objLWP As AcadLWPolyline
    Dim objBlock As AcadBlockReference
    Dim vReturnPnt As Variant
    Dim vAttList, vTemp As Variant
    Dim vCoords, vArray As Variant
    Dim dCoords() As Double
    Dim iRes, iBus, iSG, iTemp, iCounter As Integer
    Dim iChurch, iSchool, iTRL, iMDU As Integer
    Dim lADrop, lBDrop As Long
    Dim lRouteFeet, iPoles As Long
    Dim iRouteMile, iRouteKF As Double
    Dim iDistance, iGuy, iClosure As Integer
    Dim iRESTotal, iBUSTotal, iSpans As Integer
    Dim strUnit, strTemp As String
    Dim lACT, lACM, lACE, lACL As Long
    Dim lBCT, lBCM, lBCE, lBCL As Long
    Dim lUCT, lUCM, lUCE, lUCL As Long
    Dim iSkip As Integer
    
    iRes = 0: iChurch = 0: iTRL = 0: iMDU = 0
    iBus = 0: iSchool = 0: iSG = 0: iGuy = 0
    iClosure = 0: lADrop = 0: lBDrop = 0
    iPoles = 0: iSpans = 1
    
    lACT = 0: lACM = 0: lACE = 0: lACL = 0
    lBCT = 0: lBCM = 0: lBCE = 0: lBCL = 0
    lUCT = 0: lUCM = 0: lUCE = 0: lUCL = 0
    
    On Error Resume Next
    
    Me.Hide
    
    ThisDrawing.Utility.GetEntity objEntity, vReturnPnt, "Select PON Border: "
    If Not objEntity.ObjectName = "AcDbPolyline" Then
        MsgBox "Error: Invalid Selection."
        Me.show
        Exit Sub
    End If
    
    Call ClearAll
    
    Set objLWP = objEntity
    vCoords = objLWP.Coordinates
    
    iTemp = (UBound(vCoords) + 1) / 2 * 3 - 1
    ReDim dCoords(iTemp) As Double
    
    iCounter = 0
    For i = 0 To UBound(vCoords) Step 2
        dCoords(iCounter) = vCoords(i)
        iCounter = iCounter + 1
        dCoords(iCounter) = vCoords(i + 1)
        iCounter = iCounter + 1
        dCoords(iCounter) = 0#
        iCounter = iCounter + 1
    Next i
    
    Err = 0
    Set objSS = ThisDrawing.SelectionSets.Add("objSS")
    If Not Err = 0 Then Set objSS = ThisDrawing.SelectionSets.Item("objSS")
    
    objSS.SelectByPolygon acSelectionSetWindowPolygon, dCoords
    
    For Each objEntity In objSS
        If TypeOf objEntity Is AcadBlockReference Then
            Set objBlock = objEntity
            If objBlock.Layer = "Integrity Existing" Then GoTo Next_objEntity
            vAttList = objBlock.GetAttributes
            
            Select Case objBlock.Name
                Case "Customer"
                    Select Case vAttList(5).TextString
                        Case "", "R"
                            iRes = iRes + 1
                        Case "B"
                            iBus = iBus + 1
                        Case "C"
                            iChurch = iChurch + 1
                        Case "M"
                            iMDU = iMDU + 1
                        Case "S"
                            iSchool = iSchool + 1
                        Case "T"
                            iTRL = iTRL + 1
                    End Select
                'Case "RES", "LOT"
                    'iRes = iRes + 1
                'Case "CHURCH"
                    'iChurch = iChurch + 1
                'Case "TRLR"
                    'iTRL = iTRL + 1
                'Case "MDU"
                    'iMDU = iMDU + 1
                'Case "BUSINESS"
                    'iBus = iBus + 1
                'Case "SCHOOL"
                    'iSchool = iSchool + 1
                Case "SG"
                    iSG = iSG + 1
                Case "cable_span"
                    'iSpans = iSpans + 1
                    
                    If CInt(Left(vAttList(2).TextString, 1)) = 0 Then
                        strTemp = vAttList(2).TextString
                        Select Case Left(strTemp, 1)
                            Case "+"
                                vTemp = Split(strTemp, "'")
                                iDistance = CInt(Replace(vTemp(0), "+", ""))
                                strUnit = "BFO(" & Replace(vAttList(1).TextString, "F", "") & ")D"
                                lBCE = lBCE + iDistance
                                Call AddUnitToTab("BM81", 1)
                            Case Else
                                vTemp = Split(strTemp, "=")
                                strUnit = vTemp(0)
                                iDistance = CInt(Replace(vTemp(1), "'", ""))
                        End Select
                        
                        Call AddUnitToTab(CStr(strUnit), CInt(iDistance))
                        GoTo Next_objEntity
                    End If
                    
                    iDistance = CInt(Replace(vAttList(2).TextString, "'", ""))
                    lRouteFeet = lRouteFeet + iDistance
                    
                    strTemp = Replace(vAttList(1).TextString, "F", "")
                    If strTemp = "" Then strTemp = "??"
                    vTemp = Split(strTemp, " ")
                    
                    iSkip = 0
                    If UBound(vTemp) > 0 Then
                        If vTemp(0) = "" Then
                            iSkip = 1
                        End If
                    End If
                    
                    Select Case objBlock.Layer
                        Case "Integrity Cable-UG Text", "Integrity Proposed-Buried"
                            strTemp = "UO("
                            strUnit = strTemp & vTemp(0) & ")"
                            If iSkip = 0 Then Call AddUnitToTab(CStr(strUnit), CInt(iDistance))
                            If iSkip = 0 Then lUCM = lUCM + iDistance
                            If iSkip = 0 Then Call AddUnitToTab("UD(1X1-4)", CInt(iDistance))
                        Case "Integrity Cable-Buried Text"
                            strTemp = "BFO("
                            strUnit = strTemp & vTemp(0) & ")"
                            If iSkip = 0 Then Call AddUnitToTab(CStr(strUnit), CInt(iDistance))
                            If iSkip = 0 Then lBCM = lBCM + iDistance
                        Case Else
                            iSpans = iSpans + 1
                            strTemp = "CO("
                            strUnit = strTemp & vTemp(0) & ")M"
                            If iSkip = 0 Then Call AddUnitToTab(CStr(strUnit), CInt(iDistance))
                            If iSkip = 0 Then lACM = lACM + iDistance
                    End Select
                    
                    If UBound(vTemp) = 0 Then GoTo Next_objEntity
                    
                    For n = 1 To UBound(vTemp)
                        Select Case strTemp
                            Case "UO("
                                strUnit = strTemp & vTemp(n) & ")"
                                Call AddUnitToTab(CStr(strUnit), CInt(iDistance))
                                lUCE = lUCE + iDistance
                                
                                If iSkip = 1 Then
                                    Call AddUnitToTab("RRUD", CInt(iDistance))
                                    iSkip = 0
                                End If
                            Case "BFO("
                                strUnit = strTemp & vTemp(n) & ")D"
                                Call AddUnitToTab(CStr(strUnit), CInt(iDistance))
                                lBCE = lBCE + iDistance
                            Case Else
                                strUnit = strTemp & vTemp(n) & ")E"
                                Call AddUnitToTab(CStr(strUnit), CInt(iDistance))
                                lACE = lACE + iDistance
                        End Select
                    Next n
                    
                Case "Map splice", "iClosure"
                    
                    iClosure = iClosure + 1
                    
                    Select Case objBlock.Layer
                        Case "Integrity Map Splices-Aerial"
                            strUnit = "HACO(" & vAttList(0).TextString & ")"
                        Case Else
                            strUnit = "HBFO(" & vAttList(0).TextString & ")"
                    End Select
                    
                    Call AddUnitToTab(CStr(strUnit), 1)
                    
                Case "Map coil"
                    'iClosure = iClosure + 1
                    
                    iDistance = CInt(Replace(vAttList(0).TextString, "'", ""))
                    
                    Select Case objBlock.Layer
                        Case "Integrity Map Coils-Aerial"
                            strUnit = "CO(" & Replace(vAttList(1).TextString, "F", "") & ") LOOP"
                            lACL = lACL + iDistance
                            Call AddUnitToTab("PM52", 1)
                        Case "Integrity Map Coils-Buried"
                            strUnit = "BFO(" & Replace(vAttList(1).TextString, "F", "") & ") LOOP"
                            lBCL = lBCL + iDistance
                        Case Else
                            strUnit = "UO(" & Replace(vAttList(1).TextString, "F", "") & ") LOOP"
                            lUCL = lUCL + iDistance
                    End Select
                    
                    'MsgBox strUnit & vbCr & iDistance
                    Call AddUnitToTab(CStr(strUnit), CInt(iDistance))
                    
                Case "Drop"
                    iDistance = CInt(Replace(vAttList(1).TextString, "'", ""))
                    Select Case vAttList(0).TextString
                        Case "SEBO"
                            lBDrop = lBDrop + iDistance
                            strUnit = "SEBO"
                        Case Else
                            lADrop = lADrop + iDistance
                            strUnit = "SEAO"
                    End Select
                    
                    Call AddUnitToTab(CStr(strUnit), CInt(iDistance))
                    
                Case "ohgL", "ohgR"
                    iSpans = iSpans + 1
                    
                    iDistance = CInt(Replace(vAttList(0).TextString, "'", ""))
                    strUnit = vAttList(1).TextString
                    
                    Call AddUnitToTab(CStr(strUnit), CInt(iDistance))
                    Call AddUnitToTab(CStr("{O} OHG"), 1)
                    
                Case "ExGuyOL", "ExGuyOR"
                    iGuy = iGuy + 1
                    
                    If UBound(vAttList) = 6 Then
                        strUnit = vAttList(3).TextString
                    Else
                        strUnit = vAttList(2).TextString
                    End If
                    
                    Call AddUnitToTab(CStr(strUnit), 1)
                    Call AddUnitToTab(CStr("PM11"), 1)
                    
                Case "ExAncOL", "ExAncOR"
                    If UBound(vAttList) = 4 Then
                        strUnit = vAttList(0).TextString
                    Else
                        strUnit = "PF"
                    End If
                    
                    Call AddUnitToTab(CStr(strUnit), 1)
                    
                Case "__Trim"
                    vTemp = Split(vAttList(0).TextString, "=")
                    iDistance = CInt(Replace(vTemp(1), "'", ""))
                    strUnit = "R3-5"
                    
                    Call AddUnitToTab(CStr(strUnit), CInt(iDistance))
                Case "iPole"
                    If vAttList(0).TextString = "" Then GoTo Next_objEntity
                    If vAttList(0).TextString = "POLE" Then GoTo Next_objEntity
                    
                    iPoles = iPoles + 1
                    
                    If vAttList(2).TextString = "" Then
                        strUnit = "{P} ??"
                    Else
                        strUnit = "{P} " & vAttList(2).TextString
                    End If
                    
                    Call AddUnitToTab(CStr(strUnit), 1)
                    
                    If Not vAttList(8).TextString = "" Then
                        Call AddUnitToTab("PM2A", 1)
                        
                        If vAttList(8).TextString = "B" Then
                            Call AddUnitToTab("PM2R", 1)
                        End If
                    End If
                Case "iLHH", "dHH"
                    strUnit = vAttList(1).TextString
                    Call AddUnitToTab(CStr(strUnit), 1)
                Case "iLPED", "PED"
                    strUnit = vAttList(1).TextString
                    Call AddUnitToTab(CStr(strUnit), 1)
                Case "FP", "dFP"
                    Call AddUnitToTab("FP", 1)
            End Select
Next_objEntity:
        Set objBlock = Nothing
        End If
    Next objEntity
    
    objSS.Clear
    objSS.Delete
    
    If iSpans = 1 Then
        iSpans = 0
    Else
        Call AddUnitToTab("{P}  Poles", CInt(iSpans))
    End If
    
    lACT = lACM + lACE + lACL
    lBCT = lBCM + lBCE + lBCL
    lUCT = lUCM + lUCE + lUCL
    
    tbACTotal.Value = lACT
    tbAC.Value = lACM
    tbACE.Value = lACE
    tbACoil.Value = lACL
    
    tbBCTotal.Value = lBCT
    tbBC.Value = lBCM
    tbBCE.Value = lBCE
    tbBCoil.Value = lBCL
    
    tbUCTotal.Value = lUCT
    tbUC.Value = lUCM
    tbUCE.Value = lUCE
    tbUCoil.Value = lUCL

    tbAD.Value = lADrop
    tbBD.Value = lBDrop
    
    tbRouteMiles.Value = CLng(lRouteFeet * 1000 / 5280) / 1000
    tbRouteKF.Value = lRouteFeet / 1000
    tbPoles.Value = iSpans
    'tbPoles.Value = iPoles
    
    tbTerminals.Value = iClosure
    tbGuys.Value = iGuy
        
    tbRES.Value = iRes
    tbChurch.Value = iChurch
    tbTRL.Value = iTRL
    tbMDU.Value = iMDU
    tbBUS.Value = iBus
    tbSchool.Value = iSchool
    tbSG.Value = iSG
    
    iRESTotal = iRes + iChurch + iSG
    If cbTRL.Value Then iRESTotal = iRESTotal + iTRL
    If cbMDU.Value Then iRESTotal = iRESTotal + iMDU
    tbRESTot.Value = iRESTotal
    
    tbBUSTot.Value = CInt(tbBUS.Value) + CInt(tbSchool.Value)
    tbMeters.Value = CInt(tbRESTot.Value) + CInt(tbBUSTot.Value)
    
    'Call GetCables
    'Call GetCoils
    
    'tbACTotal.Value = CLng(tbAC.Value) + CLng(tbACE.Value) + CLng(tbACoil.Value)
    'tbBCTotal.Value = CLng(tbBC.Value) + CLng(tbBCE.Value) + CLng(tbBCoil.Value)
    
    Me.show
End Sub

Private Sub cbQuit_Click()
    Me.Hide
End Sub

Private Function GetBlockCount(strLayer As String)
    Dim objSS6 As AcadSelectionSet
    Dim entItem As AcadEntity
    Dim filterType, filterValue As Variant
    Dim grpCode(0) As Integer
    Dim grpValue(0) As Variant
    Dim iCount As Integer
    
    iCount = 0
    
    grpCode(0) = 8
    grpValue(0) = strLayer
    filterType = grpCode
    filterValue = grpValue
    
    Set objSS6 = ThisDrawing.SelectionSets.Add("objSS6")
    objSS6.Select acSelectionSetAll, , , filterType, filterValue
    
    For Each entItem In objSS6
        If TypeOf entItem Is AcadBlockReference Then iCount = iCount + 1
    Next entItem
    
    'iCount = objSS6.Count
    
    objSS6.Clear
    objSS6.Delete
    
    GetBlockCount = iCount
End Function

Private Sub GetCables()
    Dim objSS6 As AcadSelectionSet
    Dim entItem As AcadEntity
    Dim filterType, filterValue As Variant
    Dim grpCode(0) As Integer
    Dim grpValue(0) As Variant
    Dim objBlock As AcadBlockReference
    Dim vAttList, vTest As Variant
    Dim lALength, lELash, lBLength, lBSec As Long
    Dim iSpan As Integer
    Dim strSpan As String
    
    lALength = 0
    lELash = 0
    lBLength = 0
    lBSec = 0
    
    grpCode(0) = 2
    grpValue(0) = "cable_span"
    filterType = grpCode
    filterValue = grpValue
    
    Set objSS6 = ThisDrawing.SelectionSets.Add("objSS6")
    objSS6.Select acSelectionSetAll, , , filterType, filterValue
    
    For Each objBlock In objSS6
        vAttList = objBlock.GetAttributes
        strSpan = vAttList(2).TextString
        If Right(strSpan, 1) = "'" Then strSpan = Left(strSpan, Len(strSpan) - 1)
        If strSpan = "" Then GoTo Next_Object
        iSpan = CInt(strSpan)
        
        Select Case objBlock.Layer
            Case "Integrity Cable-Aerial Text"
                lALength = lALength + iSpan
                
                vTest = Split(vAttList(1).TextString, "F ")
                lELash = lELash + (UBound(vTest) * iSpan)
            Case "Integrity Cable-Buried Text"
                lBLength = lBLength + iSpan
                
                vTest = Split(vAttList(1).TextString, "F ")
                lBSec = lBSec + (UBound(vTest) * iSpan)
        End Select
Next_Object:
    Next objBlock
    
    tbAC.Value = lALength
    tbACE.Value = lELash
    
    tbBC.Value = lBLength
    tbBCE.Value = lBSec
    
    objSS6.Clear
    objSS6.Delete
End Sub

Private Sub GetCoils()
    Dim objSS6 As AcadSelectionSet
    Dim entItem As AcadEntity
    Dim filterType, filterValue As Variant
    Dim grpCode(0) As Integer
    Dim grpValue(0) As Variant
    Dim objBlock As AcadBlockReference
    Dim vAttList, vTest As Variant
    Dim lACoil, lBCoil As Long
    Dim iSpan As Integer
    Dim strSpan As String
    
    lACoil = 0
    lBCoil = 0
    
    grpCode(0) = 2
    grpValue(0) = "Map coil"
    filterType = grpCode
    filterValue = grpValue
    
    Set objSS6 = ThisDrawing.SelectionSets.Add("objSS6")
    objSS6.Select acSelectionSetAll, , , filterType, filterValue
    
    For Each objBlock In objSS6
        vAttList = objBlock.GetAttributes
        strSpan = vAttList(0).TextString
        If Right(strSpan, 1) = "'" Then strSpan = Left(strSpan, Len(strSpan) - 1)
        iSpan = CInt(strSpan)
        
        Select Case iSpan
            Case 20, 25
                lBCoil = lBCoil + iSpan
            Case Else
                lACoil = lACoil + iSpan
        End Select
    Next objBlock
    
    tbACoil.Value = lACoil
    tbBCoil.Value = lBCoil
    
    objSS6.Clear
    objSS6.Delete
End Sub

Private Function GetTerminals(strLayer As String)
    Dim objSS6 As AcadSelectionSet
    Dim entItem As AcadEntity
    Dim objBlock As AcadBlockReference
    Dim filterType, filterValue As Variant
    Dim grpCode(0) As Integer
    Dim grpValue(0) As Variant
    Dim iCount As Integer
    
    iCount = 0
    
    grpCode(0) = 8
    grpValue(0) = strLayer
    filterType = grpCode
    filterValue = grpValue
    
    Set objSS6 = ThisDrawing.SelectionSets.Add("objSS6")
    objSS6.Select acSelectionSetAll, , , filterType, filterValue
    
    For Each entItem In objSS6
        If TypeOf entItem Is AcadBlockReference Then
            Set objBlock = entItem
            If objBlock.Name = "Map splice" Then iCount = iCount + 1
        End If
    Next entItem
    
    'iCount = objSS6.Count
    
    objSS6.Clear
    objSS6.Delete
    
    GetTerminals = iCount
End Function

Private Sub ClearAll()
    tbACTotal.Value = ""
    tbAC.Value = ""
    tbACE.Value = ""
    tbACoil.Value = ""
    tbBCTotal.Value = ""
    tbBC.Value = ""
    tbBCE.Value = ""
    tbBCoil.Value = ""
    tbUCTotal.Value = ""
    tbUC.Value = ""
    tbUCE.Value = ""
    tbUCoil.Value = ""
    
    tbAD.Value = ""
    tbBD.Value = ""
    
    tbRouteMiles.Value = ""
    tbRouteKF.Value = ""
    tbPoles.Value = ""
    tbTerminals.Value = ""
    tbSplitters.Value = ""
    tbGuys.Value = ""
    
    tbRESTot.Value = ""
    tbRES.Value = ""
    tbChurch.Value = ""
    tbTRL.Value = ""
    tbMDU.Value = ""
    tbBUSTot.Value = ""
    tbBUS.Value = ""
    tbSchool.Value = ""
    tbSG.Value = ""
    tbMeters.Value = ""
    
    lbTab.Clear
    tbReport.Value = ""
End Sub

Private Sub AddUnitToTab(strItem As String, iDist As Integer)
    If lbTab.ListCount = 0 Then
        GoTo Add_Item
    End If
    
    For i = 0 To lbTab.ListCount - 1
        If lbTab.List(i, 0) = strItem Then
            'MsgBox lbTab.List(i, 0) & vbCr & lbTab.List(i, 1) & vbCr & iDist
            lbTab.List(i, 1) = CInt(lbTab.List(i, 1)) + iDist
            Exit Sub
        End If
    Next i
    
Add_Item:
    lbTab.AddItem strItem
    lbTab.List(lbTab.ListCount - 1, 1) = iDist
    
End Sub

Private Sub cbSort_Click()
    Dim strTemp, strTotal As String
    Dim iCount, iOffset As Integer
    Dim iIndex As Integer
    
    iCount = lbTab.ListCount - 1
    
    For a = iCount To 0 Step -1
        For b = 0 To a - 1
            If lbTab.List(b, 0) > lbTab.List(b + 1, 0) Then
                strTemp = lbTab.List(b + 1, 0)
                strTotal = lbTab.List(b + 1, 1)
                
                lbTab.List(b + 1, 0) = lbTab.List(b, 0)
                lbTab.List(b + 1, 1) = lbTab.List(b, 1)
                
                lbTab.List(b, 0) = strTemp
                lbTab.List(b, 1) = strTotal
            End If
        Next b
    Next a
    
    'iOffset = 0
    'For c = 1 To lbTab.ListCount - 1
        'iIndex = c - iOffset
        'If lbTab.List(iIndex, 0) = lbTab.List(iIndex - 1, 0) Then
            'lbTab.List(iIndex - 1, 1) = CInt(lbTab.List(iIndex - 1, 1)) + CInt(lbTab.List(iIndex, 1))
            'lbTab.RemoveItem iIndex
            'iOffset = iOffset + 1
        'End If
    'Next c
    
    tbReport.Value = ""
    
    For c = 0 To lbTab.ListCount - 1
        If c = lbTab.ListCount - 1 Then
            tbReport.Value = tbReport.Value & lbTab.List(c, 0) & vbTab & lbTab.List(c, 1)
        Else
            tbReport.Value = tbReport.Value & lbTab.List(c, 0) & vbTab & lbTab.List(c, 1) & vbCr
        End If
        
        'Select Case Left(lbTab.List(c, 0), 3)
            'Case "CO("
                'Select Case Right(lbTab.List(c, 0), 1)
                    'Case "P"
                    'Case "E"
                    'Case "M"
                'End Select
            'Case "BFO"
            'Case "UO("
        'End Select
    Next c
End Sub

Private Sub UserForm_Initialize()
    lbTab.ColumnCount = 2
    lbTab.ColumnWidths = "120;74"
End Sub

Attribute VB_Name = "ProjectCreate"
Attribute VB_Base = "0{F334AACC-BA49-4A6A-A41B-8884DA322406}{4BF16D89-33C2-404F-A2F4-B9CB4EFA81E2}"
Attribute VB_GlobalNameSpace = False
Attribute VB_Creatable = False
Attribute VB_PredeclaredId = True
Attribute VB_Exposed = False
Attribute VB_TemplateDerived = False
Attribute VB_Customizable = False
Private Sub cbCreateProject_Click()
    Call UpdateFolderNames
End Sub

Private Sub cbType_Change()
    Select Case cbType.Value
        Case "All"
            For i = 0 To lbFolders.ListCount - 1
                lbFolders.Selected(i) = True
            Next i
            
            'For i = 0 To lbFiles.ListCount - 1
                'lbFiles.Selected(i) = True
            'Next i
        Case "All Folders"
            For i = 0 To lbFolders.ListCount - 1
                If InStr(lbFolders.List(i, 1), "\") > 0 Then lbFolders.Selected(i) = True
            Next i
            
            'For i = 0 To lbFiles.ListCount - 1
                'lbFiles.Selected(i) = False
            'Next i
        Case "None"
            For i = 0 To lbFolders.ListCount - 1
                lbFolders.Selected(i) = False
            Next i
            
            'For i = 0 To lbFiles.ListCount - 1
                'lbFiles.Selected(i) = False
            'Next i
    End Select
End Sub

Private Sub lbFolders_Exit(ByVal Cancel As MSForms.ReturnBoolean)
    Call FindMotherFolders
End Sub

Private Sub tbNumber_Exit(ByVal Cancel As MSForms.ReturnBoolean)
    tbPath.Value = ""
    tbFolder.Value = ""
    
    If tbNumber.Value = "" Then Exit Sub
    
    Call GetFolderFile
    
    Dim vLine As Variant
    Dim strPath, strFolder, strDWG, strDWL As String
    Dim strAll, strNumber, strTemp As String
    Dim strUser As String
    
    strUser = Environ("USERNAME")
    tbNumber.Value = UCase(tbNumber.Value)
    strNumber = tbNumber.Value
    
    vLine = Split(strNumber, "20")
    Select Case vLine(0)
        Case ""
            strPath = "C:\Users\" & strUser & "\Dropbox\UNITED COMMUNICATIONS JOB INFORMATION\1-JOBS\"
            vLine = Split(strNumber, "-")
            
            Select Case vLine(0)
                Case "2019"
                    strPath = strPath & "1-2019 JOBS\"
                Case "2020"
                    strPath = strPath & "2-2020 JOBS\"
                Case "2021"
                    strPath = strPath & "3-2021 JOBS\"
                Case "2022"
                    strPath = strPath & "4-2022 JOBS\"
                Case "2023"
                    strPath = strPath & "5-2023 JOBS\"
            End Select
        Case "L"
            strPath = "C:\Users\" & strUser & "\Dropbox\LORETTO TEL & KCW SHARED FOLDER\01 - JOBS\"
            strNumber = Replace(strNumber, "L", "")
            vLine = Split(strNumber, "-")
            
            Select Case vLine(0)
                Case "2019"
                    strPath = strPath & "2019\"
                Case "2020"
                    strPath = strPath & "2020\"
                Case "2021"
                    strPath = strPath & "2021\"
                Case "2022"
                    strPath = strPath & "2022\"
                Case "2023"
                    strPath = strPath & "2023\"
            End Select
        Case "MAS"
            strPath = "C:\Users\" & strUser & "\Dropbox\MASTEC JOB INFORMATION\1 - JOBS\"
            strNumber = Replace(strNumber, "MAS", "")
            vLine = Split(strNumber, "-")
            
            Select Case vLine(0)
                Case "2019"
                    strPath = strPath & "2019\"
                Case "2020"
                    strPath = strPath & "2020\"
                Case "2021"
                    strPath = strPath & "1-2021 JOBS\"
                Case "2022"
                    strPath = strPath & "2-2022 JOBS\"
                Case "2023"
                    strPath = strPath & "3-2023 JOBS\"
            End Select
        
    End Select
    
    tbPath.Value = strPath
    
    strFolder = GetFolderName(CStr(strPath), CStr(strNumber))
    If strFolder = "<not found>" Then
        tbFolder.Value = ""
        tbTitle.SetFocus
        Exit Sub
    End If
    
    tbTitle.Value = Right(strFolder, Len(strFolder) - Len(tbNumber.Value))
    strFolder = strFolder & "\"
    tbFolder.Value = strFolder
    
    Call UpdateFolderNames
    Call FindIfFolderExists
    
    'For i = 0 To lbFolders.ListCount - 1
        'lbFolders.List(i) = Replace(lbFolders.List(i), "<<pn>>", tbNumber.Value)
        'lbFolders.List(i) = Replace(lbFolders.List(i), "<<pt>>", tbNumber.Value)
    'Next i
    cbCreateProject.SetFocus
End Sub

Private Sub tbTitle_Exit(ByVal Cancel As MSForms.ReturnBoolean)
    If Not tbFolder.Value = "" Then Exit Sub
    If tbNumber.Value = "" Then Exit Sub
    If tbTitle.Value = "" Then Exit Sub
    
    Dim strLine, strFolder, fName As String
    
    strFolder = tbNumber.Value & " " & tbTitle.Value & "\"
    tbFolder.Value = strFolder
    
    strFolder = tbPath.Value & strFolder
    'strLine = Dir(strFolder, vbDirectory)
    
    Call UpdateFolderNames
    
    cbCreateProject.Enabled = True
    cbCreateProject.SetFocus
    
    
End Sub

Private Sub UserForm_Initialize()
    'lbFiles.ColumnCount = 2
    'lbFiles.ColumnWidths = "192;156"
    
    lbFolders.ColumnCount = 2
    lbFolders.ColumnWidths = "72;354"
    
    cbType.AddItem "All"
    cbType.AddItem "All Folders"
    cbType.AddItem "None"
    
    Call GetFolderFile
End Sub

Private Sub GetFolderFile()
    Dim vTemp As Variant
    Dim strUser, strPath As String
    Dim fName, strLine As String
    Dim iStatus As Integer
    
    lbFolders.Clear
    'lbFiles.Clear
    
    iStatus = 0
    strUser = Environ("USERNAME")
    
    strPath = "C:\Users\" & strUser & "\Dropbox\UNITED COMMUNICATIONS JOB INFORMATION\VBA\Integrity\VBA\References\"
    strPath = strPath & "Project Folders.txt"
    
    fName = Dir(strPath)
    If fName = "" Then
        Exit Sub
    End If
    
    Open strPath For Input As #1
    
    While Not EOF(1)
        Line Input #1, strLine
        
        Select Case strLine
            Case "{{FOLDERS}}"
                iStatus = 1
            Case "{{FILES}}"
                iStatus = 2
            Case "{{NOTES}}"
                iStatus = 3
            Case ""
                'Do nothing
            Case Else
                Select Case iStatus
                    Case Is = 1
                        strLine = Replace(strLine, vbTab, "   ")
                        lbFolders.AddItem ""
                        lbFolders.List(lbFolders.ListCount - 1, 1) = strLine
                    Case Is = 2
                        'vTemp = Split(strLine, vbTab)
                        'lbFiles.AddItem vTemp(1)
                        'lbFiles.List(lbFiles.ListCount - 1, 1) = vTemp(0)
                End Select
        End Select
    Wend
    
    Close #1
End Sub

Private Function GetFolderName(strFolder As String, strNumber As String)
    Dim vDirectory As Variant
    Dim strFile As String
    Dim strResult As String
    Dim vTemp As Variant
    
    strResult = "<not found>"
    vDirectory = Dir(strFolder, vbDirectory)
    
    'MsgBox vDirectory
    
    Do While vDirectory <> ""
        If InStr(vDirectory, strNumber) > 0 Then
            strResult = CStr(vDirectory)
            GoTo Exit_Function
        End If
        vDirectory = Dir$
    Loop
Exit_Function:
    GetFolderName = strResult
End Function

Private Sub UpdateFolderNames()
    If tbNumber.Value = "" Then Exit Sub
    If tbTitle.Value = "" Then Exit Sub
    
    For i = 0 To lbFolders.ListCount - 1
        lbFolders.List(i, 1) = Replace(lbFolders.List(i, 1), "<<pn>>", tbNumber.Value)
        lbFolders.List(i, 1) = Replace(lbFolders.List(i, 1), "<<pt>>", tbTitle.Value)
    Next i
    
    'For i = 0 To lbFiles.ListCount - 1
        'lbFiles.List(i, 0) = Replace(lbFiles.List(i, 0), "<<pn>>", tbNumber.Value)
        'lbFiles.List(i, 0) = Replace(lbFiles.List(i, 0), "<<pt>>", tbTitle.Value)
        
        'lbFiles.List(i, 1) = Replace(lbFiles.List(i, 1), "<<pn>>", tbNumber.Value)
        'lbFiles.List(i, 1) = Replace(lbFiles.List(i, 1), "<<pt>>", tbTitle.Value)
    'Next i
End Sub

Private Sub FindMotherFolders()
    If lbFolders.ListCount < 2 Then Exit Sub
    
    Dim iSubfolder, iFolder As Integer
    
    For i = lbFolders.ListCount - 1 To 1 Step -1
        If lbFolders.Selected(i) = False Then GoTo Next_line
        
        If Left(lbFolders.List(i, 1), 9) = "         " Then
            iSubfolder = 3
        ElseIf Left(lbFolders.List(i, 1), 6) = "      " Then
            iSubfolder = 2
        ElseIf Left(lbFolders.List(i, 1), 3) = "   " Then
            iSubfolder = 1
        Else
            GoTo Next_line
        End If
        
        For j = i - 1 To 0 Step -1
            If Left(lbFolders.List(j, 1), 6) = "      " Then
                iFolder = 2
            ElseIf Left(lbFolders.List(j, 1), 3) = "   " Then
                iFolder = 1
            Else
                iFolder = 0
            End If
            
            If iFolder < iSubfolder Then
                lbFolders.Selected(j) = True
                i = j + 1
                GoTo Next_line
            End If
        Next j
Next_line:
    Next i
End Sub

Private Sub FindIfFolderExists()
    If lbFolders.ListCount < 1 Then Exit Sub
    
    Dim strMainFolder, strSub(3) As String
    Dim fName, strLine As String
    Dim iSelected, iSubfolder  As Integer
    
    strMainFolder = tbPath.Value & tbFolder.Value
    strSubFolders = ""
    
    For i = 0 To lbFolders.ListCount - 1
        'If InStr(lbFolders.List(i, 1), "*F*") > 0 Then GoTo Next_Line
        
        If Left(lbFolders.List(i, 1), 9) = "         " Then
            strSub(3) = Right(lbFolders.List(i, 1), Len(lbFolders.List(i, 1)) - 9)
            strLine = strMainFolder & strSub(0) & "\" & strSub(1) & "\" & strSub(2) & "\" & strSub(3)
            If InStr(strLine, "*F* ") > 0 Then
                strLine = Replace(strLine, "*F* ", "")
            End If
        ElseIf Left(lbFolders.List(i, 1), 6) = "      " Then
            strSub(2) = Right(lbFolders.List(i, 1), Len(lbFolders.List(i, 1)) - 6)
            strLine = strMainFolder & strSub(0) & "\" & strSub(1) & "\" & strSub(2)
            If InStr(strLine, "*F* ") > 0 Then
                strLine = Replace(strLine, "*F* ", "")
            End If
        ElseIf Left(lbFolders.List(i, 1), 3) = "   " Then
            strSub(1) = Right(lbFolders.List(i, 1), Len(lbFolders.List(i, 1)) - 3)
            strLine = strMainFolder & strSub(0) & "\" & strSub(1)
            If InStr(strLine, "\") > 0 Then
                strLine = Replace(strLine, "*F* ", "")
            End If
        Else
            strSub(0) = lbFolders.List(i, 1)
            strLine = strMainFolder & strSub(0)
            If InStr(strLine, "*F* ") > 0 Then
                strLine = Replace(strLine, "*F* ", "")
            End If
        End If
    
        'MsgBox strLine
        fName = Dir(strLine, vbDirectory)
        
        If Not fName = "" Then
            lbFolders.List(i, 0) = "Y"
        End If
    Next i
End Sub

'Private Sub CheckIfProjectExists()

'End Sub

Attribute VB_Name = "ProjectOpen"
Attribute VB_Base = "0{E7FBDFE2-AD33-445D-BBA7-1BDAC7296695}{CA738586-BD44-4C12-B06F-FBDE204F3917}"
Attribute VB_GlobalNameSpace = False
Attribute VB_Creatable = False
Attribute VB_PredeclaredId = True
Attribute VB_Exposed = False
Attribute VB_TemplateDerived = False
Attribute VB_Customizable = False
Private Sub cbCleanupTemp_Click()
    If InStr(tbCopyFolder.Value, "Dropbox") > 0 Then Exit Sub
    cbDeleteFile.Enabled = True
    
    tbPath.Value = ""
    tbFolder.Value = ""
    lbFiles.Clear
    lbSubFolders.Clear
    tbNumber.Value = ""
    cbAllDWGs.Value = True
    'cbDeleteFile.Enabled = True
    
    Dim vLine As Variant
    Dim strPath, strFolder, strDWG, strDWL As String
    Dim strAll, strNumber, strTemp As String
    Dim strUser As String
    Dim iIndex As Integer
    
    strPath = "C:\Integrity\"
    strFolder = "Temp\"
    
    tbPath.Value = strPath
    tbFolder.Value = strFolder
    
    Call GetSubFolders
    
    If lbSubFolders.ListCount > 0 Then
        iIndex = 1
        While iIndex < lbSubFolders.ListCount
            Call GetSubSubFolders(lbSubFolders.List(iIndex))
            
            iIndex = iIndex + 1
        Wend
        
        Call SortSubFolders
    End If
    
    lbSubFolders.Selected(0) = True
    lbSubFolders.ListIndex = 0
    
    'Call GetDrawingNames(CStr(strPath), CStr(strFolder), "")
    
    'If lbSubFolders.ListCount > 0 Then
        'For i = 1 To lbSubFolders.ListCount - 1
            'Call GetDrawingNames(CStr(strPath), CStr(strFolder), lbSubFolders.List(i) & "\")
        'Next i
    'End If
    
    If lbFiles.ListCount > -1 Then
        For i = 0 To lbFiles.ListCount - 1
            If InStr(lbFiles.List(i, 0), ".dwg") > 0 Then
                strTemp = strPath & strFolder
                strDWG = CheckIfOpen(CStr(strTemp), CStr(lbFiles.List(i, 0)))
                
                lbFiles.List(i, 1) = strDWG
            End If
        Next i
    End If
    
    lbFiles.SetFocus
End Sub

Private Sub GetDrawingNames(strPath As String, strFolder As String, strSub As String)
    Dim vDirectory As Variant
    Dim strTemp, strFile, strDWG As String
    Dim strResult As String
    Dim vTemp As Variant
    
    strTemp = strPath & strFolder & strSub
    'If cbAllFiles.Value = False Then strTemp = strTemp & "*.dwg"
    
    strFile = Dir(strTemp, vbHidden)
    
    Do While strFile <> ""
        'If cbAllDWGs.Value = False Then
            'If InStr(strFile, tbNumber.Value) > 0 Then
                'If strSub = "" Then
                    'lbFiles.AddItem strSub
                'Else
                    'lbFiles.AddItem Left(strSub, Len(strSub) - 1)
                'End If
                'lbFiles.List(lbFiles.ListCount - 1, 1) = strFile
            'End If
        'Else
            ''If strSub = "" Then
                ''lbFiles.AddItem strSub
            ''Else
                ''lbFiles.AddItem Left(strSub, Len(strSub) - 1)
            ''End If
            ''lbFiles.List(lbFiles.ListCount - 1, 1) = strFile
            lbFiles.AddItem strFile
            lbFiles.List(lbFiles.ListCount - 1, 1) = ""
        'End If
        
        strFile = Dir()
    Loop
End Sub

Private Sub GetSubFolders()
    Dim strFolder, strFile As String
    Dim strTemp As String
    
    lbSubFolders.Clear
    lbSubFolders.AddItem ""
    strFolder = tbPath.Value & tbFolder.Value
    
    strFile = Dir(strFolder, vbDirectory)
    
    Do While strFile <> ""
        strTemp = strFolder & strFile
        'MsgBox strFile & vbCr & GetAttr(strTemp)
        
        If GetAttr(strTemp) = 48 Or GetAttr(strTemp) = 16 Then
            If Not strFile = "." Then
                If Not strFile = ".." Then lbSubFolders.AddItem strFile
            End If
        End If
        
        strFile = Dir()
    Loop
End Sub

Private Sub GetSubSubFolders(strSub As String)
    Dim strFolder, strFile As String
    Dim strTemp As String
    Dim vCount As Variant
    
    If Left(strSub, 1) = "\" Then strSub = Right(strSub, Len(strSub) - 1)
    
    strFolder = tbPath.Value & tbFolder.Value & strSub & "\"
    vCount = Split(strFolder, "\")
    If UBound(vCount) > 10 Then Exit Sub
    
    strFile = Dir(strFolder, vbDirectory)
    
    Do While strFile <> ""
        strTemp = strFolder & strFile
        'MsgBox strTemp & vbCr & GetAttr(strTemp)
        'Exit Sub
        
        If GetAttr(strTemp) = 48 Or GetAttr(strTemp) = 16 Then
            If Not strFile = "." Then
                If Not strFile = ".." Then lbSubFolders.AddItem strSub & "\" & strFile
            End If
        End If
        
        strFile = Dir()
    Loop
End Sub

Private Sub SortSubFolders()
    Dim a, b As Integer
    Dim iCount As Integer
    Dim strAtt As String
    'Dim strAtt(0 To 2) As String
    
    iCount = lbSubFolders.ListCount - 1
    If iCount < 1 Then Exit Sub
    
    On Error Resume Next
    
    For a = iCount To 0 Step -1
        For b = 0 To a - 1
            If lbSubFolders.List(b, 0) > lbSubFolders.List(b + 1, 0) Then
                'If Not Err = 0 Then
                    'MsgBox "Error sorting list"
                    'lbSubFolders.Selected(b) = True
                    'lbSubFolders.ListIndex = b
                    'Exit Sub
                'End If
                
                strAtt = lbSubFolders.List(b + 1, 0)
                lbSubFolders.List(b + 1, 0) = lbSubFolders.List(b, 0)
                lbSubFolders.List(b, 0) = strAtt
            End If
        Next b
    Next a
End Sub

Private Function CheckIfOpen(strFolder As String, strNumber As String)
    If InStr(strNumber, ".dwg") = 0 Then Exit Function
    
    Dim strFile, strDWL As String
    Dim strLine As String
    Dim vTemp As Variant
    
    'strFolder = tbPath.Value & tbFolder.Value
    strDWL = Replace(strNumber, ".dwg", ".dwl")
    
    strFile = Dir$(strFolder, vbHidden)
    
    Do While strFile <> ""
        If strFile = strDWL Then GoTo Found_File
        
        strFile = Dir$()
    Loop
    
    CheckIfOpen = ""
    
    Exit Function
Found_File:
    
    strDWL = strFolder & strFile
    
    Open strDWL For Input As #1
    
    Line Input #1, strLine
    vTemp = Split(strLine, vbLf)
    vTemp(0) = Replace(vTemp(0), vbCr, "")
    
    Close #1
    
    Select Case LCase(vTemp(0))
        Case "integrity"
            strLine = "Dylan Spears"
        Case "integrity.tab"
            strLine = "Jeremy Pafford"
        Case "integrity.1"
            strLine = "Ronn Elliott"
        Case "integrity.2"
            strLine = "Rich Taylor"
        Case "integrity.3"
            strLine = "Jason Pafford"
        Case "integrity.4"
            strLine = "Byron Auer"
        Case "integrity.5"
            strLine = "Adam Kemper"
        Case "integrity.6"
            strLine = "Jon Wilburn"
        Case "integrity.7"
            strLine = "Tara Taylor"
        Case "integrity8"
            strLine = "Franklin Angulo"
        Case "integrity9"
            strLine = "Wade Hampton"
        Case "integrity10"
            strLine = "Sam Jackson"
        'Case "integrity11"
            'strLine = "A Ghost?"
        Case "integrity12"
            strLine = "Daniel Campbell"
        Case "integrity13"
            strLine = "Nick Lockyear"
        'Case "integrity14"
            'strLine = "A Ghost?"
        Case "integrity.15"
            strLine = "Jay Penny"
        Case "integrity16"
            strLine = "Drew Curtis"
        Case Else
            strLine = LCase(vTemp(0)) & " ?"
    End Select
    
    CheckIfOpen = strLine
End Function

Private Sub cbCopyDWG_Click()
    Dim iIndex As Integer
    
    iIndex = lbFiles.ListIndex
    If iIndex < 0 Then Exit Sub
    
    Dim fso As Object
    Dim strFileFrom, strFileTo As String
    
    strFileFrom = tbPath.Value & tbFolder.Value
    If Not lbSubFolders.List(lbSubFolders.ListIndex) = "" Then
        strFileFrom = strFileFrom & lbSubFolders.List(lbSubFolders.ListIndex) & "\"
    End If
    strFileFrom = strFileFrom & lbFiles.List(iIndex, 0)
    strFileTo = tbCopyFolder & lbFiles.List(iIndex, 0)
    
    'MsgBox "Copying from:" & vbCr & vbCr & strFileFrom & vbCr & vbCr & "Copying to:" & vbCr & vbCr & strFileTo
    Set fso = VBA.CreateObject("Scripting.FileSystemObject")
    
    Call fso.CopyFile(strFileFrom, strFileTo)
    
    If Right(strFileTo, 4) = ".dwg" Then
        ThisDrawing.Application.Documents.Open strFileTo
    Else
        CreateObject("Shell.Application").Open CVar(strFileTo)
    End If
End Sub

Private Sub cbCreateProject_Click()
    cbDeleteFile.Enabled = False
    
    Me.Hide
    
    Load ProjectCreate
        If Not tbNumber.Value = "" Then
            ProjectCreate.tbNumber.Value = tbNumber.Value
            ProjectCreate.tbTitle.SetFocus
        End If
        
        ProjectCreate.show
    Unload ProjectCreate
    
    Me.Hide
End Sub

Private Sub cbDeleteFile_Click()
    If lbFiles.ListIndex < 0 Then Exit Sub
    
    Dim iIndex As Integer
    
    iIndex = lbFiles.ListIndex
    If Not lbFiles.List(iIndex, 1) = "" Then
        If iIndex = lbFiles.ListCount - 1 Then
            If Not iIndex = 0 Then
                iIndex = iIndex - 1
                lbFiles.Selected(iIndex) = True
                lbFiles.ListIndex = iIndex
            End If
        Else
            iIndex = iIndex + 1
            lbFiles.Selected(iIndex) = True
            lbFiles.ListIndex = iIndex
        End If
        
        Exit Sub
    End If
    
    Dim strFile As String
    Dim result As Integer
    
    strFile = tbPath.Value & tbFolder.Value & lbSubFolders.List(lbSubFolders.ListIndex)
    If Not Right(strFile, 1) = "\" Then strFile = strFile & "\"
    'If Not lbFiles.List(iIndex, 0) = "" Then strFile = strFile & lbFiles.List(iIndex, 0) & "\"
    strFile = strFile & lbFiles.List(iIndex, 0)
    
    'MsgBox strFile
    'Exit Sub
    
    result = MsgBox("Are you sure you want to delete" & vbCr & strFile & "?", vbYesNo, "Delete File!")
    If result = vbYes Then
        Kill strFile
        lbFiles.RemoveItem iIndex
    End If
    
Exit_Sub:
    
End Sub

Private Sub cbGetInfo_Click()
    tbPath.Value = ""
    tbFolder.Value = ""
    lbFiles.Clear
    lbSubFolders.Clear
    cbDeleteFile.Enabled = False
    'cbAllFiles.Value = False
    
    If tbNumber.Value = "" Then Exit Sub
    
    Dim vLine As Variant
    Dim strPath, strFolder, strDWG, strDWL As String
    Dim strAll, strNumber, strTemp As String
    Dim strUser As String
    
    strUser = Environ("USERNAME")
    tbNumber.Value = UCase(tbNumber.Value)
    strNumber = tbNumber.Value
    
    vLine = Split(strNumber, "20")
    Select Case vLine(0)
        Case ""
            strPath = "C:\Users\" & strUser & "\Dropbox\UNITED COMMUNICATIONS JOB INFORMATION\1-JOBS\"
            vLine = Split(strNumber, "-")
            
            Select Case vLine(0)
                Case "2019"
                    strPath = strPath & "1-2019 JOBS\"
                Case "2020"
                    strPath = strPath & "2-2020 JOBS\"
                Case "2021"
                    strPath = strPath & "3-2021 JOBS\"
                Case "2022"
                    strPath = strPath & "4-2022 JOBS\"
                Case "2023"
                    strPath = strPath & "5-2023 JOBS\"
            End Select
        Case "L"
            strPath = "C:\Users\" & strUser & "\Dropbox\LORETTO TEL & KCW SHARED FOLDER\01 - JOBS\"
            strNumber = Replace(strNumber, "L", "")
            vLine = Split(strNumber, "-")
            
            Select Case vLine(0)
                Case "2019"
                    strPath = strPath & "2019\"
                Case "2020"
                    strPath = strPath & "2020\"
                Case "2021"
                    strPath = strPath & "2021\"
                Case "2022"
                    strPath = strPath & "2022\"
                Case "2023"
                    strPath = strPath & "2023\"
            End Select
        Case "MAS"
            strPath = "C:\Users\" & strUser & "\Dropbox\MASTEC JOB INFORMATION\1 - JOBS\"
            strNumber = Replace(strNumber, "MAS", "")
            vLine = Split(strNumber, "-")
            
            Select Case vLine(0)
                Case "2019"
                    strPath = strPath & "2019\"
                Case "2020"
                    strPath = strPath & "2020\"
                Case "2021"
                    strPath = strPath & "1-2021 JOBS\"
                Case "2022"
                    strPath = strPath & "2-2022 JOBS\"
                Case "2023"
                    strPath = strPath & "3-2023 JOBS\"
            End Select
        
    End Select
    
    tbPath.Value = strPath
    
    strFolder = GetFolderName(CStr(strPath), CStr(strNumber))
    'strFolder = GetFolderName(CStr(strPath), CStr(tbNumber.Value))
    If strFolder = "<not found>" Then
        tbFolder.Value = strFolder
        Exit Sub
    End If
    
    strFolder = strFolder & "\"
    tbFolder.Value = strFolder
    'strDWG = GetDrawingName(CStr(strPath), CStr(strFolder), CStr(strNumber))
    Call GetSubFolders
    
    If lbSubFolders.ListCount > 1 Then
        iIndex = 1
        While iIndex < lbSubFolders.ListCount
            Call GetSubSubFolders(lbSubFolders.List(iIndex))
            
            iIndex = iIndex + 1
        Wend
        
        Call SortSubFolders
    End If
    
    lbSubFolders.Selected(0) = True
    lbSubFolders.ListIndex = 0
    
    lbFiles.Clear
    Call GetDrawingNames(CStr(strPath), CStr(strFolder), "")
    
    'If cbAllFiles.Value = False Then
        'If lbSubFolders.ListCount > 1 Then
            'For i = 1 To lbSubFolders.ListCount - 1
                'Call GetDrawingNames(CStr(strPath), CStr(strFolder), lbSubFolders.List(i) & "\")
            'Next i
        'End If
    'End If
    
    If lbFiles.ListCount > -1 Then
        For i = 0 To lbFiles.ListCount - 1
            If InStr(lbFiles.List(i, 0), ".dwg") > 0 Then
                strTemp = strPath & strFolder
                strDWG = CheckIfOpen(CStr(strTemp), CStr(lbFiles.List(i, 0)))
                
                lbFiles.List(i, 1) = strDWG
            End If
        Next i
        
        vLine = Split(tbFolder.Value, "\")
        strTemp = LCase(vLine(UBound(vLine) - 1)) & ".dwg"
        
        For i = 0 To lbFiles.ListCount - 1
            If LCase(lbFiles.List(i, 0)) = strTemp Then
                lbFiles.Selected(i) = True
                GoTo Exit_Sub
            End If
        Next i
    End If
Exit_Sub:
    
    lbFiles.SetFocus
End Sub

Private Sub cbReadOnly_Click()
    If lbFiles.ListIndex < 0 Then Exit Sub
    
    Dim strFileName As String
    
    strFileName = tbPath.Value & tbFolder.Value & lbSubFolders.List(lbSubFolders.ListIndex)
    If Not Right(strFileName, 1) = "\" Then strFileName = strFileName & "\"
    strFileName = strFileName & lbFiles.List(lbDrawings.ListIndex, 0)
    
    ThisDrawing.Application.Documents.Open strFileName, True
End Sub

Private Sub lbFiles_DblClick(ByVal Cancel As MSForms.ReturnBoolean)
    Dim strFileName As String
    
    strFileName = tbPath.Value & tbFolder.Value & lbSubFolders.List(lbSubFolders.ListIndex)
    If Not Right(strFileName, 1) = "\" Then strFileName = strFileName & "\"
    strFileName = strFileName & lbFiles.List(lbFiles.ListIndex, 0)
    
    If Right(strFileName, 4) = ".dwg" Then
        Select Case lbFiles.List(lbFiles.ListIndex, 1)
            Case ""
                ThisDrawing.Application.Documents.Open strFileName
            Case Else
                'MsgBox strFileName
                ThisDrawing.Application.Documents.Open strFileName, True
                MsgBox lbFiles.List(lbFiles.ListIndex, 0) & vbCr & "was opened in ReadOnly."
        End Select
        'ThisDrawing.Application.Documents.Open strFileName
    Else
        CreateObject("Shell.Application").Open CVar(strFileName)
    End If
End Sub

Private Sub lbFiles_KeyDown(ByVal KeyCode As MSForms.ReturnInteger, ByVal Shift As Integer)
    Dim strFileName As String
    
    strFileName = tbPath.Value & tbFolder.Value & lbSubFolders.List(lbSubFolders.ListIndex)
    If Not Right(strFileName, 1) = "\" Then strFileName = strFileName & "\"
    
    Select Case KeyCode
        Case vbKeyReturn
            strFileName = strFileName & lbFiles.List(lbFiles.ListIndex, 0)
            If Right(strFileName, 4) = ".dwg" Then
                Select Case lbFiles.List(lbFiles.ListIndex, 1)
                    Case ""
                        ThisDrawing.Application.Documents.Open strFileName
                    Case Else
                        ThisDrawing.Application.Documents.Open strFileName, True
                        MsgBox lbFiles.List(lbFiles.ListIndex, 0) & vbCr & "was opened in ReadOnly."
                End Select
            Else
                CreateObject("Shell.Application").Open CVar(strFileName)
            End If
    End Select
End Sub

Private Sub lbSubFolders_Click()
    Dim strPath, strFolder As String
    Dim iIndex As Integer
    
    lbFiles.Clear
    iIndex = lbSubFolders.ListIndex
    
    strPath = tbPath.Value
    strFolder = tbFolder.Value
    
    lbFiles.Clear
    
    Call GetDrawingNames(CStr(strPath), CStr(strFolder), lbSubFolders.List(iIndex) & "\")
    
    If lbFiles.ListCount > -1 Then
        For i = 0 To lbFiles.ListCount - 1
            If InStr(lbFiles.List(i, 0), ".dwg") > 0 Then
                strTemp = strPath & strFolder & lbSubFolders.List(lbSubFolders.ListIndex) & "\"
                strDWG = CheckIfOpen(CStr(strTemp), CStr(lbFiles.List(i, 0)))
                
                lbFiles.List(i, 1) = strDWG
            End If
        Next i
        
        vLine = Split(tbFolder.Value, "\")
        strTemp = LCase(vLine(UBound(vLine) - 1)) & ".dwg"
        
        For i = 0 To lbFiles.ListCount - 1
            If LCase(lbFiles.List(i, 1)) = strTemp Then
                lbFiles.Selected(i) = True
                GoTo Exit_Sub
            End If
        Next i
    End If
Exit_Sub:
    
    lbFiles.SetFocus
End Sub

Private Sub UserForm_Initialize()
    lbFiles.ColumnCount = 2
    lbFiles.ColumnWidths = "264;78"
    
    tbNumber.SetFocus
End Sub

Private Function GetFolderName(strFolder As String, strNumber As String)
    Dim vDirectory As Variant
    Dim strFile As String
    Dim strResult As String
    Dim vTemp As Variant
    
    strResult = "<not found>"
    vDirectory = Dir(strFolder, vbDirectory)
    
    'MsgBox vDirectory
    
    Do While vDirectory <> ""
        If InStr(vDirectory, strNumber) > 0 Then
            strResult = CStr(vDirectory)
            GoTo Exit_Function
        End If
        vDirectory = Dir$
    Loop
Exit_Function:
    GetFolderName = strResult
End Function

Attribute VB_Name = "ProjectStatus"
Attribute VB_Base = "0{19D8C5A4-6893-444D-98E0-F7AA2F97A184}{011654A6-E9BE-4793-B38D-CFEF7A44E040}"
Attribute VB_GlobalNameSpace = False
Attribute VB_Creatable = False
Attribute VB_PredeclaredId = True
Attribute VB_Exposed = False
Attribute VB_TemplateDerived = False
Attribute VB_Customizable = False

Dim strFileName As String
Dim strProjectName As String
Dim iEmailSent As Integer

Private Sub cbGetWorkload_Click()
    Me.Hide
        Load zzzWorkload
            zzzWorkload.show
        Unload zzzWorkload
    Me.show
End Sub

Private Sub CommandButton1_Click()
    Dim vTemp As Variant
    Dim strReport, strTemp As String
    Dim strCompleted, strDate As String
    Dim iSendEmail As Integer
    
    Me.Hide
    
    strCompleted = ""
    
    vTemp = Split(Me.Caption, " ")
    strTemp = vTemp(0)
    strReport = "Project:" & vbTab & strTemp & vbCr
    
    strReport = strReport & "Setup:" & vbTab
    If Not tbPSI.Value = "" Then
        strReport = strReport & tbPSI.Value & vbTab & tbPSS.Value & vbTab & tbPSC.Value & vbTab & tbPSH.Value
        If Not tbPSC.Value = "" Then
            If tbPSC.Enabled = True Then strCompleted = "Setup"
        End If
    End If
    
    strReport = strReport & vbCr & "BDK:" & vbTab
    If Not tbBI.Value = "" Then
        strReport = strReport & tbBI.Value & vbTab & tbBS.Value & vbTab & tbBC.Value & vbTab & tbBH.Value
        If Not tbBC.Value = "" Then
            If tbBC.Enabled = True Then strCompleted = "BDK"
        End If
    End If
    
    strReport = strReport & vbCr & "Planning:" & vbTab
    If Not tbPLI.Value = "" Then
        strReport = strReport & tbPLI.Value & vbTab & tbPLS.Value & vbTab & tbPLC.Value & vbTab & tbPLH.Value
        If Not tbPLC.Value = "" Then
            If tbPLC.Enabled = True Then strCompleted = "Planning"
        End If
    End If
    
    strReport = strReport & vbCr & "Prepare:" & vbTab
    If Not tbCOI.Value = "" Then
        strReport = strReport & tbCOI.Value & vbTab & tbCOS.Value & vbTab & tbCOC.Value & vbTab & tbCOH.Value
        If Not tbCOC.Value = "" Then
            If tbCOC.Enabled = True Then strCompleted = "Prepare Job"
        End If
    End If
    
    strReport = strReport & vbCr & "Field:" & vbTab
    If Not tbFI.Value = "" Then
        strReport = strReport & tbFI.Value & vbTab & tbFS.Value & vbTab & tbFC.Value & vbTab & tbFH.Value
        If Not tbFC.Value = "" Then
            If tbFC.Enabled = True Then strCompleted = "Fielding"
        End If
    End If
    
    strReport = strReport & vbCr & "Cleanup:" & vbTab
    If Not tbCUI.Value = "" Then
        strReport = strReport & tbCUI.Value & vbTab & tbCUS.Value & vbTab & tbCUC.Value & vbTab & tbCUH.Value
        If Not tbCUC.Value = "" Then
            If tbCUC.Enabled = True Then strCompleted = "Cleanup"
        End If
    End If
    
    strReport = strReport & vbCr & "Cut Out:" & vbTab
    If Not tbCDI.Value = "" Then
        strReport = strReport & tbCDI.Value & vbTab & tbCDS.Value & vbTab & tbCDC.Value & vbTab & tbCDH.Value
        If Not tbCDC.Value = "" Then
            If tbCDC.Enabled = True Then strCompleted = "Cut Out"
        End If
    End If
    
    strReport = strReport & vbCr & "Make Ready:" & vbTab
    If Not tbMRI.Value = "" Then
        strReport = strReport & tbMRI.Value & vbTab & tbMRS.Value & vbTab & tbMRC.Value & vbTab & tbMRH.Value
        If Not tbMRC.Value = "" Then
            If tbMRC.Enabled = True Then strCompleted = "Make Ready"
        End If
    End If
    
    strReport = strReport & vbCr & "Permits:" & vbTab
    If Not tbPI.Value = "" Then
        strReport = strReport & tbPI.Value & vbTab & tbPS.Value & vbTab & tbPC.Value & vbTab & tbPH.Value
        If Not tbPC.Value = "" Then
            If tbPC.Enabled = True Then strCompleted = "Permits"
        End If
    End If
    
    strReport = strReport & vbCr & "Counts:" & vbTab
    If Not tbCntI.Value = "" Then
        strReport = strReport & tbCntI.Value & vbTab & tbCntS.Value & vbTab & tbCntC.Value & vbTab & tbCntH.Value
        If Not tbCntC.Value = "" Then
            If tbCntC.Enabled = True Then strCompleted = "Counts"
        End If
    End If
    
    strReport = strReport & vbCr & "Units:" & vbTab
    If Not tbUI.Value = "" Then
        strReport = strReport & tbUI.Value & vbTab & tbUS.Value & vbTab & tbUC.Value & vbTab & tbUH.Value
        If Not tbUC.Value = "" Then
            If tbUC.Enabled = True Then strCompleted = "Units"
        End If
    End If
    
    strReport = strReport & vbCr & "QC:" & vbTab
    If Not tbQCI.Value = "" Then
        strReport = strReport & tbQCI.Value & vbTab & tbQCS.Value & vbTab & tbQCC.Value & vbTab & tbQCH.Value
        If Not tbQCC.Value = "" Then
            If tbQCC.Enabled = True Then strCompleted = "QC"
        End If
    End If
    
    strReport = strReport & vbCr & "Reports:" & vbTab
    If Not tbRI.Value = "" Then
        strReport = strReport & tbRI.Value & vbTab & tbRS.Value & vbTab & tbRC.Value & vbTab & tbRH.Value
        If Not tbRC.Value = "" Then
            If tbRC.Enabled = True Then strCompleted = "Reports"
        End If
    End If
    
  On Error Resume Next
    
    If Not strCompleted = "" Then
        SendCompleteEmail (strCompleted)
    End If
    
    If iEmailSent = 0 Then
        Dim result As Integer
    
        result = MsgBox("Update without email?", vbYesNo, "Update without Email")
        If result = vbNo Then
            MsgBox "Update Cancelled"
            Me.show
            Exit Sub
        Else
            strCompleted = ""
        End If
    End If
    
    Open strFileName For Output As #3
    
    Print #3, UCase(strReport)
    
    Close #3
    
    Call RefreshProjectForm
    
    If Not strCompleted = "" Then
        MsgBox "Updated and Email sent for " & strCompleted
    Else
        MsgBox "Updated"
    End If
    Me.show
End Sub

Private Sub CommandButton2_Click()
    Me.Hide
End Sub

Private Sub Frame1_DblClick(ByVal Cancel As MSForms.ReturnBoolean)
    tbFI.Enabled = True
    tbFS.Enabled = True
    tbFC.Enabled = True
End Sub

Private Sub Frame10_DblClick(ByVal Cancel As MSForms.ReturnBoolean)
    tbCDI.Enabled = True
    tbCDS.Enabled = True
    tbCDC.Enabled = True
End Sub

Private Sub Frame2_DblClick(ByVal Cancel As MSForms.ReturnBoolean)
    tbCOI.Enabled = True
    tbCOS.Enabled = True
    tbCOC.Enabled = True
End Sub

Private Sub Frame3_DblClick(ByVal Cancel As MSForms.ReturnBoolean)
    tbCUI.Enabled = True
    tbCUS.Enabled = True
    tbCUC.Enabled = True
End Sub

Private Sub Frame4_DblClick(ByVal Cancel As MSForms.ReturnBoolean)
    tbMRI.Enabled = True
    tbMRS.Enabled = True
    tbMRC.Enabled = True
End Sub

Private Sub Frame5_DblClick(ByVal Cancel As MSForms.ReturnBoolean)
    tbPI.Enabled = True
    tbPS.Enabled = True
    tbPC.Enabled = True
End Sub

Private Sub Frame6_DblClick(ByVal Cancel As MSForms.ReturnBoolean)
    tbCntI.Enabled = True
    tbCntS.Enabled = True
    tbCntC.Enabled = True
End Sub

Private Sub Frame7_DblClick(ByVal Cancel As MSForms.ReturnBoolean)
    tbUI.Enabled = True
    tbUS.Enabled = True
    tbUC.Enabled = True
End Sub

Private Sub Frame8_DblClick(ByVal Cancel As MSForms.ReturnBoolean)
    tbQCI.Enabled = True
    tbQCS.Enabled = True
    tbQCC.Enabled = True
End Sub

Private Sub Frame9_DblClick(ByVal Cancel As MSForms.ReturnBoolean)
    tbRI.Enabled = True
    tbRS.Enabled = True
    tbRC.Enabled = True
End Sub

Private Sub Label41_Click()
    If tbCOI.Value = "" Then Exit Sub
    If Not tbCOS.Value = "" Then Exit Sub
    tbCOS.Value = Date
    
    'SendCompleteEmail ("Prepare Assigned")
    'MsgBox "Email sent to Project Management"
End Sub

Private Sub Label42_Click()
    'Add Fielding Hours
    Dim dNewHours, dOldHours, dTotal As Double
    Dim strDate As String
    
    If tbFH.Value = "" Then
        dOldHours = 0#
    Else
        dOldHours = CDbl(tbFH.Value)
    End If
    
    strJob = strProjectName
    
    Load ProjectStatusHours
        ProjectStatusHours.tbJob.Value = strJob
        ProjectStatusHours.show
        
        dNewHours = CDbl(ProjectStatusHours.tbHours.Value)
        'strDate = ProjectStatusHours.tbDate.Value
        'strJob = ProjectStatusHours.tbJob.Value
        'MsgBox strDate & " - " & dNewHours & " Hours"
    Unload ProjectStatusHours
    
    tbFH.Value = dOldHours + dNewHours
    
End Sub

Private Sub Label44_Click()
    If Not tbFC.Value = "" Then Exit Sub
    tbFC.Value = Date
End Sub

Private Sub Label45_Click()
    If Not tbFS.Value = "" Then Exit Sub
    If tbFI.Value = "" Then Exit Sub
    tbFS.Value = Date
    SendCompleteEmail ("Fielding Assigned")
    MsgBox "Email sent to Project Management"
End Sub

Private Sub Label46_Click()
    'Add Cleanup Hours
    Dim dNewHours, dOldHours, dTotal As Double
    Dim strDate As String
    
    If tbCUH.Value = "" Then    '<---------------------------------------------Change
        dOldHours = 0#
    Else
        dOldHours = CDbl(tbCUH.Value)    '<---------------------------------------------Change
    End If
    
    strJob = strProjectName
    
    Load ProjectStatusHours
        ProjectStatusHours.tbJob.Value = strJob
        ProjectStatusHours.show
        
        dNewHours = CDbl(ProjectStatusHours.tbHours.Value)
        strDate = ProjectStatusHours.tbDate.Value
        strJob = ProjectStatusHours.tbJob.Value
        'MsgBox strDate & " - " & dNewHours & " Hours"
    Unload ProjectStatusHours
    
    tbCUH.Value = dOldHours + dNewHours    '<---------------------------------------------Change
    
    Call AddHoursToTimesheet(CStr(strJob), CStr(strDate), CDbl(dNewHours))
End Sub

Private Sub Label48_Click()
    If Not tbCUC.Value = "" Then Exit Sub
    tbCUC.Value = Date
End Sub

Private Sub Label49_Click()
    If Not tbCUS.Value = "" Then Exit Sub
    tbCUS.Value = Date
End Sub

Private Sub Label5_Click()
    If Not tbCOC.Value = "" Then Exit Sub
    tbCOC.Value = Date
End Sub

Private Sub Label50_Click()
    'Add Cleanup Hours
    Dim dNewHours, dOldHours, dTotal As Double
    Dim strDate As String
    
    If tbMRH.Value = "" Then    '<---------------------------------------------Change
        dOldHours = 0#
    Else
        dOldHours = CDbl(tbMRH.Value)    '<---------------------------------------------Change
    End If
    
    strJob = strProjectName
    
    Load ProjectStatusHours
        ProjectStatusHours.tbJob.Value = strJob
        ProjectStatusHours.show
        
        dNewHours = CDbl(ProjectStatusHours.tbHours.Value)
        strDate = ProjectStatusHours.tbDate.Value
        strJob = ProjectStatusHours.tbJob.Value
        'MsgBox strDate & " - " & dNewHours & " Hours"
    Unload ProjectStatusHours
    
    tbMRH.Value = dOldHours + dNewHours    '<---------------------------------------------Change
    
    Call AddHoursToTimesheet(CStr(strJob), CStr(strDate), CDbl(dNewHours))
End Sub

Private Sub Label52_Click()
    If Not tbMRC.Value = "" Then Exit Sub
    tbMRC.Value = Date
End Sub

Private Sub Label53_Click()
    If Not tbMRS.Value = "" Then Exit Sub
    tbMRS.Value = Date
End Sub

Private Sub Label54_Click()
    'Add Cleanup Hours
    Dim dNewHours, dOldHours, dTotal As Double
    Dim strDate As String
    
    If tbPH.Value = "" Then    '<---------------------------------------------Change
        dOldHours = 0#
    Else
        dOldHours = CDbl(tbPH.Value)    '<---------------------------------------------Change
    End If
    
    strJob = strProjectName
    
    Load ProjectStatusHours
        ProjectStatusHours.tbJob.Value = strJob
        ProjectStatusHours.show
        
        dNewHours = CDbl(ProjectStatusHours.tbHours.Value)
        strDate = ProjectStatusHours.tbDate.Value
        strJob = ProjectStatusHours.tbJob.Value
        'MsgBox strDate & " - " & dNewHours & " Hours"
    Unload ProjectStatusHours
    
    tbPH.Value = dOldHours + dNewHours    '<---------------------------------------------Change
    
    Call AddHoursToTimesheet(CStr(strJob), CStr(strDate), CDbl(dNewHours))
End Sub

Private Sub Label56_Click()
    If Not tbPC.Value = "" Then Exit Sub
    tbPC.Value = Date
End Sub

Private Sub Label57_Click()
    If Not tbPS.Value = "" Then Exit Sub
    tbPS.Value = Date
End Sub

Private Sub Label58_Click()
    'Add Cleanup Hours
    Dim dNewHours, dOldHours, dTotal As Double
    Dim strDate As String
    
    If tbCntH.Value = "" Then    '<---------------------------------------------Change
        dOldHours = 0#
    Else
        dOldHours = CDbl(tbCntH.Value)    '<---------------------------------------------Change
    End If
    
    strJob = strProjectName
    
    Load ProjectStatusHours
        ProjectStatusHours.tbJob.Value = strJob
        ProjectStatusHours.show
        
        dNewHours = CDbl(ProjectStatusHours.tbHours.Value)
        strDate = ProjectStatusHours.tbDate.Value
        strJob = ProjectStatusHours.tbJob.Value
        'MsgBox strDate & " - " & dNewHours & " Hours"
    Unload ProjectStatusHours
    
    tbCntH.Value = dOldHours + dNewHours    '<---------------------------------------------Change
    
    Call AddHoursToTimesheet(CStr(strJob), CStr(strDate), CDbl(dNewHours))
End Sub

Private Sub Label6_Click()
    'Add Prepare Hours
    Dim dNewHours, dOldHours, dTotal As Double
    Dim strDate As String
    
    If tbCOH.Value = "" Then
        dOldHours = 0#
    Else
        dOldHours = CDbl(tbCOH.Value)
    End If
    
    strJob = strProjectName
    
    Load ProjectStatusHours
        ProjectStatusHours.tbJob.Value = strJob
        ProjectStatusHours.show
        
        dNewHours = CDbl(ProjectStatusHours.tbHours.Value)
        strDate = ProjectStatusHours.tbDate.Value
        strJob = ProjectStatusHours.tbJob.Value
        'MsgBox strDate & " - " & dNewHours & " Hours"
    Unload ProjectStatusHours
    
    tbCOH.Value = dOldHours + dNewHours
    
    Call AddHoursToTimesheet(CStr(strJob), CStr(strDate), CDbl(dNewHours))
End Sub

Private Sub Label60_Click()
    If Not tbCntC.Value = "" Then Exit Sub
    tbCntC.Value = Date
End Sub

Private Sub Label61_Click()
    If Not tbCntS.Value = "" Then Exit Sub
    tbCntS.Value = Date
End Sub

Private Sub Label62_Click()
    'Add Cleanup Hours
    Dim dNewHours, dOldHours, dTotal As Double
    Dim strDate As String
    
    If tbUH.Value = "" Then    '<---------------------------------------------Change
        dOldHours = 0#
    Else
        dOldHours = CDbl(tbUH.Value)    '<---------------------------------------------Change
    End If
    
    strJob = strProjectName
    
    Load ProjectStatusHours
        ProjectStatusHours.tbJob.Value = strJob
        ProjectStatusHours.show
        
        dNewHours = CDbl(ProjectStatusHours.tbHours.Value)
        strDate = ProjectStatusHours.tbDate.Value
        strJob = ProjectStatusHours.tbJob.Value
        'MsgBox strDate & " - " & dNewHours & " Hours"
    Unload ProjectStatusHours
    
    tbUH.Value = dOldHours + dNewHours    '<---------------------------------------------Change
    
    Call AddHoursToTimesheet(CStr(strJob), CStr(strDate), CDbl(dNewHours))
End Sub

Private Sub Label64_Click()
    If Not tbUC.Value = "" Then Exit Sub
    tbUC.Value = Date
End Sub

Private Sub Label65_Click()
    If Not tbUS.Value = "" Then Exit Sub
    tbUS.Value = Date
End Sub

Private Sub Label66_Click()
    'Add Cleanup Hours
    Dim dNewHours, dOldHours, dTotal As Double
    Dim strDate As String
    
    If tbQCH.Value = "" Then    '<---------------------------------------------Change
        dOldHours = 0#
    Else
        dOldHours = CDbl(tbQCH.Value)    '<---------------------------------------------Change
    End If
    
    strJob = strProjectName
    
    Load ProjectStatusHours
        ProjectStatusHours.tbJob.Value = strJob
        ProjectStatusHours.show
        
        dNewHours = CDbl(ProjectStatusHours.tbHours.Value)
        strDate = ProjectStatusHours.tbDate.Value
        strJob = ProjectStatusHours.tbJob.Value
        'MsgBox strDate & " - " & dNewHours & " Hours"
    Unload ProjectStatusHours
    
    tbQCH.Value = dOldHours + dNewHours    '<---------------------------------------------Change
    
    Call AddHoursToTimesheet(CStr(strJob), CStr(strDate), CDbl(dNewHours))
End Sub

Private Sub Label68_Click()
    If Not tbQCC.Value = "" Then Exit Sub
    tbQCC.Value = Date
End Sub

Private Sub Label69_Click()
    If Not tbQCS.Value = "" Then Exit Sub
    tbQCS.Value = Date
End Sub

Private Sub Label70_Click()
    'Add Cleanup Hours
    Dim dNewHours, dOldHours, dTotal As Double
    Dim strDate As String
    
    If tbRH.Value = "" Then    '<---------------------------------------------Change
        dOldHours = 0#
    Else
        dOldHours = CDbl(tbRH.Value)    '<---------------------------------------------Change
    End If
    
    strJob = strProjectName
    
    Load ProjectStatusHours
        ProjectStatusHours.tbJob.Value = strJob
        ProjectStatusHours.show
        
        dNewHours = CDbl(ProjectStatusHours.tbHours.Value)
        strDate = ProjectStatusHours.tbDate.Value
        strJob = ProjectStatusHours.tbJob.Value
        'MsgBox strDate & " - " & dNewHours & " Hours"
    Unload ProjectStatusHours
    
    tbRH.Value = dOldHours + dNewHours    '<---------------------------------------------Change
    
    Call AddHoursToTimesheet(CStr(strJob), CStr(strDate), CDbl(dNewHours))
End Sub

Private Sub Label72_Click()
    If Not tbRC.Value = "" Then Exit Sub
    tbRC.Value = Date
End Sub

Private Sub Label73_Click()
    If Not tbRS.Value = "" Then Exit Sub
    tbRS.Value = Date
End Sub

Private Sub Label74_Click()
    If Not tbCDC.Value = "" Then Exit Sub
    tbCDC.Value = Date
End Sub

Private Sub Label75_Click()
    'Add Cleanup Hours
    Dim dNewHours, dOldHours, dTotal As Double
    Dim strDate As String
    
    If tbCDH.Value = "" Then    '<---------------------------------------------Change
        dOldHours = 0#
    Else
        dOldHours = CDbl(tbCDH.Value)    '<---------------------------------------------Change
    End If
    
    strJob = strProjectName
    
    Load ProjectStatusHours
        ProjectStatusHours.tbJob.Value = strJob
        ProjectStatusHours.show
        
        dNewHours = CDbl(ProjectStatusHours.tbHours.Value)
        strDate = ProjectStatusHours.tbDate.Value
        strJob = ProjectStatusHours.tbJob.Value
        'MsgBox strDate & " - " & dNewHours & " Hours"
    Unload ProjectStatusHours
    
    tbCDH.Value = dOldHours + dNewHours    '<---------------------------------------------Change
    
    Call AddHoursToTimesheet(CStr(strJob), CStr(strDate), CDbl(dNewHours))
End Sub

Private Sub Label77_Click()
    If Not tbCDS.Value = "" Then Exit Sub
    tbCDS.Value = Date
End Sub

Private Sub Label78_Click()
    Dim dNewHours, dOldHours, dTotal As Double
    Dim strDate As String
    
    If tbPLH.Value = "" Then
        dOldHours = 0#
    Else
        dOldHours = CDbl(tbPLH.Value)
    End If
    
    strJob = strProjectName
    
    Load ProjectStatusHours
        ProjectStatusHours.tbJob.Value = strJob
        ProjectStatusHours.show
        
        dNewHours = CDbl(ProjectStatusHours.tbHours.Value)
        strDate = ProjectStatusHours.tbDate.Value
        strJob = ProjectStatusHours.tbJob.Value
        'MsgBox strDate & " - " & dNewHours & " Hours"
    Unload ProjectStatusHours
    
    tbPLH.Value = dOldHours + dNewHours
    
    Call AddHoursToTimesheet(CStr(strJob), CStr(strDate), CDbl(dNewHours))
End Sub

Private Sub Label80_Click()
    If Not tbPLC.Value = "" Then Exit Sub
    tbPLC.Value = Date
End Sub

Private Sub Label81_Click()
    If tbPLI.Value = "" Then Exit Sub
    If Not tbPLS.Value = "" Then Exit Sub
    tbPLS.Value = Date
    
    SendCompleteEmail ("Planning Assigned")
    MsgBox "Email sent to Project Management"
End Sub

Private Sub Label84_Click()
    If Not tbPSC.Value = "" Then Exit Sub
    tbPSC.Value = Date
    
    Frame13.Enabled = True
End Sub

Private Sub Label85_Click()
    If tbPSI.Value = "" Then Exit Sub
    If Not tbPSS.Value = "" Then Exit Sub
    tbPSS.Value = Date
End Sub

Private Sub Label88_Click()
    If Not tbBC.Value = "" Then Exit Sub
    tbBC.Value = Date
    
    Frame11.Enabled = True
End Sub

Private Sub Label89_Click()
    If tbBI.Value = "" Then Exit Sub
    If Not tbBS.Value = "" Then Exit Sub
    tbBS.Value = Date
End Sub

Private Sub UserForm_Initialize()
    Dim strProject As String
    Dim vName As Variant
    
    strProject = ThisDrawing.Name
    vName = Split(strProject, " ")
    strProjectName = vName(0)
    Me.Caption = strProjectName & " Project Status"
    
    Call RefreshProjectForm
End Sub

Private Sub SendCompleteEmail(strStatus As String)
    If Not cbEmails.Value Then Exit Sub
    
    Dim objOutlook As Outlook.Application
    Dim objMail As Outlook.MailItem
    Dim strTo, strCC, strSubject, strBody As String
    Dim strVerb As String
    Dim strCompany, strPath As String
    Dim vTemp As Variant
    Dim iNumber, iEmailSelf As Integer
    Dim iMTEMC, iOther, iDWG As Integer
    
    On Error Resume Next
    
    vTemp = Split(Me.Caption, " ")
    
    If Right(strStatus, 1) = "s" Then
        strVerb = "have"
    Else
        strVerb = "has"
    End If
    
    strPath = ThisDrawing.Path
    strCompany = ""
    If InStr(UCase(strPath), "UNITED") Then strCompany = "UTC "
    If InStr(UCase(strPath), "LORETTO") Then strCompany = "Loretto "
    
    'strTo = "jon.wilburn@integrity-us.com;rich.taylor@integrity-us.com;jeremy.pafford@integrity-us.com"
    strSubject = "<Project Update> " & strCompany & strProjectName & " - " & strStatus & " Complete"
    strBody = "<b>" & strStatus & "</b> " & strVerb & " been completed and ready for the next stage."
    strTo = "jon.wilburn@integrity-us.com;rich.taylor@integrity-us.com"
    strCC = ""
    
    Load ProjectStatusEmail
    
    'Me.Hide

    Select Case strStatus
        Case "Units", "Counts"
            strTo = strTo & ";daniel.campbell@integrity-us.com"
        'Case "Prepare Job", "Fielding"
            'strTo = "jon.wilburn@integrity-us.com;rich.taylor@integrity-us.com;wade.hampton@integrity-us.com"
        Case "QC"
            strBody = GetQCData(strBody)
        Case "Cleanup"
            strBody = GetCleanupData(strBody)
            ProjectStatusEmail.lbCC.AddItem "Ronn.Elliott@Integrity-US.com"
        Case "Cut Out"
            ''If UCase(tbCOI.Value) = "TT" Then
                ''strBody = "Ronn, This one is now ready for you.  <span style='font-family:Segoe UI Emoji,sans-serif'>&#128522;</span><br><br>Tara"
            ''End If
            'strTo = "jon.wilburn@integrity-us.com;rich.taylor@integrity-us.com"
            Err = 0
            iNumber = GetLastDWG()
            If Not Err = 0 Then iNumber = 0
            strBody = strBody & "<br><b>" & iNumber & " Drawings</b>"
        'Case "Make Ready"
            'strTo = "jon.wilburn@integrity-us.com;rich.taylor@integrity-us.com"
        Case "Permits"
            'strTo = "jon.wilburn@integrity-us.com;rich.taylor@integrity-us.com"
            If tbPI.Value = "N/A" Then
                strSubject = "<Project Update> " & strCompany & vTemp(0) & " Permits - Not Required"
                strBody = "<b>Permits are not required for this Job.</b>"
            End If
        Case "Setup"
            strTo = "adam.kemper@integrity-us.com;jon.wilburn@integrity-us.com;rich.taylor@integrity-us.com"
            strSubject = "<Project Update> " & strCompany & vTemp(0) & " Planning Setup completed by " & tbPSI.Value
            strBody = "<b>BDK</b> is ready to be assigned."
            ProjectStatusEmail.lbCC.AddItem "Byron.Auer@Integrity-US.com"
            ProjectStatusEmail.lbCC.AddItem "Franklin.Angulo@Integrity-US.com"
            ProjectStatusEmail.lbCC.AddItem "Matt.Snyder@Integrity-US.com"
        Case "BDK"
            strTo = "adam.kemper@integrity-us.com;jon.wilburn@integrity-us.com;rich.taylor@integrity-us.com"
            strSubject = "<Project Update> " & strCompany & vTemp(0) & " BDK is completed by " & tbBI.Value
            strBody = "<b>Planning</b> is ready to be assigned."
            ProjectStatusEmail.lbCC.AddItem "Byron.Auer@Integrity-US.com"
            ProjectStatusEmail.lbCC.AddItem "Franklin.Angulo@Integrity-US.com"
            ProjectStatusEmail.lbCC.AddItem "Matt.Snyder@Integrity-US.com"
        Case "Planning"
            strTo = "adam.kemper@integrity-us.com;jon.wilburn@integrity-us.com;rich.taylor@integrity-us.com"
            strSubject = "<Project Update> " & strCompany & vTemp(0) & " Planning Review has completed by " & tbPLI.Value
            strBody = "<b>Prepare</b> is ready to be assigned."
            ProjectStatusEmail.lbCC.AddItem "Wade.Hampton@Integrity-US.com"
        Case "Planning Assigned"
            strTo = "adam.kemper@integrity-us.com;jon.wilburn@integrity-us.com;rich.taylor@integrity-us.com"
            strSubject = "<Project Update> " & strCompany & vTemp(0) & " Planning task assigned to " & tbPLI.Value
            strBody = "<b>" & tbPLI.Value & "</b> has been assigned " & vTemp(0) & " to plan."
        Case "Fielding Assigned"
            'strTo = "jon.wilburn@integrity-us.com;rich.taylor@integrity-us.com"
            strSubject = "<Project Update> " & strCompany & vTemp(0) & " Fielding task assigned to " & tbFI.Value
            strBody = "<b>" & tbFI.Value & "</b> has been assigned " & vTemp(0) & " to field."
        Case "Reports"
            strBody = strBody & vbCr & vbCr & "LU/BU: 0/0" & vbCr & "DWG: 0" & vbCr & "Route Footage: 0" & vbCr
            strBody = strBody & "JU Company:" & vbTab & "Unknown" & vbCr & "xx Total Poles" & vbCr & "xx Poles to OCALC"
            strBody = strBody & vbCr & vbCr & "City Permit:" & vbTab & "Unknown" & vbCr & "TDOT Permit:" & vbTab & "Unknown"
            strBody = strBody & vbCr & "RR Permit:" & vbTab & "Unknown" & vbCr & vbCr & "Make Ready Required:" & vbCr & "None"
            strBody = strBody & vbCr & vbCr & "Notes:" & vbCr & "None"
    End Select
    
    strBody = strBody & vbCr & vbCr & "<b>THIS JOB IS USING ENGINEERING 2.0</b>"
    
    ProjectStatusEmail.tbBody.Value = Replace(strBody, "<br>", vbCr)
    ProjectStatusEmail.tbSubject.Value = strSubject
    ProjectStatusEmail.show
    'Me.show
    
    strBody = Replace(ProjectStatusEmail.tbBody.Value, vbCr, "<br>")
    If strBody = "" Then
        iEmailSent = 0
        Exit Sub
    Else
        iEmailSent = 1
    End If
    
    If ProjectStatusEmail.cbCcSelf.Value = True Then
        iEmailSelf = 1
    Else
        iEmailSelf = 0
    End If
    
    If ProjectStatusEmail.lbCC.ListCount > -1 Then
        For n = 0 To ProjectStatusEmail.lbCC.ListCount - 1
            strCC = strCC & ProjectStatusEmail.lbCC.List(n) & ";"
        Next n
    End If
    
    Unload ProjectStatusEmail
    
    Set objOutlook = New Outlook.Application
    Set objMail = objOutlook.CreateItem(olMailItem)
    
    objMail.To = strTo  '"rich.taylor@integrity-us.com"
    'objMail.To = objOutlook.Session.CurrentUser.Address
    If iEmailSelf = 1 Then strCC = strCC & objOutlook.Session.CurrentUser.Address
    objMail.CC = strCC  'objOutlook.Session.CurrentUser.Address
    objMail.Subject = strSubject
    objMail.HTMLBody = strBody
    
    'objMail.Display
    objMail.Send
End Sub

Private Sub RefreshProjectForm()
    Dim strProject As String
    Dim vName As Variant
    
    Dim str As String
    
    Dim strDWGPath As String
    Dim strDWGName As String
    Dim vItem As Variant
    Dim fName As String
    'Dim iCount As Integer
    
    'strProject = ThisDrawing.Name
    'vName = Split(strProject, " ")
    strFileName = ThisDrawing.Path & "\" & strProjectName & " Project Status.pjs"
    
    fName = Dir(strFileName)
    If fName = "" Then
        Exit Sub
    End If
    
    Open strFileName For Input As #2
    
    While Not EOF(2)
        Input #2, str
        
        vName = Split(str, vbTab)
        
        Select Case vName(0)
            Case "SETUP:"
                If UBound(vName) > 0 Then
                    If vName(1) = "" Then GoTo Next_line
                    tbPSI.Value = vName(1)
                    tbPSI.Enabled = False
                End If
                If UBound(vName) > 1 Then
                    tbPSS.Value = vName(2)
                    If Not vName(2) = "" Then tbPSS.Enabled = False
                End If
                If UBound(vName) > 2 Then
                    tbPSC.Value = vName(3)
                    If Not vName(3) = "" Then
                        tbPSC.Enabled = False
                        Frame12.ForeColor = &H8000000D
                    End If
                End If
                If UBound(vName) > 3 Then tbPSH.Value = vName(4)
            Case "BDK:"
                If UBound(vName) > 0 Then
                    Frame13.Enabled = True
                    If vName(1) = "" Then GoTo Next_line
                    tbBI.Value = vName(1)
                    tbBI.Enabled = False
                End If
                If UBound(vName) > 1 Then
                    tbBS.Value = vName(2)
                    If Not vName(2) = "" Then tbBS.Enabled = False
                End If
                If UBound(vName) > 2 Then
                    tbBC.Value = vName(3)
                    If Not vName(3) = "" Then
                        tbBC.Enabled = False
                        Frame13.ForeColor = &H8000000D
                    End If
                End If
                If UBound(vName) > 3 Then tbBH.Value = vName(4)
            Case "PLANNING:"
                If UBound(vName) > 0 Then
                    Frame11.Enabled = True
                    If vName(1) = "" Then GoTo Next_line
                    tbPLI.Value = vName(1)
                    tbPLI.Enabled = False
                End If
                If UBound(vName) > 1 Then
                    tbPLS.Value = vName(2)
                    If Not vName(2) = "" Then tbPLS.Enabled = False
                End If
                If UBound(vName) > 2 Then
                    tbPLC.Value = vName(3)
                    If Not vName(3) = "" Then
                        tbPLC.Enabled = False
                        Frame11.ForeColor = &H8000000D
                    End If
                End If
                If UBound(vName) > 3 Then tbPLH.Value = vName(4)
            Case "PREPARE:"
                If UBound(vName) > 0 Then
                    If vName(1) = "" Then GoTo Next_line
                    tbCOI.Value = vName(1)
                    tbCOI.Enabled = False
                End If
                If UBound(vName) > 1 Then
                    tbCOS.Value = vName(2)
                    If Not vName(2) = "" Then tbCOS.Enabled = False
                End If
                If UBound(vName) > 2 Then
                    tbCOC.Value = vName(3)
                    If Not vName(3) = "" Then
                        tbCOC.Enabled = False
                        Frame2.ForeColor = &H8000000D
                    End If
                End If
                If UBound(vName) > 3 Then tbCOH.Value = vName(4)
            Case "FIELD:"
                If UBound(vName) > 0 Then
                    If vName(1) = "" Then GoTo Next_line
                    tbFI.Value = vName(1)
                    tbFI.Enabled = False
                End If
                If UBound(vName) > 1 Then
                    tbFS.Value = vName(2)
                    If Not vName(2) = "" Then tbFS.Enabled = False
                End If
                If UBound(vName) > 2 Then
                    tbFC.Value = vName(3)
                    If Not vName(3) = "" Then
                        tbFC.Enabled = False
                        Frame1.ForeColor = &H8000000D
                    End If
                End If
                If UBound(vName) > 3 Then tbFH.Value = vName(4)
            Case "CLEANUP:"
                If UBound(vName) > 0 Then
                    If vName(1) = "" Then GoTo Next_line
                    tbCUI.Value = vName(1)
                    tbCUI.Enabled = False
                End If
                If UBound(vName) > 1 Then
                    tbCUS.Value = vName(2)
                    If Not vName(2) = "" Then tbCUS.Enabled = False
                End If
                If UBound(vName) > 2 Then
                    tbCUC.Value = vName(3)
                    If Not vName(3) = "" Then
                        tbCUC.Enabled = False
                        Frame3.ForeColor = &H8000000D
                    End If
                End If
                If UBound(vName) > 3 Then tbCUH.Value = vName(4)
            Case "CUT OUT:"
                If UBound(vName) > 0 Then
                    If vName(1) = "" Then GoTo Next_line
                    tbCDI.Value = vName(1)
                    tbCDI.Enabled = False
                End If
                If UBound(vName) > 1 Then
                    tbCDS.Value = vName(2)
                    If Not vName(2) = "" Then tbCDS.Enabled = False
                End If
                If UBound(vName) > 2 Then
                    tbCDC.Value = vName(3)
                    If Not vName(3) = "" Then
                        tbCDC.Enabled = False
                        Frame10.ForeColor = &H8000000D
                    End If
                End If
                If UBound(vName) > 3 Then tbCDH.Value = vName(4)
            Case "MAKE READY:"
                If UBound(vName) > 0 Then
                    If vName(1) = "" Then GoTo Next_line
                    tbMRI.Value = vName(1)
                    tbMRI.Enabled = False
                End If
                If UBound(vName) > 1 Then
                    tbMRS.Value = vName(2)
                    If Not vName(2) = "" Then tbMRS.Enabled = False
                End If
                If UBound(vName) > 2 Then
                    tbMRC.Value = vName(3)
                    If Not vName(3) = "" Then
                        tbMRC.Enabled = False
                        Frame4.ForeColor = &H8000000D
                    End If
                End If
                If UBound(vName) > 3 Then tbMRH.Value = vName(4)
            Case "PERMITS:"
                If UBound(vName) > 0 Then
                    If vName(1) = "" Then GoTo Next_line
                    tbPI.Value = vName(1)
                    tbPI.Enabled = False
                End If
                If UBound(vName) > 1 Then
                    tbPS.Value = vName(2)
                    If Not vName(2) = "" Then tbPS.Enabled = False
                End If
                If UBound(vName) > 2 Then
                    tbPC.Value = vName(3)
                    If Not vName(3) = "" Then
                        tbPC.Enabled = False
                        Frame5.ForeColor = &H8000000D
                    End If
                End If
                If UBound(vName) > 3 Then tbPH.Value = vName(4)
            Case "COUNTS:"
                If UBound(vName) > 0 Then
                    If vName(1) = "" Then GoTo Next_line
                    tbCntI.Value = vName(1)
                    tbCntI.Enabled = False
                End If
                If UBound(vName) > 1 Then
                    tbCntS.Value = vName(2)
                    If Not vName(2) = "" Then tbCntS.Enabled = False
                End If
                If UBound(vName) > 2 Then
                    tbCntC.Value = vName(3)
                    If Not vName(3) = "" Then
                        tbCntC.Enabled = False
                        Frame6.ForeColor = &H8000000D
                    End If
                End If
                If UBound(vName) > 3 Then tbCntH.Value = vName(4)
            Case "UNITS:"
                If UBound(vName) > 0 Then
                    If vName(1) = "" Then GoTo Next_line
                    tbUI.Value = vName(1)
                    tbUI.Enabled = False
                End If
                If UBound(vName) > 1 Then
                    tbUS.Value = vName(2)
                    If Not vName(2) = "" Then tbUS.Enabled = False
                End If
                If UBound(vName) > 2 Then
                    tbUC.Value = vName(3)
                    If Not vName(3) = "" Then
                        tbUC.Enabled = False
                        Frame7.ForeColor = &H8000000D
                    End If
                End If
                If UBound(vName) > 3 Then tbUH.Value = vName(4)
            Case "QC:"
                If UBound(vName) > 0 Then
                    If vName(1) = "" Then GoTo Next_line
                    tbQCI.Value = vName(1)
                    tbQCI.Enabled = False
                End If
                If UBound(vName) > 1 Then
                    tbQCS.Value = vName(2)
                    If Not vName(2) = "" Then tbQCS.Enabled = False
                End If
                If UBound(vName) > 2 Then
                    tbQCC.Value = vName(3)
                    If Not vName(3) = "" Then
                        tbQCC.Enabled = False
                        Frame8.ForeColor = &H8000000D
                    End If
                End If
                If UBound(vName) > 3 Then tbQCH.Value = vName(4)
            Case "REPORTS:"
                If UBound(vName) > 0 Then
                    If vName(1) = "" Then GoTo Next_line
                    tbRI.Value = vName(1)
                    tbRI.Enabled = False
                End If
                If UBound(vName) > 1 Then
                    tbRS.Value = vName(2)
                    If Not vName(2) = "" Then tbRS.Enabled = False
                End If
                If UBound(vName) > 2 Then
                    tbRC.Value = vName(3)
                    If Not vName(3) = "" Then
                        tbRC.Enabled = False
                        Frame9.ForeColor = &H8000000D
                    End If
                End If
                If UBound(vName) > 3 Then tbRH.Value = vName(4)
        End Select
Next_line:
    Wend
    
    Close #2
End Sub

Private Sub AddHoursToTimesheet(strJob As String, strDate As String, dHours As Double)
    Dim excelApp As Excel.Application
    Dim ws As Excel.Worksheet
    Dim strPath As String
    Dim iRow, iColumn As Integer
    Dim fName As String
    Dim strComputer, strFile As String
    
    strComputer = Environ$("Username")
    
    strFile = "C:\Users\" & strComputer & "\Documents\Work\Timesheets\Active Timesheet.xlsx"
    
    fName = Dir(strFile)
    If fName = "" Then
        MsgBox "There is no Timesheet ready."
        Exit Sub
    End If
    
    On Error Resume Next
    
    Set excelApp = CreateObject("Excel.Application")
    'excelApp.Visible = True
    excelApp.Visible = False
    
    'excelApp.Workbooks.Add
    Set ws = excelApp.ActiveWorkbook.Sheets("Sheet1")
    'Set wb = Nothing
    
    Err = 0
    Set wb = Excel.Workbooks.Open(strFile)
    If Not Err = 0 Then
        MsgBox "Error opening file"
        Exit Sub
    End If
    iRow = 5
    
    While iRow < 60
        For iColumn = 2 To 7
            If InStr(1, Sheets("Sheet1").Cells(iRow, iColumn).Value, strDate, vbTextCompare) > 0 Then GoTo Exit_While
        Next iColumn
        iRow = iRow + 1
    Wend
Exit_While:
    
    'MsgBox "Cell(" & iRow & " , " & iColumn & ")"
    
    iRow = iRow + 2
    While iRow < 60
        If InStr(1, Sheets("Sheet1").Cells(iRow, 1).Value, strJob, vbTextCompare) > 0 Then GoTo Exit_While2
        If Sheets("Sheet1").Cells(iRow, 1).Value = "" Then
            Sheets("Sheet1").Cells(iRow, 1).Value = strJob
            GoTo Exit_While2
        End If
        
        iRow = iRow + 1
    Wend
Exit_While2:
    
    If iRow < 60 Then
        Sheets("Sheet1").Cells(iRow, iColumn).Value = Sheets("Sheet1").Cells(iRow, iColumn).Value + dHours
    End If
    
    ActiveWorkbook.Save
    ActiveWorkbook.Close
    
    excelApp.Quit
End Sub

Private Function GetLastDWG()
    Dim filterType, filterValue As Variant  '
    Dim grpCode(0) As Integer               '
    Dim grpValue(0) As Variant              '
    Dim objSS7 As AcadSelectionSet          '
    Dim objDWG As AcadBlockReference        '
    Dim vAttList, vTemp As Variant          '
    Dim iCount As Integer
    
    iCount = 0
    
    grpCode(0) = 2
    grpValue(0) = "SS-11x17"
    filterType = grpCode
    filterValue = grpValue
    
    Set objSS7 = ThisDrawing.SelectionSets.Add("objSS7")
    objSS7.Select acSelectionSetAll, , , filterType, filterValue
    
    For Each objDWG In objSS7
        vAttList = objDWG.GetAttributes
            vTemp = Split(vAttList(0).TextString, " ")
            If vTemp(0) = "DWG" Then
                If UBound(vTemp) > 0 Then
                    If CInt(vTemp(1)) > iCount Then
                        iCount = CInt(vTemp(1))
                    End If
                End If
            End If
    Next objDWG
    
    GetLastDWG = iCount
End Function

Private Function GetCleanupData(strText As String)
    Dim objSSTemp2 As AcadSelectionSet
    Dim filterType, filterValue As Variant
    Dim grpCode(0) As Integer
    Dim grpValue(0) As Variant
    Dim entItem As AcadEntity
    Dim obrTemp As AcadBlockReference
    Dim vAttList, vTemp As Variant
    Dim iMTEMC, iOther, iUTC As Integer
    Dim iDWG As Integer
    
    iMTEMC = 0
    iOther = 0
    iUTC = 0
    iDWG = 0

    grpCode(0) = 2
    grpValue(0) = "iPole"
    filterType = grpCode
    filterValue = grpValue
  
    Set objSSTemp2 = ThisDrawing.SelectionSets.Add("objSSTemp2")
    objSSTemp2.Select acSelectionSetAll, , , filterType, filterValue
    
    For Each obrTemp In objSSTemp2
        vAttList = obrTemp.GetAttributes
        If Not vAttList(0).TextString = "POLE" Then
            Select Case obrTemp.Layer
                Case "Integrity Poles-Power"
                    iMTEMC = iMTEMC + 1
                Case "Integrity Poles-Other"
                    iOther = iOther + 1
                Case "Integrity Poles-UTC"
                    iUTC = iUTC + 1
            End Select
        End If
    Next obrTemp
    
    objSSTemp2.Clear

    grpCode(0) = 2
    grpValue(0) = "SS-11x17"
    filterType = grpCode
    filterValue = grpValue
    
    objSSTemp2.Select acSelectionSetAll, , , filterType, filterValue
    
    For Each obrTemp In objSSTemp2
        vAttList = obrTemp.GetAttributes
        If obrTemp.Layer = "Integrity Sheets" Then
            vTemp = Split(vAttList(0).TextString, " ")
            If UBound(vTemp) > 0 Then
                If iDWG < CInt(vTemp(1)) Then iDWG = CInt(vTemp(1))
            End If
        End If
    Next obrTemp
    
    objSSTemp2.Clear
    objSSTemp2.Delete
    
    strText = strText & "<br>" & iMTEMC & " Power Poles<br>" & iUTC & " UTC Poles<br>" & iOther & " Other Poles<br>"
    strText = strText & "<br>" & iDWG & " Drawings<br>"
    
    GetCleanupData = strText
End Function

Private Function GetQCData(strText As String)
    Dim objSSTemp2 As AcadSelectionSet
    Dim filterType, filterValue As Variant
    Dim grpCode(0) As Integer
    Dim grpValue(0) As Variant
    Dim entItem As AcadEntity
    'Dim obrTemp As AcadBlockReference
    Dim objText As AcadText
    Dim objMText As AcadMText
    Dim vTemp As Variant
    Dim strTemp As String
    Dim iOCALC As Integer
    
    iOCALC = 0

    grpCode(0) = 8
    grpValue(0) = "Integrity Poles-Other"
    filterType = grpCode
    filterValue = grpValue
  
    Set objSSTemp2 = ThisDrawing.SelectionSets.Add("objSSTemp2")
    objSSTemp2.Select acSelectionSetAll, , , filterType, filterValue
    
    For Each entItem In objSSTemp2
        If TypeOf entItem Is AcadText Then
            Set objText = entItem
            vTemp = Split(objText.TextString, " ")
            If UBound(vTemp) > 0 Then
                If vTemp(1) = "POLES" Then
                    iOCALC = CInt(vTemp(0))
                    GoTo Exit_For
                End If
            End If
        End If
        
        If TypeOf entItem Is AcadMText Then
            Set objMText = entItem
            vTemp = Split(objMText.TextString, " ")
            If UBound(vTemp) > 0 Then
                If vTemp(1) = "POLES" Then
                    iOCALC = CInt(vTemp(0))
                    GoTo Exit_For
                End If
            End If
        End If
    Next entItem
Exit_For:
    
    strText = strText & "<br>" & iOCALC & " Poles to OCALC"
    GetQCData = strText
End Function

Attribute VB_Name = "ProjectStatusEmail"
Attribute VB_Base = "0{0EE52011-4975-463A-A68C-FFE0DF2EFE16}{C5F8FF4B-086D-48DE-9022-D874709EE092}"
Attribute VB_GlobalNameSpace = False
Attribute VB_Creatable = False
Attribute VB_PredeclaredId = True
Attribute VB_Exposed = False
Attribute VB_TemplateDerived = False
Attribute VB_Customizable = False

Private Sub AddRouteInfo_Click()
    Me.Hide
    Load GetCableLengths
        GetCableLengths.show
        
        tbBody.Value = tbBody.Value & vbCr & vbCr & "<b>Layer:</b>" & vbTab & GetCableLengths.lbLayers.Value
        tbBody.Value = tbBody.Value & vbCr & "<b>Route Miles =</b>" & vbTab & GetCableLengths.tbTotalMiles.Value
        tbBody.Value = tbBody.Value & vbCr & "<b>Route KF =</b>" & vbTab & GetCableLengths.tbTotalFeet.Value
    Unload GetCableLengths
    Me.show
End Sub

Private Sub cbAddRuBu_Click()
    Me.Hide
    Load LoadBlocks
        LoadBlocks.show
        
        tbBody.Value = tbBody.Value & vbCr & vbCr & "<b>RU =</b>" & vbTab & LoadBlocks.tbRES.Value
        tbBody.Value = tbBody.Value & vbCr & "<b>BU =</b>" & vbTab & LoadBlocks.tbBUS.Value
        tbBody.Value = tbBody.Value & vbCr & "<b>SG =</b>" & vbTab & LoadBlocks.tbSG.Value
    Unload LoadBlocks
    Me.show
End Sub

Private Sub cbCancel_Click()
    tbBody.Value = ""
    Me.Hide
End Sub

Private Sub cbConvert_Click()
    Dim strText As String
    
    strText = tbBody.Value
    strText = Replace(strText, "<br>", vbCr)
    
    tbBody.Value = strText
End Sub

Private Sub cbSend_Click()
    Me.Hide
End Sub

Private Sub lbCC_KeyDown(ByVal KeyCode As MSForms.ReturnInteger, ByVal Shift As Integer)
    If lbCC.ListCount < 0 Then Exit Sub
    
    Select Case KeyCode
        Case vbKeyDelete
            lbCC.RemoveItem lbCC.ListIndex
    End Select
End Sub

Private Sub lbEmails_DblClick(ByVal Cancel As MSForms.ReturnBoolean)
    lbCC.AddItem lbEmails.List(lbEmails.ListIndex)
End Sub

Private Sub UserForm_Initialize()
    lbCC.Clear
    lbEmails.AddItem "Adam.Kemper@Integrity-US.com"
    'lbEmails.AddItem "Alex.Skae@Integrity-US.com"
    lbEmails.AddItem "Byron.Auer@Integrity-US.com"
    lbEmails.AddItem "Daniel.Campbell@Integrity-US.com"
    lbEmails.AddItem "Drew.Curtis@Integrity-US.com"
    lbEmails.AddItem "Dylan.Spears@Integrity-US.com"
    lbEmails.AddItem "Franklin.Angulo@Integrity-US.com"
    lbEmails.AddItem "Jason.Pafford@Integrity-US.com"
    lbEmails.AddItem "Jay.Penny@Integrity-US.com"
    lbEmails.AddItem "Jeremy.Pafford@Integrity-US.com"
    lbEmails.AddItem "Jon.Wilburn@Integrity-US.com"
    lbEmails.AddItem "Matt.Snyder@Integrity-US.com"
    lbEmails.AddItem "Rich.Taylor@Integrity-US.com"
    lbEmails.AddItem "Ronn.Elliott@Integrity-US.com"
    lbEmails.AddItem "Sam.Jackson@Integrity-US.com"
    lbEmails.AddItem "Tara.Taylor@Integrity-US.com"
    lbEmails.AddItem "Wade.Hampton@Integrity-US.com"
End Sub

Attribute VB_Name = "ProjectStatusHours"
Attribute VB_Base = "0{4F4D5C32-925A-4F57-966F-D56B7C04816B}{672066D0-736F-4D08-B660-51B13DA16134}"
Attribute VB_GlobalNameSpace = False
Attribute VB_Creatable = False
Attribute VB_PredeclaredId = True
Attribute VB_Exposed = False
Attribute VB_TemplateDerived = False
Attribute VB_Customizable = False

Private Sub cbAdd_Click()
    Me.Hide
End Sub

Private Sub Label1_Click()
    tbDate.Value = Date
End Sub

Attribute VB_Name = "RearrangeCounts"
Attribute VB_Base = "0{D7568889-E17E-4ED4-8297-2D4FE2234E25}{6ABBEDD7-CC1A-4B2E-9591-47C6303468D6}"
Attribute VB_GlobalNameSpace = False
Attribute VB_Creatable = False
Attribute VB_PredeclaredId = True
Attribute VB_Exposed = False
Attribute VB_TemplateDerived = False
Attribute VB_Customizable = False
Dim objBlock As AcadBlockReference
Dim iListIndex As Integer

Private Sub cbAddRange_Click()
    If cbAddRange.Caption = "Update" Then
        If tbRFibers.Value = "" Then GoTo Done_Updating
        If tbRName.Value = "" Then tbRName.Value = "**"
        If tbRCounts.Value = "" Then tbRCounts.Value = "*-*"
        
        lbRange.List(iListIndex, 0) = tbRFibers.Value
        lbRange.List(iListIndex, 1) = tbRName.Value
        lbRange.List(iListIndex, 2) = tbRCounts.Value
        
Done_Updating:
        cbAddRange.Caption = "Add Range"
        Exit Sub
    End If
    
    If cbCableSize.Value = "" Then Exit Sub
    If tbRFibers.Value = "" Then Exit Sub
    If tbRName.Value = "" Then Exit Sub
    If tbRCounts.Value = "" Then Exit Sub
    
    'lbRange.AddItem tbRFibers.Value
    'lbRange.List(lbRange.ListCount - 1, 1) = tbRName.Value
    'lbRange.List(lbRange.ListCount - 1, 2) = tbRCounts.Value
    
    Dim vCounts As Variant
    Dim strName As String
    Dim iIndex, iSize, iTemp As Integer
    Dim iStart, iEnd As Integer
    Dim iLStart, iLEnd As Integer
    Dim iLCStart, iLCEnd As Integer
    
    iSize = CInt(cbCableSize.Value)
    
    vCounts = Split(tbRFibers.Value, "-")
    iStart = CInt(vCounts(0))
    If UBound(vCounts) = 0 Then
        iEnd = iStart
    Else
        iEnd = CInt(vCounts(1))
    End If
    
    If iStart > iSize Then Exit Sub
    'If iEnd > iSize Then iEnd = iSize
    
    For i = 0 To lbRange.ListCount - 1
        If Not lbRange.List(i, 1) = "**" And Not lbRange.List(i, 2) = "*-*" Then GoTo Not_Present
        
        strName = lbRange.List(i, 1)
        
        vCounts = Split(lbRange.List(i, 0), "-")
        iLStart = CInt(vCounts(0))
        iLEnd = CInt(vCounts(1))
        
        If iStart > iLEnd Then GoTo Not_Present
        
        Select Case (iLStart - iStart)
            Case Is = 0
                Select Case (iLEnd - iEnd)
                    Case Is < 0
                        lbRange.List(i, 1) = tbRName.Value
                        If tbRCounts.Value = "*-*" Then
                            lbRange.List(i, 2) = tbRCounts.Value
                        Else
                            vCounts = Split(tbRCounts.Value, "-")
                            vCounts(1) = CInt(vCounts(0)) + iLEnd - iLStart
                            
                            lbRange.List(i, 2) = vCounts(0) & "-" & vCounts(1)
                        End If
                    Case Is = 0
                        lbRange.List(i, 0) = tbRFibers.Value
                        lbRange.List(i, 1) = tbRName.Value
                        lbRange.List(i, 2) = tbRCounts.Value
                    Case Is > 0
                        lbRange.List(i, 0) = tbRFibers.Value
                        lbRange.List(i, 1) = tbRName.Value
                        lbRange.List(i, 2) = tbRCounts.Value
                        
                        iTemp = iEnd + 1
                        lbRange.AddItem iTemp & "-" & iLEnd, i + 1
                        lbRange.List(i + 1, 1) = strName
                        lbRange.List(i + 1, 2) = "*-*"
                End Select
            Case Is > 0
                Select Case (iLEnd - iEnd)
                    
                End Select
        End Select
        
Not_Present:
    Next i
    
    tbRFibers.Value = ""
    tbRName.Value = ""
    tbRCounts.Value = ""
    tbRFibers.SetFocus
End Sub

Private Sub cbAddToList_Click()
    If tbEndFibers.Value = "" Then Exit Sub
    If tbSource.Value = "" Then Exit Sub
    
    lbList.AddItem tbEndFibers.Value
    If UCase(tbSource.Value) = "XD" Then tbSource.Value = UCase(tbSource.Value) & ": " & tbEndFibers.Value
    lbList.List(lbList.ListCount - 1, 1) = tbSource.Value
    
    tbEndFibers.Value = ""
    tbSource.Value = ""
    tbEndFibers.SetFocus
End Sub

Private Sub cbCableSize_Change()
    If cbCableSize.Value = "" Then Exit Sub
    
    lbRange.Clear
    lbRange.AddItem "1-" & cbCableSize.Value
    lbRange.List(0, 1) = "**"
    lbRange.List(0, 2) = "*-*"
End Sub

Private Sub cbGetBlock_Click()
    Dim objEntity As AcadEntity
    Dim vReturnPnt As Variant
    Dim vAttList As Variant
    Dim strLine, strCable As String
    Dim iStart, iEnd, iSize As Integer
    
    Me.Hide
    
    On Error Resume Next
    ThisDrawing.Utility.GetEntity objEntity, vReturnPnt, vbCr & "Select Block:"
    If Not Err = 0 Then GoTo Exit_Sub
    
    If Not TypeOf objEntity Is AcadBlockReference Then GoTo Exit_Sub
    Set objBlock = objEntity
    vAttList = objBlock.GetAttributes
    
    Dim vLine, vItem, vCounts, vTemp As Variant
    
    Select Case objBlock.Name
        Case "sPole"
            strLine = vAttList(25).TextString
        Case "sPed", "sHH", "sFP", "sMH", "sPanel"
            strLine = vAttList(5).TextString
        Case "Callout"
            strCable = vAttList(1).TextString
            vLine = Split(strCable, ")")
            vItem = Split(vLine(0), "(")
            iSize = CInt(vItem(1))
            'If Not vItem(1) = cbCableSize.Value Then
                'If cbCableSize.Value = "" Then
                    'cbCableSize.Value = vItem(1)
                'Else
                    'GoTo Exit_Sub
                'End If
            'End If
            
            strLine = Replace(vAttList(2).TextString, "\P", " + ")
            strCable = vAttList(1).TextString
            'MsgBox strLine
            GoTo Fixed_Line
        Case "CableCounts"
            strCable = vAttList(1).TextString
            vLine = Split(strCable, ")")
            vItem = Split(vLine(0), "(")
            iSize = CInt(vItem(1))
            'If Not vItem(1) = cbCableSize.Value Then
                'If cbCableSize.Value = "" Then
                    'cbCableSize.Value = vItem(1)
                'Else
                    'GoTo Exit_Sub
                'End If
            'End If
            
            strLine = Replace(vAttList(0).TextString, "\P", " + ")
            strCable = vAttList(1).TextString
            'MsgBox strLine
            GoTo Fixed_Line
        Case Else
            GoTo Exit_Sub
    End Select
    
    vLine = Split(strLine, " / ")
    strCable = vLine(0)
    
    vItem = Split(strCable, ")")
    vTemp = Split(vItem(0), "(")
    iSize = CInt(vTemp(1))
    
    If lbList.ListCount < 1 Then
        lbList.AddItem "1-" & iSize
        lbList.List(0, 1) = "1-" & iSize
    End If
    'If Not vTemp(1) = cbCableSize.Value Then
        'If cbCableSize.Value = "" Then
            'cbCableSize.Value = vTemp(1)
        'Else
            'GoTo Exit_Sub
        'End If
    'End If
    
    strLine = vLine(1)
    
Fixed_Line:
    
    'If cbCableSize.Value = "" Then GoTo Exit_Sub
    If strLine = "" Then GoTo Exit_Sub
    
    Dim strName, strSource As String
    Dim iFiber As Integer
    
    iFiber = 1
    lbCounts.Clear
    'lbCounts.AddItem ""
    
    vLine = Split(strLine, " + ")
    For i = 0 To UBound(vLine)
        vItem = Split(vLine(i), ": ")
        strName = vItem(0)
        If UBound(vItem) < 2 Then
            strSource = ""
        Else
            strSource = vItem(2)
        End If
        
        vCounts = Split(vItem(1), "-")
        iStart = CInt(vCounts(0))
        If UBound(vCounts) < 1 Then
            iEnd = iStart
        Else
            iEnd = CInt(vCounts(1))
        End If
        
        strLine = iFiber & "-"
        iFiber = iFiber + iEnd - iStart
        strLine = strLine & iFiber
        
        lbCounts.AddItem strLine
        lbCounts.List(lbCounts.ListCount - 1, 1) = strName
        lbCounts.List(lbCounts.ListCount - 1, 2) = vItem(1)
        lbCounts.List(lbCounts.ListCount - 1, 3) = strSource
        
        iFiber = iFiber + 1
        
        'For j = iStart To iEnd
            'lbCounts.AddItem iFiber
            'lbCounts.List(lbCounts.ListCount - 1, 1) = strName
            'lbCounts.List(lbCounts.ListCount - 1, 2) = j
            'lbCounts.List(lbCounts.ListCount - 1, 3) = strSource
            
            'iFiber = iFiber + 1
        'Next j
    Next i
    
    tbCable.Value = strCable
    
Exit_Sub:
    Me.show
End Sub

Private Sub cbRearrange_Click()
    If lbList.ListCount < 1 Then Exit Sub
    If lbCounts.ListCount < 1 Then Exit Sub
    If cbEndFiber.Value = "" Then Exit Sub
    
    Dim vLine, vItem, vCounts, vTemp As Variant
    Dim strResult, strLine, strName, strSource As String
    Dim iFStart, iFEnd As Integer
    Dim iCStart, iCEnd As Integer
    Dim iTStart, iTEnd As String
    Dim iFiber As Integer
    
    iFiber = 1
    strResult = ""
    
    If InStr(tbCable.Value, cbCableSize.Value) = 0 Then
        Exit Sub
    End If
    
    tbCable.Value = Replace(tbCable.Value, cbCableSize.Value, cbEndFiber.Value)
    
    For i = 0 To lbList.ListCount - 1
        vLine = Split(lbList.List(i, 1), ": ")
        
        Select Case UBound(vLine)
            Case Is = 0
                vCounts = Split(vLine(0), "-")
                iFStart = CInt(vCounts(0))
                If UBound(vCounts) = 0 Then
                    iFEnd = iFStart
                Else
                    iFEnd = CInt(vCounts(1))
                End If
                
                For j = 0 To lbCounts.ListCount - 1
                    strLine = ""
                    vCounts = Split(lbCounts.List(j, 0), "-")
                    iCStart = CInt(vCounts(0))
                    If UBound(vCounts) = 0 Then
                        iCEnd = iCStart
                    Else
                        iCEnd = CInt(vCounts(1))
                    End If
                    
                    'MsgBox "FS: " & iFStart & vbTab & "FE: " & iFEnd & vbCr & "CS: " & iCStart & vbTab & "CE: " & iCEnd
                    
                    Select Case iFStart - iCStart
                        Case Is = 0
                            Select Case iFEnd - iCEnd
                                Case Is < 0
                                    vCounts = Split(lbCounts.List(j, 2), "-")
                                    vCounts(1) = CInt(vCounts(0)) + iFEnd - iFStart
                                    strLine = lbCounts.List(j, 1) & ": " & vCounts(0) & "-" & vCounts(1)
                                    If Not lbCounts.List(j, 3) = "" Then strLine = strLine & ": " & lbCounts.List(j, 3)
                                Case Is = 0
                                    strLine = lbCounts.List(j, 1) & ": " & lbCounts.List(j, 2)
                                    
                                    If Not lbCounts.List(j, 3) = "" Then strLine = strLine & ": " & lbCounts.List(j, 3)
                                Case Is > 0
                                    strLine = lbCounts.List(j, 1) & ": " & lbCounts.List(j, 2)
                                    
                                    If Not lbCounts.List(j, 3) = "" Then strLine = strLine & ": " & lbCounts.List(j, 3)
                                    iFStart = iCEnd + 1
                            End Select
                        Case Is > 0
                            If iFStart > iCEnd Then GoTo Next_line
                            
                            vCounts = Split(lbCounts.List(j, 2), "-")
                            vCounts(0) = CInt(vCounts(0)) + iFStart - iCStart
                            
                            Select Case iFEnd - iCEnd
                                Case Is < 0
                                    vCounts(1) = CInt(vCounts(0)) + iFEnd - iFStart
                                    
                                    strLine = lbCounts.List(j, 1) & ": " & vCounts(0) & "-" & vCounts(1)
                                    If Not lbCounts.List(j, 3) = "" Then strLine = strLine & ": " & lbCounts.List(j, 3)
                                Case Is = 0
                                    vCounts(1) = CInt(vCounts(0)) + iFEnd - iFStart
                                    
                                    strLine = lbCounts.List(j, 1) & ": " & vCounts(0) & "-" & vCounts(1)
                                    
                                    If Not lbCounts.List(j, 3) = "" Then strLine = strLine & ": " & lbCounts.List(j, 3)
                                Case Is > 0
                                    strLine = lbCounts.List(j, 1) & ": " & vCounts(0) & "-" & vCounts(1)
                                    
                                    If Not lbCounts.List(j, 3) = "" Then strLine = strLine & ": " & lbCounts.List(j, 3)
                                    iFStart = iCEnd + 1
                            End Select
                        Case Is < 0
                            'If iCStart > iFEnd Then GoTo Next_Line
                            
                            
                            GoTo Next_line
                    End Select
                    
                    If strResult = "" Then
                        strResult = strLine
                    Else
                        strResult = strResult & vbCr & strLine
                    End If
Next_line:
                    'MsgBox "i: " & i & vbCr & "j: " & j & vbCr & "strLine:  " & strLine
                Next j
            Case Is > 0
                strLine = lbList.List(i, 1)
        
                If strResult = "" Then
                    strResult = strLine
                Else
                    strResult = strResult & vbCr & strLine
                End If
        End Select
    Next i
    
    iFiber = 1
    strSource = ""
    vLine = Split(strResult, vbCr)
    For i = 0 To UBound(vLine)
        vItem = Split(vLine(i), ": ")
        If UBound(vItem) > 1 Then
            If Not vItem(2) = "" Then strSource = vItem(2)
        End If
        
        vCounts = Split(vItem(1), "-")
        iTStart = CInt(vCounts(0))
        If UBound(vCounts) = 0 Then
            iTEnd = iTStart
        Else
            iTEnd = CInt(vCounts(1))
        End If
        
        If vItem(0) = "XD" Then
            iTEnd = iFiber + iTEnd - iTStart
            iTStart = iFiber
            
            vLine(i) = vItem(0) & ": " & iTStart & "-" & iTEnd
            If UBound(vItem) > 1 Then vLine(i) = vLine(i) & ": " & vItem(2)
            iFiber = iTEnd + 1
        Else
            iFiber = iFiber + iTEnd - iTStart + 1
        End If
    Next i
    
    If Not strSource = "" Then
        vItem = Split(vLine(0), ": ")
                
        If UBound(vItem) < 2 Then
            vLine(0) = vLine(0) & ": " & strSource
        Else
            If vItem(2) = "" Then vLine(0) = vItem(0) & ": " & vItem(1) & ": " & strSource
        End If
    End If
    
    strResult = vLine(0)
    If UBound(vLine) > 0 Then
        For i = 1 To UBound(vLine)
            If Not strSource = "" Then
                vItem = Split(vLine(i), ": ")
                
                If UBound(vItem) < 2 Then
                    vLine(i) = vLine(i) & ": " & strSource
                Else
                    If vItem(2) = "" Then vLine(i) = vItem(0) & ": " & vItem(1) & ": " & strSource
                End If
            End If
            
            strResult = strResult & vbCr & vLine(i)
        Next i
    End If
    
    tbResult.Value = UCase(strResult)
    Call ConsolidateCounts
End Sub

Private Sub cbUpdateBlock_Click()
    If tbCable.Value = "" Then Exit Sub
    If tbResult.Value = "" Then Exit Sub
    
    Dim vLine, vItem, vCounts, vTemp As Variant
    Dim vAttList As Variant
    Dim strLine, strPosition As String
    
    vAttList = objBlock.GetAttributes
    vTemp = Split(tbCable.Value, ": ")
    If UBound(vTemp) = 0 Then
        strPosition = ""
    Else
        strPosition = vTemp(0)
    End If
    
    strLine = Replace(tbResult.Value, vbCr, " + ")
    strLine = Replace(strLine, vbLf, "")
    
    Select Case objBlock.Name
        Case "sPole"
            strLine = tbCable.Value & " / " & strLine
            
            vTemp = Split(vAttList(25).TextString, vbCr)
            For i = 0 To UBound(vTemp)
                vLine = Split(vTemp(i), ": ")
                If vLine(0) = strPosition Then
                    vTemp(i) = strLine
                End If
            Next i
            
            strLine = vTemp(0)
            If UBound(vTemp) > 0 Then
                For i = 1 To UBound(vTemp)
                    strLine = strLine & vbCr & vTemp(i)
                Next i
            End If
            
            vAttList(25).TextString = strLine
        Case "sPed", "sHH", "sFP", "sMH", "sPanel"
            strLine = tbCable.Value & " / " & strLine
            
            vTemp = Split(vAttList(5).TextString, vbCr)
            For i = 0 To UBound(vTemp)
                vLine = Split(vTemp(i), ": ")
                If vLine(0) = strPosition Then
                    vTemp(i) = strLine
                End If
            Next i
            
            strLine = vTemp(0)
            If UBound(vTemp) > 0 Then
                For i = 1 To UBound(vTemp)
                    strLine = strLine & vbCr & vTemp(i)
                Next i
            End If
            
            vAttList(5).TextString = strLine
        Case "Callout"
            vAttList(1).TextString = tbCable.Value
            vAttList(2).TextString = Replace(strLine, " + ", "\P")
        Case "CableCounts"
            vAttList(1).TextString = tbCable.Value
            vAttList(0).TextString = Replace(strLine, " + ", "\P")
    End Select
    
    objBlock.Update
End Sub

Private Sub CommandButton1_Click()
    If lbRange.ListCount < 1 Then Exit Sub
    If lbCounts.ListCount < 1 Then Exit Sub
    
    Dim vLine As Variant
    Dim strResult, strName As String
    Dim strTemp, strLine As String
    Dim iFiber, iDiff As Integer
    Dim iFTest, iCTest As Integer
    Dim iRStart, iREnd As Integer
    Dim iCStart, iCEnd As Integer
    Dim iType, iLen As Integer
    Dim bFound As Boolean
    'Dim lLen As Long
    
    strResult = ""
    iFiber = 1
    
    For i = 0 To lbRange.ListCount - 1
        vLine = Split(lbRange.List(i, 0), "-")
        iRStart = CInt(vLine(0))
        iREnd = CInt(vLine(1))
        strName = lbRange.List(i, 1)
        
        iType = 0
        If Left(strName, 1) = "*" Then iType = iType + 1
        If Right(strName, 1) = "*" Then iType = iType + 2
        strName = Replace(strName, "*", "")
        
        For j = 0 To lbCounts.ListCount - 1
            strLine = lbCounts.List(j, 1)
            If strLine = "XD" Then GoTo Next_Count_Line
            
            bFound = False
            Select Case iType
                Case Is = 0
                    If strLine = strName Then bFound = True
                Case Is = 1
                    iLen = Len(strName)
                    'lLen = Len(strName)
                    If Right(strLine, iLen) = strName Then bFound = True
                Case Is = 2
                    iLen = Len(strName)
                    'lLen = Len(strName)
                    If Left(strLine, iLen) = strName Then bFound = True
                Case Is = 3
                    If strName = "" Then
                        bFound = True
                    Else
                        If InStr(strLine, strName) > 0 Then bFound = True
                    End If
            End Select
            If bFound = False Then GoTo Next_Count_Line
            
            vLine = Split(lbCounts.List(j, 0), "-")
            iCStart = CInt(vLine(0))
            iCEnd = CInt(vLine(1))
            iDiff = iCEnd - iCStart
            
            Select Case iREnd - iRStart
                Case Is = iDiff
                    
            End Select
            
            
Next_Count_Line:
        Next j
    Next i
End Sub

Private Sub lbList_KeyDown(ByVal KeyCode As MSForms.ReturnInteger, ByVal Shift As Integer)
    Dim strAtt(1) As String
    Dim iIndex As Integer
    
    Select Case KeyCode
        'Case vbKeyReturn
            'iListIndex = lbList.ListIndex
    
            'tbEndFibers.Value = lbList.List(iListIndex, 0)
            'tbSource.Value = lbList.List(iListIndex, 1)
    
            'cbAddToList.Caption = "Update"
        Case vbKeyUp
            iIndex = lbList.ListIndex
            If iIndex < 1 Then Exit Sub
            
            strAtt(0) = lbList.List(iIndex, 0)
            strAtt(1) = lbList.List(iIndex, 1)
            
            lbList.List(iIndex, 0) = lbList.List(iIndex - 1, 0)
            lbList.List(iIndex, 1) = lbList.List(iIndex - 1, 1)
            
            lbList.List(iIndex - 1, 0) = strAtt(0)
            lbList.List(iIndex - 1, 1) = strAtt(1)
        Case vbKeyDown
            iIndex = lbList.ListIndex
            If iIndex > lbList.ListCount - 2 Then Exit Sub
            
            strAtt(0) = lbList.List(iIndex, 0)
            strAtt(1) = lbList.List(iIndex, 1)
            
            lbList.List(iIndex, 0) = lbList.List(iIndex + 1, 0)
            lbList.List(iIndex, 1) = lbList.List(iIndex + 1, 1)
            
            lbList.List(iIndex + 1, 0) = strAtt(0)
            lbList.List(iIndex + 1, 1) = strAtt(1)
        Case vbKeyDelete
            lbList.RemoveItem lbList.ListIndex
    End Select
End Sub

Private Sub lbRange_DblClick(ByVal Cancel As MSForms.ReturnBoolean)
    iListIndex = lbRange.ListIndex
    
    tbRFibers.Value = lbRange.List(iListIndex, 0)
    tbRName.Value = lbRange.List(iListIndex, 1)
    tbRCounts.Value = lbRange.List(iListIndex, 2)
    
    cbAddRange.Caption = "Update"
End Sub

Private Sub lbRange_KeyDown(ByVal KeyCode As MSForms.ReturnInteger, ByVal Shift As Integer)
    Dim strAtt(2) As String
    Dim iIndex As Integer
    
    Select Case KeyCode
        Case vbKeyReturn
            iListIndex = lbRange.ListIndex
    
            tbRFibers.Value = lbRange.List(iListIndex, 0)
            tbRName.Value = lbRange.List(iListIndex, 1)
            tbRCounts.Value = lbRange.List(iListIndex, 2)
    
            cbAddRange.Caption = "Update"
        Case vbKeyUp
            iIndex = lbRange.ListIndex
            If iIndex < 1 Then Exit Sub
            
            strAtt(0) = lbRange.List(iIndex, 0)
            strAtt(1) = lbRange.List(iIndex, 1)
            strAtt(2) = lbRange.List(iIndex, 2)
            
            lbRange.List(iIndex, 0) = lbRange.List(iIndex - 1, 0)
            lbRange.List(iIndex, 1) = lbRange.List(iIndex - 1, 1)
            lbRange.List(iIndex, 2) = lbRange.List(iIndex - 1, 2)
            
            lbRange.List(iIndex - 1, 0) = strAtt(0)
            lbRange.List(iIndex - 1, 1) = strAtt(1)
            lbRange.List(iIndex - 1, 2) = strAtt(2)
        Case vbKeyDown
            iIndex = lbRange.ListIndex
            If iIndex > lbRange.ListCount - 2 Then Exit Sub
            
            strAtt(0) = lbRange.List(iIndex, 0)
            strAtt(1) = lbRange.List(iIndex, 1)
            strAtt(2) = lbRange.List(iIndex, 2)
            
            lbRange.List(iIndex, 0) = lbRange.List(iIndex + 1, 0)
            lbRange.List(iIndex, 1) = lbRange.List(iIndex + 1, 1)
            lbRange.List(iIndex, 2) = lbRange.List(iIndex + 1, 2)
            
            lbRange.List(iIndex + 1, 0) = strAtt(0)
            lbRange.List(iIndex + 1, 1) = strAtt(1)
            lbRange.List(iIndex + 1, 2) = strAtt(2)
    End Select
End Sub

Private Sub tbRCounts_KeyDown(ByVal KeyCode As MSForms.ReturnInteger, ByVal Shift As Integer)
    Select Case KeyCode
        Case vbKeySubtract
            If tbRCounts.Value = "*-" Then
                tbRCounts.Value = "*-*"
                cbAddRange.SetFocus
                
                Exit Sub
            End If
            
            Dim vFibers, vCounts As Variant
            Dim iFiber, iCount As Integer
            
            vFibers = Split(tbRFibers.Value, "-")
            iFiber = CInt(vFibers(0))
            While iFiber > 12
                iFiber = iFiber - 12
            Wend
            
            vCounts = Split(tbRCounts.Value, "-")
            iCount = CInt(vCounts(0))
            While iCount > 12
                iCount = iCount - 12
            Wend
            
            If Not iFiber = iCount Then
                MsgBox "Off Color"
                Exit Sub
            End If
            
            iCount = CInt(vCounts(0)) + CInt(vFibers(1)) - CInt(vFibers(0))
            tbRCounts.Value = tbRCounts.Value & "-" & iCount
            
            cbAddRange.SetFocus
    End Select
End Sub

Private Sub tbRFibers_Exit(ByVal Cancel As MSForms.ReturnBoolean)
    If tbRFibers.Value = "" Then Exit Sub
    
    If InStr(tbRFibers.Value, "-") < 1 Then tbRFibers.Value = tbRFibers.Value & "-" & tbRFibers.Value
End Sub

Private Sub UserForm_Initialize()
    lbCounts.ColumnCount = 4
    lbCounts.ColumnWidths = "48;132;48;126"
    
    lbRange.ColumnCount = 3
    lbRange.ColumnWidths = "42;96;54"

    lbList.ColumnCount = 2
    lbList.ColumnWidths = "72;72"
    
    cbCableSize.AddItem "12"
    cbCableSize.AddItem "24"
    cbCableSize.AddItem "48"
    cbCableSize.AddItem "72"
    cbCableSize.AddItem "96"
    cbCableSize.AddItem "144"
    cbCableSize.AddItem "216"
    cbCableSize.AddItem "288"
    cbCableSize.AddItem "360"
    cbCableSize.AddItem "432"
    cbCableSize.AddItem "576"
    cbCableSize.AddItem "876"
    
    cbEndFiber.AddItem "12"
    cbEndFiber.AddItem "24"
    cbEndFiber.AddItem "48"
    cbEndFiber.AddItem "72"
    cbEndFiber.AddItem "96"
    cbEndFiber.AddItem "144"
    cbEndFiber.AddItem "216"
    cbEndFiber.AddItem "288"
    cbEndFiber.AddItem "360"
    cbEndFiber.AddItem "432"
    cbEndFiber.AddItem "576"
    cbEndFiber.AddItem "876"
    
    tbRName.ControlTipText = "* is a wildcard.  Ex: F1000-* will match anything that starts with F1000-"
End Sub

Private Sub ConsolidateCounts()
    Dim vLine, vItem, vCounts, vTemp As Variant
    Dim strLine, strPrevious, strSource As String
    Dim iEnd, iStart As Integer
    Dim iAStart, iAEnd As Integer
    
    strLine = Replace(tbResult.Value, vbLf, "")
    vLine = Split(strLine, vbCr)
    
    If UBound(vLine) = 0 Then Exit Sub
    
    vItem = Split(vLine(UBound(vLine)), ": ")
    strPrevious = vItem(0)
    
    vCounts = Split(vItem(1), "-")
    iStart = CInt(vCounts(0))
    iEnd = CInt(vCounts(UBound(vCounts)))
    
    If UBound(vItem) > 1 Then
        strSource = vItem(2)
    Else
        strSource = ""
    End If
    
    For i = UBound(vLine) - 1 To 0 Step -1
        vItem = Split(vLine(i), ": ")
        If Not vItem(0) = strPrevious Then GoTo Next_line
        
        If UBound(vItem) > 1 Then
            If Not vItem(2) = strSource Then GoTo Next_line
        End If
        
        vCounts = Split(vItem(1), "-")
        iAStart = CInt(vCounts(0))
        iAEnd = CInt(vCounts(UBound(vCounts)))
        
        If iStart = iAEnd + 1 Then
            iAEnd = iEnd
            vLine(i) = vItem(0) & ": " & iAStart & "-" & iAEnd
            If UBound(vItem) > 1 Then vLine(i) = vLine(i) & ": " & vItem(2)
            
            vLine(i + 1) = ""
        End If
        
Next_line:
        strPrevious = vItem(0)
        iStart = iAStart
        iEnd = iAEnd
        If UBound(vItem) > 1 Then strSource = vItem(2)
    Next i
    
    strLine = vLine(0)
    For i = 1 To UBound(vLine)
        If Not vLine(i) = "" Then strLine = strLine & vbCr & vLine(i)
    Next i
    
    tbResult.Value = strLine
End Sub

Attribute VB_Name = "RenumberPoles"
Attribute VB_Base = "0{25914C9A-E775-4FD7-81CE-84C8C4AC0EC0}{ED64EBD8-AE51-4AE8-B055-5DBA25FC16D9}"
Attribute VB_GlobalNameSpace = False
Attribute VB_Creatable = False
Attribute VB_PredeclaredId = True
Attribute VB_Exposed = False
Attribute VB_TemplateDerived = False
Attribute VB_Customizable = False

Private Sub cbBlocks_Click()
    Dim objSS As AcadSelectionSet
    Dim objEntity As AcadEntity
    Dim objBlock As AcadBlockReference
    Dim vAttList, vList As Variant
    Dim str1, strList As String
    Dim strNumber As String
    
    Me.Hide
    strNumber = tbRoute.Value & tbPole.Value
    'strList = ""
    
  On Error Resume Next
    Set objSS = ThisDrawing.SelectionSets.Add("objSS")
    If Not Err = 0 Then
        Set objSS = ThisDrawing.SelectionSets.Item("objSS")
        Err = 0
    End If
    
    objSS.SelectOnScreen
    
    For Each objEntity In objSS
        If TypeOf objEntity Is AcadBlockReference Then
            Set objBlock = objEntity
            vAttList = objBlock.GetAttributes
            
            Select Case objBlock.Name
                Case "iPole", "sPole", "sPed", "sHH", "pole_attach", "pole_attach_title", "pole_unit"
                    vAttList(0).TextString = strNumber
                Case "pole_info"
                    vAttList(0).TextString = strNumber
                    
                    If vAttList(1).TextString = "0.0" Then
                        vAttList(2).TextString = strNumber
                    End If
            End Select
            
            objBlock.Update
        End If
    Next objEntity
    
    tbPole.Value = CInt(tbPole.Value) + 1
    
    objSS.Clear
    objSS.Delete
    Me.show
End Sub

Private Sub cbQuit_Click()
    Me.Hide
End Sub

Private Sub cbRenumPole_Click()
    Dim entPole As AcadObject
    Dim entObj As AcadEntity
    Dim obrPole As AcadBlockReference
    Dim vList As Variant
    Dim str1 As String
    Dim iNum As Integer
    Dim dN, dE As Double
    Dim vLL As Variant
    Dim iPlus As Integer
    Dim iChr As Integer
    
    
    Me.Hide
    iPlus = CInt(tbIncrement.Value)
    iNum = CInt(tbPole.Value) - iPlus
    iChr = 65
    
  On Error Resume Next
    While Err = 0
        ThisDrawing.Utility.GetEntity entPole, basePnt, "Select Pole: "
        If Not Err = 0 Then GoTo Exit_Sub
        If TypeOf entPole Is AcadBlockReference Then
            Set obrPole = entPole
        Else
            tbPole.Value = iNum
            Me.show
            Exit Sub
        End If
        
        'MsgBox obrPole.Name
        
        Select Case obrPole.Name
            Case "sPole"
                iNum = iNum + iPlus
                iChr = 65
                
                vList = obrPole.GetAttributes
                vList(0).TextString = tbRoute.Value & iNum
        
                If cbLL.Value = True Then
                    If vList(7).TextString = "" Then
                        vLL = TN83FtoLL(CDbl(obrPole.InsertionPoint(0)), CDbl(obrPole.InsertionPoint(1)))
                        vList(7).TextString = vLL(0) & "," & vLL(1)
                    End If
                End If
            Case "sPed", "sHH", "sPanel", "sMH"
                iNum = iNum + iPlus
                iChr = 65
                
                vList = obrPole.GetAttributes
                vList(0).TextString = tbRoute.Value & iNum
        
                If cbLL.Value = True Then
                    If vList(3).TextString = "" Then
                        vLL = TN83FtoLL(CDbl(obrPole.InsertionPoint(0)), CDbl(obrPole.InsertionPoint(1)))
                        vList(3).TextString = vLL(0) & "," & vLL(1)
                    End If
                End If
            Case "sFP"
                vList = obrPole.GetAttributes
                vList(0).TextString = tbRoute.Value & iNum & Chr(iChr)
                vList(1).TextString = iNum & Chr(iChr)
                iChr = iChr + 1
        
                If cbLL.Value = True Then
                    If vList(3).TextString = "" Then
                        vLL = TN83FtoLL(CDbl(obrPole.InsertionPoint(0)), CDbl(obrPole.InsertionPoint(1)))
                        vList(3).TextString = vLL(0) & "," & vLL(1)
                    End If
                End If
        End Select
        
        obrPole.Update
    Wend
Exit_Sub:
    tbPole.Value = iNum + iPlus
    Me.show
End Sub

Private Sub Label1_Click()
    Dim entPole As AcadObject
    Dim entObj As AcadEntity
    Dim obrPole As AcadBlockReference
    Dim vList As Variant
    Dim str1 As String
    Dim iNum As Integer
    
    Me.Hide
    
  On Error Resume Next
    ThisDrawing.Utility.GetEntity entPole, basePnt, "Select Pole: "
    If TypeOf entPole Is AcadBlockReference Then
        Set obrPole = entPole
    Else
        Me.show
        Exit Sub
    End If
        
    vList = obrPole.GetAttributes
    tbRoute.Value = vList(0).TextString
    tbPole.Value = "1"
    
    Me.show
End Sub

Private Function TN83FtoLL(dNorth As Double, dEast As Double)
    Dim dLat, dLong, dDLat As Double
    Dim dDiffE, dEast0 As Double
    Dim dDiffN, dNorth0 As Double
    Dim dR, dCAR, dCA, dU, dK As Double
    Dim LL(2) As Double
    
    dEast = dEast * 0.3048006096
    dNorth = dNorth * 0.3048006096
    
    dDiffE = dEast - 600000
    dDiffN = dNorth - 166504.1691
    
    dR = 8842127.1422 - dDiffN
    dCAR = Atn(dDiffE / dR)
    dCA = dCAR * 180 / 3.14159265359
    dLong = -86 + dCA / 0.585439726459
    
    dU = dDiffN - dDiffE * Tan(dCAR / 2)
    dDLat = dU * (0.00000901305249 + dU * (-6.77268E-15 + dU * (-3.72351E-20 + dU * -9.2828E-28)))
    dLat = 35.8340607459 + dDLat
    
    dK = 0.999948401424 + (1.23188E-14 * dU * dU) + (4.54E-22 * dU * dU * dU)
    
    LL(0) = dLat
    LL(1) = dLong
    LL(2) = dK
    
    TN83FtoLL = LL
End Function

Attribute VB_Name = "ReplaceCounts"
Attribute VB_Base = "0{B631BDFF-91DE-41A2-82AB-0FF35A096698}{306DA330-1CA3-4778-91F7-6A7C24C423CD}"
Attribute VB_GlobalNameSpace = False
Attribute VB_Creatable = False
Attribute VB_PredeclaredId = True
Attribute VB_Exposed = False
Attribute VB_TemplateDerived = False
Attribute VB_Customizable = False
Private Sub cbMove_Click()
    If tbMName.Value = "" Then Exit Sub
    If tbMFC.Value = "" Then Exit Sub
    If tbMTC.Value = "" Then Exit Sub
    If cbMSize.Value = "" Then Exit Sub
    If tbMFF.Value = "" Then Exit Sub
    If tbMTF.Value = "" Then Exit Sub
    
    '--------------------------------------------
    
    Dim strSize, strName As String
    Dim iFC, iTC As Integer
    Dim iFF, iTF As Integer
    
    strSize = "(" & cbMSize.Value & ")"
    strName = tbMName.Value
    
    iFC = CInt(tbMFC.Value)
    iTC = CInt(tbMTC.Value)
    iFF = CInt(tbMFF.Value)
    iTF = CInt(tbMTF.Value)
    
    '--------------------------------------------
    
    Dim vDwgLL, vDwgUR As Variant
    Dim filterType, filterValue As Variant
    Dim grpCode(0) As Integer
    Dim grpValue(0) As Variant
    Dim objSS As AcadSelectionSet
    Dim objBlock As AcadBlockReference
    Dim vAttList As Variant
    Dim strLine, strResult As String
    Dim vLine, vItem, vCable As Variant
    
    Me.Hide
    
    vDwgLL = ThisDrawing.Utility.GetPoint(, "Get DWG LL Corner: ")
    vDwgUR = ThisDrawing.Utility.GetCorner(vDwgLL, vbCr & "Get DWG UR Corner: ")
    
    grpCode(0) = 2
    grpValue(0) = "sPole"
    filterType = grpCode
    filterValue = grpValue
    
    Set objSS = ThisDrawing.SelectionSets.Add("objSS")
    objSS.Select acSelectionSetWindow, vDwgLL, vDwgUR, filterType, filterValue
    If objSS.count < 1 Then GoTo Exit_Sub
    
    'MsgBox objSS.count & "  CableCounts found."
    
    For Each objBlock In objSS
        vAttList = objBlock.GetAttributes
        
        strLine = vAttList(25).TextString
        If strLine = "" Then GoTo Next_objBlock
        If InStr(strLine, strSize) < 1 Then GoTo Next_objBlock
        If InStr(strLine, strName) < 1 Then GoTo Next_objBlock
        
        vLine = Split(strLine, vbCr)
        For i = 0 To UBound(vLine)
            If InStr(vLine(i), strName) > 0 Then
                vItem = Split(vLine(i), " / ")
                strResult = MoveCounts(vItem(1))
                vLine(i) = vItem(0) & " / " & strResult
            End If
        Next i
        
        strResult = vLine(0)
        If UBound(vLine) > 0 Then
            For i = 1 To UBound(vLine)
                strResult = strResult & vbCr & vLine(i)
            Next i
        End If
        
        vAttList(25).TextString = strResult
        
        objBlock.Update
Next_objBlock:
    Next objBlock
    
Exit_Sub:
    objSS.Clear
    objSS.Delete
    
    Me.show
End Sub

Private Sub cbQuit_Click()
    Me.Hide
End Sub

Private Sub cbReplace_Click()
    Select Case cbOptions.Value
        Case "Single"
            Call ReplaceSingle
        Case "All sPole"
            Call ReplaceAllsPole
        Case "All Callouts"
            Call ReplaceAllCallouts
    End Select
End Sub

Private Sub Label7_DblClick(ByVal Cancel As MSForms.ReturnBoolean)
    Call ReplaceAllCallouts
End Sub

Private Sub tbMFF_Exit(ByVal Cancel As MSForms.ReturnBoolean)
    If tbMTC.Value = "" Then Exit Sub
    If tbMFC.Value = "" Then Exit Sub
    If tbMFF.Value = "" Then Exit Sub
    
    Dim iFC, iTC As Integer
    Dim iFF, iTF As Integer
    Dim iDiff, iTest As Integer
    Dim dTest, dResult As Double
    
    iFC = CInt(tbMFC.Value)
    iTC = CInt(tbMTC.Value)
    iDiff = iTC - iFC
    iFF = CInt(tbMFF.Value)
    iTF = iFF + iDiff
    
    iTest = Abs(iFF - iFC)
    dTest = (iTest / 12)
    dResult = dTest - Int(dTest)
    
    If Not dResult = 0# Then
        MsgBox "Off-Color"
        Exit Sub
    End If
    
    tbMTF.Value = iTF
End Sub

Private Sub tbMName_Change()
    If tbMName.Value = "" Then Exit Sub
    
    tbMName.Value = UCase(tbMName.Value)
End Sub

Private Sub tbMTC_Exit(ByVal Cancel As MSForms.ReturnBoolean)
    If tbMFC.Value = "" Then Exit Sub
    
    If tbMFC.Value = "" Then tbMTC.Value = tbMFC.Value
End Sub

Private Sub UserForm_Initialize()
    cbOptions.AddItem "Single"
    cbOptions.AddItem "All sPole"
    cbOptions.AddItem "All Callouts"
    cbOptions.Value = "Single"
    
    cbMSize.AddItem ""
    cbMSize.AddItem "12"
    cbMSize.AddItem "24"
    cbMSize.AddItem "48"
    cbMSize.AddItem "72"
    cbMSize.AddItem "96"
    cbMSize.AddItem "144"
    cbMSize.AddItem "216"
    cbMSize.AddItem "288"
    cbMSize.AddItem "360"
    cbMSize.AddItem "432"
    cbMSize.AddItem "576"
    
    tbFName.SetFocus
End Sub

Private Sub ReplaceSingle()
    If tbFName.Value = "" Then Exit Sub
    If tbRName.Value = "" Then Exit Sub
    
    If tbFFrom.Value = "" Then Exit Sub
    If tbRFrom.Value = "" Then Exit Sub
    
    If tbFTo.Value = "" Then tbFTo.Value = tbFFrom.Value
    If tbRTo.Value = "" Then tbRTo.Value = tbRFrom.Value
    
    Dim objEntity As AcadEntity
    Dim objBlock As AcadBlockReference
    Dim vReturnPnt As Variant
    Dim vAttList As Variant
    Dim vLine, vItem, vCount As Variant
    Dim vTemp As Variant
    Dim strFind, strReplace As String
    Dim strLine, strInsert As String
    Dim iFFrom, iFTo, iRFrom, iRTo As Integer
    Dim iFFFiber, iRFFiber As Integer
    Dim iFind, iReplace As Integer
    Dim iCFrom, iCTo As Integer
    Dim iFTemp, iTTemp As Integer
    
    On Error Resume Next
    
    strFind = UCase(tbFName.Value)
    strReplace = UCase(tbRName.Value)
    
    iFFrom = CInt(tbFFrom.Value)
    If Not Err = 0 Then
        MsgBox "Find From is not an integer"
        Exit Sub
    End If
    
    iFTo = CInt(tbFTo.Value)
    If Not Err = 0 Then
        MsgBox "Find To is not an integer"
        Exit Sub
    End If
    
    iFind = iFTo - iFFrom
    
    iRFrom = CInt(tbRFrom.Value)
    If Not Err = 0 Then
        MsgBox "Replace From is not an integer"
        Exit Sub
    End If
    
    iRTo = CInt(tbRTo.Value)
    If Not Err = 0 Then
        MsgBox "Replace To is not an integer"
        Exit Sub
    End If
    
    iReplace = iRTo - iRFrom
    
    If Not iFind = iReplace Then
        strLine = "Number of Find counts (" & iFind & ") does not match the Replace counts (" & iReplace & ")"
        MsgBox strLine
        Exit Sub
    End If
    
    iFFFiber = iFFrom
    While iFFFiber > 12
        iFFFiber = iFFFiber - 12
    Wend
    
    iRFFiber = iRFrom
    While iRFFiber > 12
        iRFFiber = iRFFiber - 12
    Wend
    
    If Not iFFFiber = iRFFiber Then
        strLine = "Start Fiber for Find counts (" & iFFFiber & ") does not match the Replace counts (" & iRFFiber & ")"
        MsgBox strLine
        Exit Sub
    End If
    
    
    Me.Hide
    
Get_Entity:
    ThisDrawing.Utility.GetEntity objEntity, vReturnPnt, vbCr & "Select Callout or Pole: "
    If Not Err = 0 Then GoTo Exit_Sub
    
    If Not TypeOf objEntity Is AcadBlockReference Then GoTo Get_Entity
    Set objBlock = objEntity
    
    Select Case objBlock.Name
        Case "Callout"
            vAttList = objBlock.GetAttributes
            
            vLine = Split(UCase(vAttList(2).TextString), "\P")
            For i = 0 To UBound(vLine)
                vItem = Split(vLine(i), ": ")
                If vItem(0) = strFind Then
                    vCount = Split(vItem(1), "-")
                    iCFrom = CInt(vCount(0))
                    If UBound(vCount) = 0 Then
                        iCTo = CInt(vCount(0))
                    Else
                        iCTo = CInt(vCount(1))
                    End If
                    
                    Select Case iCFrom - iFFrom
                        Case Is < 0
                            If iCTo < iFTo Then GoTo Next_I1
                            
                            iTTemp = iFFrom - 1
                            iFTemp = iFTo + 1
                            strInsert = strFind & ": " & iCFrom
                            If Not iTTemp = iCFrom Then strInsert = strInsert & "-" & iTTemp
                            
                            strInsert = strInsert & "\P" & strReplace & ": " & iRFrom
                            If Not iRFrom = iRTo Then strInsert = strInsert & "-" & iRTo
                            
                            If Not iFTemp > iCTo Then
                                strInsert = strInsert & "\P" & strFind & ": " & iFTemp
                                If iCTo > iFTemp Then strInsert = strInsert & "-" & iCTo
                            End If
                            
                            vLine(i) = strInsert
                            
                            strLine = vLine(0)
                            If UBound(vLine) > 0 Then
                                For j = 1 To UBound(vLine)
                                    strLine = strLine & "\P" & vLine(j)
                                Next j
                            End If
                            
                            vAttList(2).TextString = strLine
                            objBlock.Update
                            
                            GoTo Get_Entity
                        Case Is = 0
                            If iCTo < iFTo Then GoTo Next_I1
                            
                            iFTemp = iFTo + 1
                            strInsert = strReplace & ": " & iRFrom
                            If Not iRFrom = iRTo Then strInsert = strInsert & "-" & iRTo
                            
                            If Not iFTemp > iCTo Then
                                strInsert = strInsert & "\P" & strFind & ": " & iFTemp
                                If iCTo > iFTemp Then strInsert = strInsert & "-" & iCTo
                            End If
                            
                            vLine(i) = strInsert
                            
                            strLine = vLine(0)
                            If UBound(vLine) > 0 Then
                                For j = 1 To UBound(vLine)
                                    strLine = strLine & "\P" & vLine(j)
                                Next j
                            End If
                            
                            vAttList(2).TextString = strLine
                            objBlock.Update
                            
                            GoTo Get_Entity
                        Case Is > 0
                            GoTo Next_I1
                    End Select
                End If
Next_I1:
            Next i
        Case "CableCounts"
            vAttList = objBlock.GetAttributes
            
            vLine = Split(UCase(vAttList(0).TextString), "\P")
            For i = 0 To UBound(vLine)
                vItem = Split(vLine(i), ": ")
                If vItem(0) = strFind Then
                    vCount = Split(vItem(1), "-")
                    iCFrom = CInt(vCount(0))
                    If UBound(vCount) = 0 Then
                        iCTo = CInt(vCount(0))
                    Else
                        iCTo = CInt(vCount(1))
                    End If
                    
                    Select Case iCFrom - iFFrom
                        Case Is < 0
                            If iCTo < iFTo Then GoTo Next_I
                            
                            iTTemp = iFFrom - 1
                            iFTemp = iFTo + 1
                            strInsert = strFind & ": " & iCFrom
                            If Not iTTemp = iCFrom Then strInsert = strInsert & "-" & iTTemp
                            
                            strInsert = strInsert & "\P" & strReplace & ": " & iRFrom
                            If Not iRFrom = iRTo Then strInsert = strInsert & "-" & iRTo
                            
                            If Not iFTemp > iCTo Then
                                strInsert = strInsert & "\P" & strFind & ": " & iFTemp
                                If iCTo > iFTemp Then strInsert = strInsert & "-" & iCTo
                            End If
                            
                            vLine(i) = strInsert
                            
                            strLine = vLine(0)
                            If UBound(vLine) > 0 Then
                                For j = 1 To UBound(vLine)
                                    strLine = strLine & "\P" & vLine(j)
                                Next j
                            End If
                            
                            vAttList(0).TextString = strLine
                            objBlock.Update
                            
                            GoTo Get_Entity
                        Case Is = 0
                            If iCTo < iFTo Then GoTo Next_I
                            
                            iFTemp = iFTo + 1
                            strInsert = strReplace & ": " & iRFrom
                            If Not iRFrom = iRTo Then strInsert = strInsert & "-" & iRTo
                            
                            If Not iFTemp > iCTo Then
                                strInsert = strInsert & "\P" & strFind & ": " & iFTemp
                                If iCTo > iFTemp Then strInsert = strInsert & "-" & iCTo
                            End If
                            
                            vLine(i) = strInsert
                            
                            strLine = vLine(0)
                            If UBound(vLine) > 0 Then
                                For j = 1 To UBound(vLine)
                                    strLine = strLine & "\P" & vLine(j)
                                Next j
                            End If
                            
                            vAttList(0).TextString = strLine
                            objBlock.Update
                            
                            GoTo Get_Entity
                        Case Is > 0
                            GoTo Next_I
                    End Select
                End If
Next_I:
            Next i
        Case "sPole"
            vAttList = objBlock.GetAttributes
            
            vLine = Split(UCase(vAttList(25).TextString), " / ")
            vTemp = Split(vLine(1), " + ")
            
            
            For i = 0 To UBound(vTemp)
                vItem = Split(vTemp(i), ": ")
                If vItem(0) = strFind Then
                    vCount = Split(vItem(1), "-")
                    iCFrom = CInt(vCount(0))
                    If UBound(vCount) = 0 Then
                        iCTo = CInt(vCount(0))
                    Else
                        iCTo = CInt(vCount(1))
                    End If
                    
                    Select Case iCFrom - iFFrom
                        Case Is < 0
                            If iCTo < iFTo Then GoTo Next_I1
                            
                            iTTemp = iFFrom - 1
                            iFTemp = iFTo + 1
                            strInsert = strFind & ": " & iCFrom
                            If Not iTTemp = iCFrom Then strInsert = strInsert & "-" & iTTemp
                            If UBound(vItem) > 1 Then strInsert = strInsert & ": " & vItem(2)
                            
                            strInsert = strInsert & " + " & strReplace & ": " & iRFrom
                            If Not iRFrom = iRTo Then strInsert = strInsert & "-" & iRTo
                            If UBound(vItem) > 1 Then strInsert = strInsert & ": " & vItem(2)
                            
                            If Not iFTemp > iCTo Then
                                strInsert = strInsert & " + " & strFind & ": " & iFTemp
                                If iCTo > iFTemp Then strInsert = strInsert & "-" & iCTo
                                If UBound(vItem) > 1 Then strInsert = strInsert & ": " & vItem(2)
                            End If
                            
                            vTemp(i) = strInsert
                            
                            strLine = vTemp(0)
                            If UBound(vTemp) > 0 Then
                                For j = 1 To UBound(vTemp)
                                    strLine = strLine & " + " & vTemp(j)
                                Next j
                            End If
                            
                            vAttList(25).TextString = vLine(0) & " / " & strLine
                            objBlock.Update
                            
                            GoTo Get_Entity
                        Case Is = 0
                            If iCTo < iFTo Then GoTo Next_I2
                            
                            iFTemp = iFTo + 1
                            strInsert = strReplace & ": " & iRFrom
                            If Not iRFrom = iRTo Then strInsert = strInsert & "-" & iRTo
                            If UBound(vItem) > 1 Then strInsert = strInsert & ": " & vItem(2)
                            
                            If Not iFTemp > iCTo Then
                                strInsert = strInsert & " + " & strFind & ": " & iFTemp
                                If iCTo > iFTemp Then strInsert = strInsert & "-" & iCTo
                                If UBound(vItem) > 1 Then strInsert = strInsert & ": " & vItem(2)
                            End If
                            
                            vTemp(i) = strInsert
                            
                            strLine = vTemp(0)
                            If UBound(vTemp) > 0 Then
                                For j = 1 To UBound(vTemp)
                                    strLine = strLine & " + " & vTemp(j)
                                Next j
                            End If
                            
                            vAttList(25).TextString = vLine(0) & " / " & strLine
                            objBlock.Update
                            
                            GoTo Get_Entity
                        Case Is > 0
                            GoTo Next_I2
                    End Select
                End If
Next_I2:
            Next i
        Case Else
    End Select
    
    GoTo Get_Entity
Exit_Sub:
    Me.show
End Sub

Private Sub ReplaceAllCallouts()
    If tbFName.Value = "" Then Exit Sub
    If tbRName.Value = "" Then Exit Sub
    
    If tbFFrom.Value = "" Then Exit Sub
    If tbRFrom.Value = "" Then Exit Sub
    
    If tbFTo.Value = "" Then tbFTo.Value = tbFFrom.Value
    If tbRTo.Value = "" Then tbRTo.Value = tbRFrom.Value
    
    Dim objEntity As AcadEntity
    Dim objBlock As AcadBlockReference
    Dim vReturnPnt As Variant
    Dim vAttList As Variant
    Dim vLine, vItem, vCount As Variant
    Dim vPole As Variant
    Dim strFind, strReplace As String
    Dim strLine, strInsert As String
    Dim iFFrom, iFTo, iRFrom, iRTo As Integer
    Dim iFFFiber, iRFFiber As Integer
    Dim iFind, iReplace As Integer
    Dim iCFrom, iCTo As Integer
    Dim iFTemp, iTTemp As Integer
    
    On Error Resume Next
    
    strFind = UCase(tbFName.Value)
    strReplace = UCase(tbRName.Value)
    
    iFFrom = CInt(tbFFrom.Value)
    If Not Err = 0 Then
        MsgBox "Find From is not an integer"
        Exit Sub
    End If
    
    iFTo = CInt(tbFTo.Value)
    If Not Err = 0 Then
        MsgBox "Find To is not an integer"
        Exit Sub
    End If
    
    iFind = iFTo - iFFrom
    
    iRFrom = CInt(tbRFrom.Value)
    If Not Err = 0 Then
        MsgBox "Replace From is not an integer"
        Exit Sub
    End If
    
    iRTo = CInt(tbRTo.Value)
    If Not Err = 0 Then
        MsgBox "Replace To is not an integer"
        Exit Sub
    End If
    
    iReplace = iRTo - iRFrom
    
    If Not iFind = iReplace Then
        strLine = "Number of Find counts (" & iFind & ") does not match the Replace counts (" & iReplace & ")"
        MsgBox strLine
        Exit Sub
    End If
    
    iFFFiber = iFFrom
    While iFFFiber > 12
        iFFFiber = iFFFiber - 12
    Wend
    
    iRFFiber = iRFrom
    While iRFFiber > 12
        iRFFiber = iRFFiber - 12
    Wend
    
    If Not iFFFiber = iRFFiber Then
        strLine = "Start Fiber for Find counts (" & iFFFiber & ") does not match the Replace counts (" & iRFFiber & ")"
        MsgBox strLine
        Exit Sub
    End If
    
    Dim vDwgLL, vDwgUR As Variant
    Dim filterType, filterValue As Variant
    Dim grpCode(0) As Integer
    Dim grpValue(0) As Variant
    Dim objSSDwg As AcadSelectionSet
    
    Me.Hide
    
    vDwgLL = ThisDrawing.Utility.GetPoint(, "Get DWG LL Corner: ")
    vDwgUR = ThisDrawing.Utility.GetCorner(vDwgLL, vbCr & "Get DWG UR Corner: ")
    
    grpCode(0) = 2
    grpValue(0) = "CableCounts"
    filterType = grpCode
    filterValue = grpValue
    
    Set objSSDwg = ThisDrawing.SelectionSets.Add("objSSDwg")
    objSSDwg.Select acSelectionSetWindow, vDwgLL, vDwgUR, filterType, filterValue
    If objSSDwg.count < 1 Then GoTo Exit_Sub
    
    MsgBox objSSDwg.count & "  CableCounts found."
    
    For Each objBlock In objSSDwg
        vAttList = objBlock.GetAttributes
            
        vLine = Split(UCase(vAttList(0).TextString), "\P")
        For i = 0 To UBound(vLine)
            vItem = Split(vLine(i), ": ")
            
            If vItem(0) = strFind Then
                vCount = Split(vItem(1), "-")
                iCFrom = CInt(vCount(0))
                If UBound(vCount) = 0 Then
                    iCTo = CInt(vCount(0))
                Else
                    iCTo = CInt(vCount(1))
                End If
                    
                Select Case iCFrom - iFFrom
                    Case Is < 0
                        If iCTo < iFTo Then GoTo Next_I
                            
                        iTTemp = iFFrom - 1
                        iFTemp = iFTo + 1
                        strInsert = strFind & ": " & iCFrom
                        If Not iTTemp = iCFrom Then strInsert = strInsert & "-" & iTTemp
                            
                        strInsert = strInsert & "\P" & strReplace & ": " & iRFrom
                        If Not iRFrom = iRTo Then strInsert = strInsert & "-" & iRTo
                            
                        If Not iFTemp > iCTo Then
                            strInsert = strInsert & "\P" & strFind & ": " & iFTemp
                            If iCTo > iFTemp Then strInsert = strInsert & "-" & iCTo
                        End If
                            
                        vLine(i) = strInsert
                            
                        strLine = vLine(0)
                        If UBound(vLine) > 0 Then
                            For j = 1 To UBound(vLine)
                                strLine = strLine & "\P" & vLine(j)
                            Next j
                        End If
                            
                        vAttList(0).TextString = strLine
                        objBlock.Update
                            
                        GoTo Next_objBlock
                    Case Is = 0
                        If iCTo < iFTo Then GoTo Next_I
                            
                        iFTemp = iFTo + 1
                        strInsert = strReplace & ": " & iRFrom
                        If Not iRFrom = iRTo Then strInsert = strInsert & "-" & iRTo
                            
                        If Not iFTemp > iCTo Then
                            strInsert = strInsert & "\P" & strFind & ": " & iFTemp
                            If iCTo > iFTemp Then strInsert = strInsert & "-" & iCTo
                        End If
                            
                        vLine(i) = strInsert
                            
                        strLine = vLine(0)
                        If UBound(vLine) > 0 Then
                            For j = 1 To UBound(vLine)
                                strLine = strLine & "\P" & vLine(j)
                            Next j
                        End If
                            
                        vAttList(0).TextString = strLine
                        objBlock.Update
                            
                        GoTo Next_objBlock
                    Case Is > 0
                        GoTo Next_I
                End Select
            End If
Next_I:
        Next i
Next_objBlock:
    Next objBlock
    
Exit_Sub:
    objSSDwg.Clear
    objSSDwg.Delete
    
    Me.show
End Sub

Private Sub ReplaceAllsPole()
    If tbFName.Value = "" Then Exit Sub
    If tbRName.Value = "" Then Exit Sub
    
    If tbFFrom.Value = "" Then Exit Sub
    If tbRFrom.Value = "" Then Exit Sub
    
    If tbFTo.Value = "" Then tbFTo.Value = tbFFrom.Value
    If tbRTo.Value = "" Then tbRTo.Value = tbRFrom.Value
    
    Dim objEntity As AcadEntity
    Dim objBlock As AcadBlockReference
    Dim vReturnPnt As Variant
    Dim vAttList As Variant
    Dim vLine, vItem, vCount As Variant
    Dim vPole As Variant
    Dim strFind, strReplace As String
    Dim strLine, strInsert As String
    Dim iFFrom, iFTo, iRFrom, iRTo As Integer
    Dim iFFFiber, iRFFiber As Integer
    Dim iFind, iReplace As Integer
    Dim iCFrom, iCTo As Integer
    Dim iFTemp, iTTemp As Integer
    
    On Error Resume Next
    
    strFind = UCase(tbFName.Value)
    strReplace = UCase(tbRName.Value)
    
    iFFrom = CInt(tbFFrom.Value)
    If Not Err = 0 Then
        MsgBox "Find From is not an integer"
        Exit Sub
    End If
    
    iFTo = CInt(tbFTo.Value)
    If Not Err = 0 Then
        MsgBox "Find To is not an integer"
        Exit Sub
    End If
    
    iFind = iFTo - iFFrom
    
    iRFrom = CInt(tbRFrom.Value)
    If Not Err = 0 Then
        MsgBox "Replace From is not an integer"
        Exit Sub
    End If
    
    iRTo = CInt(tbRTo.Value)
    If Not Err = 0 Then
        MsgBox "Replace To is not an integer"
        Exit Sub
    End If
    
    iReplace = iRTo - iRFrom
    
    If Not iFind = iReplace Then
        strLine = "Number of Find counts (" & iFind & ") does not match the Replace counts (" & iReplace & ")"
        MsgBox strLine
        Exit Sub
    End If
    
    iFFFiber = iFFrom
    While iFFFiber > 12
        iFFFiber = iFFFiber - 12
    Wend
    
    iRFFiber = iRFrom
    While iRFFiber > 12
        iRFFiber = iRFFiber - 12
    Wend
    
    If Not iFFFiber = iRFFiber Then
        strLine = "Start Fiber for Find counts (" & iFFFiber & ") does not match the Replace counts (" & iRFFiber & ")"
        MsgBox strLine
        Exit Sub
    End If
    
    Dim vDwgLL, vDwgUR As Variant
    Dim filterType, filterValue As Variant
    Dim grpCode(0) As Integer
    Dim grpValue(0) As Variant
    Dim objSSDwg As AcadSelectionSet
    
    Me.Hide
    
    vDwgLL = ThisDrawing.Utility.GetPoint(, "Get DWG LL Corner: ")
    vDwgUR = ThisDrawing.Utility.GetCorner(vDwgLL, vbCr & "Get DWG UR Corner: ")
    
    grpCode(0) = 2
    grpValue(0) = "sPole"
    filterType = grpCode
    filterValue = grpValue
    
    Set objSSDwg = ThisDrawing.SelectionSets.Add("objSSDwg")
    objSSDwg.Select acSelectionSetWindow, vDwgLL, vDwgUR, filterType, filterValue
    If objSSDwg.count < 1 Then GoTo Exit_Sub
    
    MsgBox objSSDwg.count & "  CableCounts found."
    
    For Each objBlock In objSSDwg
        vAttList = objBlock.GetAttributes
        
        vPole = Split(UCase(vAttList(25).TextString), " / ")
        vLine = Split(vPole(1), " + ")
        For i = 0 To UBound(vLine)
            vItem = Split(vLine(i), ": ")
            
            If vItem(0) = strFind Then
                strBack = vItem(2)
                vCount = Split(vItem(1), "-")
                iCFrom = CInt(vCount(0))
                If UBound(vCount) = 0 Then
                    iCTo = CInt(vCount(0))
                Else
                    iCTo = CInt(vCount(1))
                End If
                    
                Select Case iCFrom - iFFrom
                    Case Is < 0
                        If iCTo < iFTo Then GoTo Next_I
                            
                        iTTemp = iFFrom - 1
                        iFTemp = iFTo + 1
                        strInsert = strFind & ": " & iCFrom
                        If Not iTTemp = iCFrom Then strInsert = strInsert & "-" & iTTemp
                        strInsert = strInsert & ": " & strBack
                            
                        strInsert = strInsert & " + " & strReplace & ": " & iRFrom
                        If Not iRFrom = iRTo Then strInsert = strInsert & "-" & iRTo
                        strInsert = strInsert & ": " & strBack
                            
                        If Not iFTemp > iCTo Then
                            strInsert = strInsert & " + " & strFind & ": " & iFTemp
                            If iCTo > iFTemp Then strInsert = strInsert & "-" & iCTo
                            strInsert = strInsert & ": " & strBack
                        End If
                            
                        vLine(i) = strInsert
                            
                        strLine = vLine(0)
                        If UBound(vLine) > 0 Then
                            For j = 1 To UBound(vLine)
                                strLine = strLine & " + " & vLine(j)
                            Next j
                        End If
                            
                        vAttList(25).TextString = vPole(0) & " / " & strLine
                        objBlock.Update
                            
                        GoTo Next_objBlock
                    Case Is = 0
                        If iCTo < iFTo Then GoTo Next_I
                            
                        iFTemp = iFTo + 1
                        strInsert = strReplace & ": " & iRFrom
                        If Not iRFrom = iRTo Then strInsert = strInsert & "-" & iRTo
                        strInsert = strInsert & ": " & strBack
                            
                        If Not iFTemp > iCTo Then
                            strInsert = strInsert & " + " & strFind & ": " & iFTemp
                            If iCTo > iFTemp Then strInsert = strInsert & "-" & iCTo
                            strInsert = strInsert & ": " & strBack
                        End If
                            
                        vLine(i) = strInsert
                            
                        strLine = vLine(0)
                        If UBound(vLine) > 0 Then
                            For j = 1 To UBound(vLine)
                                strLine = strLine & " + " & vLine(j)
                            Next j
                        End If
                            
                        vAttList(25).TextString = vPole(0) & " / " & strLine
                        objBlock.Update
                            
                        GoTo Next_objBlock
                    Case Is > 0
                        GoTo Next_I
                End Select
            End If
Next_I:
        Next i
Next_objBlock:
    Next objBlock
    
Exit_Sub:
    objSSDwg.Clear
    objSSDwg.Delete
    
    Me.show
End Sub

Private Function MoveCounts(strLine As String)
    Dim vLine, vItem, vCounts As Variant
    Dim strResult, strTemp As String
    Dim strName As String
    Dim strPrevious As String
    Dim iFC, iTC As Integer
    Dim iFF, iTF As Integer
    Dim iCFC, iCTC As Integer
    Dim iCFF, iCTF As Integer
    Dim iFFiber, iTFiber, iTemp As Integer
    
    Dim iSize As Integer
    Dim iFiber, iStart, iEnd As Integer
    Dim strCable(12) As String
    Dim iCount(12) As Integer
    Dim strSource(12) As String
    
    iSize = CInt(cbMSize.Value)
    ReDim strCable(iSize) As String
    ReDim iCount(iSize) As Integer
    ReDim strSource(iSize) As String
    iFiber = 1
    
    strName = tbMName.Value
    strResult = ""
    
    iFC = CInt(tbMFC.Value)
    iTC = CInt(tbMTC.Value)
    iFF = CInt(tbMFF.Value)
    iTF = CInt(tbMTF.Value)
    
    vLine = Split(strLine, " + ")
    For i = 0 To UBound(vLine)
        vItem = Split(vLine(i), ": ")
        If vItem(0) = strName Then
            vCounts = Split(vlitem(1), "-")
            iCFC = CInt(vCounts(0))
            
            If UBound(vCounts) > 0 Then
                iCTC = CInt(vCounts(1))
            Else
                iCTC = iCFC
            End If
            
            If iCTC < iFC Then GoTo Next_I
            If iCFC > iTC Then GoTo Next_I
            
            If iCFC < iFC Then
                iCFC = iFC
                iCFF = iFF
            Else
                iCFF = iFF + (iCFC - iFC)
            End If
            
            If iCTC > iTC Then
                iCTC = iTC
                iCTF = iTF
            Else
                iCTF = iTF + (iCTC - iTC)
            End If
            
            If UBound(vItem) > 1 Then
                strSource(0) = vItem(2)
            Else
                strSource(0) = ""
            End If
Next_I:
    Next i
    
    For i = 0 To UBound(vLine)
        vItem = Split(vLine(i), ": ")
        vCounts = Split(vlitem(1), "-")
        
        iStart = CInt(vCounts(0))
        If UBound(vCounts) = 0 Then
            iEnd = iStart
        Else
            iEnd = CInt(vCounts(1))
        End If
        
        For j = iStart To iEnd
            If vItem(0) = strName Then
                If j > iFF - 1 And j < iTF + 1 Then
                    strCable(iFiber) = "XD"
                    
                    If UBound(vItem) < 2 Then
                        strSource(iFiber) = ""
                    Else
                        strSource(iFiber) = vItem(2)
                    End If
                    
                    iCount(iFiber) = iFiber
                    
                    GoTo Omit_Fiber
                End If
            End If
            
            strCable(iFiber) = vItem(0)
            If UBound(vItem) < 2 Then
                strSource(iFiber) = ""
            Else
                strSource(iFiber) = vItem(2)
            End If
            
            iCount(iFiber) = j
            
Omit_Fiber:
            
            iFiber = iFiber + 1
        Next j
    Next i
    
    For i = iCFF To iCTF
        strCable(i) = strName
        strSource(i) = strSource(0)
        iCount(i) = iCFC + i - iCFF
    Next i
    
    strResult = ""
    
    strPrevious = strCable(1)
    iStart = iCount(1)
    iEnd = iStart
    
    For i = 2 To UBound(strCable)
        If strCable(i) = strPrevious Then
            iEnd = iCount(i)
        Else
            strLine = strPrevious & ": " & iStart
            
            If Not iEnd = iStart Then strLine = strLine & "-" & iEnd
            If Not strSource(i - 1) = "" Then strLine = strLine & ": " & strSource(i)
            
            If strResult = "" Then
                strResult = strLine
            Else
                strResult = strResult & " + " & strLine
            End If
            
            strPrevious = strCable(i)
            iStart = iCount(i)
            iEnd = iStart
        End If
    Next i
    
    MoveCounts = strResult
End Function

Attribute VB_Name = "ReplaceF1"
Attribute VB_Base = "0{4A8911A5-2DAE-444E-91FB-780D8166A9B5}{2BA88A92-BEEA-4663-BAE3-F413DD00C1EB}"
Attribute VB_GlobalNameSpace = False
Attribute VB_Creatable = False
Attribute VB_PredeclaredId = True
Attribute VB_Exposed = False
Attribute VB_TemplateDerived = False
Attribute VB_Customizable = False
Dim vPnt1, vPnt2 As Variant

Private Sub cbClearData_Click()
    Dim result As Integer
    
    result = MsgBox("Are you sure you want to Clear the Cables and Splices from the Checked Boxes?", vbYesNo, "Clear Data!!!")
    If result = vbNo Then
        Exit Sub
    End If
    
    On Error Resume Next
    Me.Hide
    
    vPnt1 = ThisDrawing.Utility.GetPoint(, vbCr & "Get a corner:")
    vPnt2 = ThisDrawing.Utility.GetCorner(vPnt1, vbCr & "Get opposite corner:")
    
    If cbPoles.Value = True Then Call ClearBlocks("sPole")
    If cbPoles.Value = True Then Call ClearBlocks("sPed")
    If cbPoles.Value = True Then Call ClearBlocks("sHH")
    If cbPoles.Value = True Then Call ClearBlocks("Customer")
    
    Me.show
End Sub

Private Sub cbQuit_Click()
    Me.Hide
End Sub

Private Sub ClearBlocks(strName As String)
    Dim objSS As AcadSelectionSet
    Dim filterType, filterValue As Variant
    Dim grpCode(0) As Integer
    Dim grpValue(0) As Variant
    Dim objEntity As AcadEntity
    Dim objBlock As AcadBlockReference
    Dim vAttList As Variant
    
    grpCode(0) = 2
    grpValue(0) = strName
    filterType = grpCode
    filterValue = grpValue
    
    On Error Resume Next
    
    Set objSS = ThisDrawing.SelectionSets.Add("objSS")
    If Not Err = 0 Then
        Set objSS = ThisDrawing.SelectionSets.Item("objSS")
        Err = 0
    End If
    
    objSS.Select acSelectionSetWindow, vPnt1, vPnt2, filterType, filterValue
    If objSS.count < 1 Then GoTo Exit_Sub
    
    For Each objBlock In objSS
        vAttList = objBlock.GetAttributes
        
        Select Case objBlock.Name
            Case "sPole"
                vAttList(25).TextString = ""
                vAttList(26).TextString = ""
            Case "sPed", "sHH"
                vAttList(5).TextString = ""
                vAttList(6).TextString = ""
            Case "Customer"
                vAttList(4).TextString = ""
        End Select
        
        objBlock.Update
    Next objBlock
    
Exit_Sub:
    objSS.Clear
    objSS.Delete
End Sub

Attribute VB_Name = "ReplaceUnits"
Attribute VB_Base = "0{66FD499C-3EA2-4C75-8F67-3AF18901326C}{ED7A00B3-E4E3-4E59-8B82-EE3FCB130E82}"
Attribute VB_GlobalNameSpace = False
Attribute VB_Creatable = False
Attribute VB_PredeclaredId = True
Attribute VB_Exposed = False
Attribute VB_TemplateDerived = False
Attribute VB_Customizable = False
Private Sub cbAddToList_Click()
    If tbFind.Value = "" Then Exit Sub
    If tbReplace.Value = "" Then Exit Sub
    
    Dim strLine As String
    Dim vLine, vItem As Variant
    Dim strType, strTest As String
    
    strLine = Replace(UCase(tbReplace.Value), vbLf, "")
    vLine = Split(strLine, vbCr)
    For i = 0 To UBound(vLine)
        If vLine(i) = "" Then GoTo Next_line
        If Not Left(vLine(i), 1) = "+" Then vLine(i) = "+" & vLine(i)
        
        If InStr(vLine(i), "=") > 0 Then
            vItem = Split(vLine(i), "=")
            
            If Left(vItem(1), 1) = " " Then
                vLine(i) = vItem(0) & "={A} " & vItem(1)
            'Else
                'vLine(i) = vItem(0) & "=" & vItem(1)
            End If
        Else
            vLine(i) = vLine(i) & "=1"
        End If
        
Next_line:
    Next i
    
    strLine = ""
    For i = 0 To UBound(vLine)
        If vLine(i) = "" Then GoTo Next_Unit
        
        If strLine = "" Then
            strLine = vLine(i)
        Else
            strLine = strLine & ";;" & vLine(i)
        End If
        
Next_Unit:
    Next i
    
    If InStr(tbFind.Value, "+") > 0 Then
        strType = "f"
    Else
        strType = "p"
    End If
    
    If InStr(tbFind.Value, "= ") > 0 Then
        strType = strType & "f"
    Else
        strType = strType & "p"
    End If
    
    strTest = Left(tbFind.Value, 1)
    If Not strTest = "=" And Not strTest = "+" Then strLine = "+" & strLine
    
    lbList.AddItem UCase(tbFind.Value)
    lbList.List(lbList.ListCount - 1, 1) = strLine
    lbList.List(lbList.ListCount - 1, 2) = strType
    'MsgBox strType
End Sub

Private Sub cbClearText_Click()
    tbFind.Value = ""
    tbReplace.Value = ""
End Sub

Private Sub cbHelp_Click()
    If cbHelp.Caption = "Help" Then
        Me.Height = 366
        
        cbHelp.Caption = "Help Off"
    Else
        Me.Height = 234
        
        cbHelp.Caption = "Help"
    End If
End Sub

Private Sub cbReplace_Click()
    Dim vDwgLL, vDwgUR As Variant
    Dim filterType, filterValue As Variant
    Dim grpCode(0) As Integer
    Dim grpValue(0) As Variant
    Dim objSS As AcadSelectionSet
    Dim strType, strFind, strReplace As String
    Dim strStructures, strExtra, strSize As String
    Dim strAmount, strUnit As String
    Dim vFind, vReplace As Variant
    Dim vList, vUnit, vExtra As Variant
    Dim vLine, vItem, vTemp As Variant
    Dim iPos As Integer
    
    On Error Resume Next
    
    strStructures = ""
    If cbPoles.Value = True Then strStructures = "sPole"
    If cbPEDs.Value = True Then
        If strStructures = "" Then
            strStructures = "sPED"
        Else
            strStructures = strStructures & ",sPED"
        End If
    End If
    If cbHHs.Value = True Then
        If strStructures = "" Then
            strStructures = "sHH"
        Else
            strStructures = strStructures & ",sHH"
        End If
    End If
    If cbPanels.Value = True Then
        If strStructures = "" Then
            strStructures = "sPanel"
        Else
            strStructures = strStructures & ",sPanel"
        End If
    End If
    If cbFPs.Value = True Then
        If strStructures = "" Then
            strStructures = "sFP"
        Else
            strStructures = strStructures & ",sFP"
        End If
    End If
    
    Me.Hide
    
    vDwgLL = ThisDrawing.Utility.GetPoint(, "Get DWG LL Corner: ")
    vDwgUR = ThisDrawing.Utility.GetCorner(vDwgLL, vbCr & "Get DWG UR Corner: ")
    If Not Err = 0 Then
        Me.show
        Exit Sub
    End If
    
    grpCode(0) = 2
    grpValue(0) = strStructures
    filterType = grpCode
    filterValue = grpValue
    
    Set objSS = ThisDrawing.SelectionSets.Add("objSS")
    If Not Err = 0 Then
        Set objSS = ThisDrawing.SelectionSets.Item("objSS")
    End If
    objSS.Select acSelectionSetWindow, vDwgLL, vDwgUR, filterType, filterValue
    If objSS.count < 1 Then GoTo Exit_Sub
    
    MsgBox objSS.count & "  " & strStructures & " found."
    
    'GoTo Exit_Sub
    
    For Each objBlock In objSS
        vAttList = objBlock.GetAttributes
        
        Select Case objBlock.Name
            Case "sPole"
                If vAttList(27).TextString = "" Then GoTo Next_objBlock
                vList = Split(vAttList(27).TextString, ";;")
            Case Else
                If vAttList(7).TextString = "" Then GoTo Next_objBlock
                vList = Split(vAttList(7).TextString, ";;")
        End Select
        
        For i = 0 To UBound(vList)
            strUnit = vList(i)
            
            For j = 0 To lbList.ListCount - 1
                vFind = Split(lbList.List(j, 0), "=")
                
                'Check Left of =
                If InStr(vFind(0), "()") > 0 Then
                    vItem = Split(vFind(0), "()")
                    If InStr(strUnit, vItem(0)) > 0 Then
                        If InStr(strUnit, vItem(1)) < 1 Then GoTo Next_Find
                    Else
                        GoTo Next_Find
                    End If
                Else
                    If InStr(strUnit, vFind(0)) < 1 Then GoTo Next_Find
                End If
                
                'Check Right of = and get strAmount
                If InStr(vFind(1), "  ") < 1 Then
                    If InStr(vFind(1), " ") > 0 Then
                        vItem = Split(vFind(1), " ")
                        vFind(1) = Replace(vFind(1), vItem(0), vItem(0) & " ")
                        vItem = Split(vFind(1), "  ")
                    End If
                    
                    vUnit = Split(strUnit, "=")
                    vTemp = Split(vUnit(1), "  ")
                    If UBound(vTemp) < 1 Then GoTo Next_Find
                    
                    If InStr(vTemp(1), vItem(1)) < 1 Then GoTo Next_Find
                    strAmount = vTemp(0)
                Else
                    strAmount = vUnit(1)
                End If
                
                'FOUND UNIT: Now replace the units
                strReplace = Replace(lbList.List(j, 1), "{A}", strAmount)
                If InStr(strReplace, "()") > 0 Then
                    If InStr(strUnit, ")") > 0 Then
                        vLine = Split(strUnit, ")")
                        vTemp = Split(vLine(0), "(")
                        strSize = "(" & vTemp(1) & ")"
                        
                        strReplace = Replace(strReplace, "()", strSize)
                    End If
                End If
                
                vList(i) = strReplace
                
Next_Find:
            Next j
            
        Next i
        
        strLine = ""
        For i = 0 To UBound(vList)
            If Not vList(i) = "" Then
                If strLine = "" Then
                    strLine = vList(i)
                Else
                    strLine = strLine & ";;" & vList(i)
                End If
            End If
        Next i
        
        Select Case objBlock.Name
            Case "sPole"
                vAttList(27).TextString = strLine
            Case Else
                vAttList(7).TextString = strLine
        End Select
        
        objBlock.Update
        
Next_objBlock:
    Next objBlock
    
    
Exit_Sub:
    objSS.Clear
    objSS.Delete
    
    Me.show
End Sub

Private Sub tbFind_Exit(ByVal Cancel As MSForms.ReturnBoolean)
    If tbFind.Value = "" Then Exit Sub
    If Not Left(tbFind.Value, 1) = "+" Then tbFind.Value = "+" & tbFind.Value
    If InStr(tbFind.Value, "=") < 1 Then
        tbFind.Value = tbFind.Value & "={a}"
    Else
        If InStr(tbFind.Value, "= ") < 1 Then
            If InStr(tbFind.Value, "={") < 1 Then tbFind.Value = Replace(tbFind.Value, "=", "={A} ")
        End If
    End If
        
    If tbReplace.Value = "" Then
        tbReplace.Value = tbFind.Value
        Exit Sub
    End If
    
    If InStr(tbFind.Value, "(") < 1 Then Exit Sub
    If InStr(tbReplace.Value, "(") < 1 Then Exit Sub
    
    Dim vLine, vItem, vTemp As Variant
    Dim strLine, strSize, strFind, strReplace As String
    
    vLine = Split(tbFind.Value, "(")
    vItem = Split(vLine(1), ")")
    'strSize = vItem(0)
    strReplace = "(" & vItem(0) & ")"
    
    vTemp = Split(tbReplace.Value, vbCr)
    
    vLine = Split(vTemp(0), "(")
    vItem = Split(vLine(1), ")")
    strFind = "(" & vItem(0) & ")"
    
    strLine = vLine(0) & strReplace & vItem(1)
    If UBound(vTemp) > 0 Then
        For i = 1 To UBound(vTemp)
            vTemp(i) = Replace(vTemp(i), strFind, strReplace)
            strLine = strLine & vbCr & vTemp(i)
        Next i
    End If
    
    tbReplace.Value = strLine
End Sub

Private Sub UserForm_Initialize()
    lbList.ColumnCount = 3
    lbList.ColumnWidths = "84;180;6"
    
    Dim strLine As String
    
    strLine = "Enter the unit name you want to find.  It is not case senitive.  If you don't start with a plus symbol, it will be added for you."
    strLine = strLine & "  If you want to find all closures or cables placed in the same way, do not put a size inbetween the parenthesis."
    strLine = strLine & "  If you need to find something with a description add an equal sign and a space then enter the description."
    strLine = strLine & vbCr & vbCr & "Find Examples:" & vbCr & "+haco(12)" & vbCr & "haco()= g5"
    strLine = strLine & vbCr & "+co()e" & vbCr & "+co()e= loop" & vbCr & vbCr
    strLine = strLine & ""
    strLine = strLine & "Enter the replacement unit first then any other units that need to added.  Seperated the units on different lines."
    strLine = strLine & "  If the Replace text box is empty, it will copy the Find text into the box."
    strLine = strLine & "  If you want the amount of any units to be equal to a know number add an equal sign and the number it will be."
    strLine = strLine & "  If you need to add a description, make sure there is an equal sign and after the known amount, if any, add the description."
    strLine = strLine & "  The plus symbol is not necessary on the any of the replace units."
    strLine = strLine & ""
    strLine = strLine & ""
    strLine = strLine & ""
    
    tbHelp.Value = strLine
End Sub

Attribute VB_Name = "ResizeBlocks"
Attribute VB_Base = "0{182FCE73-399D-4E28-AC7A-3D3321E1DD0B}{283D0B95-9170-42E3-B9F5-E54F2894EEAC}"
Attribute VB_GlobalNameSpace = False
Attribute VB_Creatable = False
Attribute VB_PredeclaredId = True
Attribute VB_Exposed = False
Attribute VB_TemplateDerived = False
Attribute VB_Customizable = False
Private Sub cbExport_Click()
    If tbFile.Value = "" Then Exit Sub
    
    Dim strText, strFileName As String
    
    strFileName = "C:\Integrity\VBA\References\"
    strFileName = strFileName & tbFile.Value & ".rbl"
    
    strText = ""
    
    If lbBlocks.ListCount > 0 Then
        For i = 0 To lbBlocks.ListCount - 1
            If lbBlocks.List(i, 1) = "YES" Then
                If strText = "" Then
                    strText = lbBlocks.List(i, 0) & vbCr
                Else
                    strText = strText & lbBlocks.List(i, 0) & vbCr
                End If
            End If
        Next i
    End If
    
    Open strFileName For Output As #1
    
    Print #1, strText
    
    Close #1
End Sub

Private Sub cbImport_Click()
    If lbFiles.ListCount < 1 Then Exit Sub
    If lbFiles.ListIndex < 0 Then Exit Sub
    
    tbFile.Value = lbFiles.List(lbFiles.ListIndex)
    
    Dim strLine, strFileName As String
    Dim strBlocks As String
    Dim vBlocks As Variant
    Dim fName As String
    
    strFileName = "C:\Integrity\VBA\References\"
    strFileName = strFileName & lbFiles.List(lbFiles.ListIndex) & ".rbl"
    
    strBlocks = ""
    
    fName = Dir(strFileName)
    If fName = "" Then
        Exit Sub
    End If
    
    Open strFileName For Input As #2
    
    While Not EOF(2)
        Input #2, strLine
        
        If strBlocks = "" Then
            strBlocks = strLine
        Else
            strBlocks = strBlocks & vbTab & strLine
        End If
    Wend
    
    Close #2
    
    If Not strBlocks = "" Then
        vBlocks = Split(strBlocks, vbTab)
        
        If lbBlocks.ListCount > 0 Then
            For i = 0 To lbBlocks.ListCount - 1
                For j = 0 To UBound(vBlocks)
                    If lbBlocks.List(i, 0) = vBlocks(j) Then
                        lbBlocks.List(i, 1) = "YES"
                        GoTo Next_Block
                    End If
                Next j
Next_Block:
            Next i
        End If
    End If
End Sub

Private Sub cbQuit_Click()
    Me.Hide
End Sub

Private Sub cbResize_Click()
    Dim vDwgLL, vDwgUR As Variant
    Dim objSSSS, objSSBlocks As AcadSelectionSet
    Dim objBlock, objBlockSS As AcadBlockReference
    Dim dScale, dPnt(2) As Double
    Dim dLL(2), dUR(2) As Double
    Dim filterType, filterValue As Variant
    Dim grpCode(0) As Integer
    Dim grpValue(0) As Variant
    Dim vPnt As Variant
    Dim strText As String
    
    On Error Resume Next
    
    strText = ""
    
    For i = 0 To lbBlocks.ListCount - 1
        If lbBlocks.List(i, 1) = "YES" Then
            If strText = "" Then
                strText = lbBlocks.List(i, 0)
            Else
                strText = strText & "," & lbBlocks.List(i, 0)
            End If
        End If
    Next i
    
    If strText = "" Then Exit Sub
    
    Me.Hide
    
    vDwgLL = ThisDrawing.Utility.GetPoint(, "Get LL Corner: ")
    vDwgUR = ThisDrawing.Utility.GetCorner(vDwgLL, vbCr & "Get UR Corner: ")
    
    If Not Err = 0 Then GoTo Exit_Sub
    
    Set objSSSS = ThisDrawing.SelectionSets.Add("objSSSS")
    If Not Err = 0 Then
        Set objSSSS = ThisDrawing.SelectionSets.Item("objSSSS")
        Err = 0
    End If
    
    Set objSSBlocks = ThisDrawing.SelectionSets.Add("objSSBlocks")
    If Not Err = 0 Then
        Set objSSBlocks = ThisDrawing.SelectionSets.Item("objSSBlocks")
        Err = 0
    End If
    
    grpCode(0) = 2
    grpValue(0) = "SS-11x17"
    filterType = grpCode
    filterValue = grpValue
    
    objSSSS.Select acSelectionSetWindow, vDwgLL, vDwgUR, filterType, filterValue
    
    grpValue(0) = strText
    filterType = grpCode
    filterValue = grpValue
    
    objSSBlocks.Select acSelectionSetWindow, vDwgLL, vDwgUR, filterType, filterValue
    
    For Each objBlock In objSSSS
        dScale = objBlock.XScaleFactor * 1.3333333333
        
        vPnt = objBlock.InsertionPoint
        dLL(0) = vPnt(0)
        dLL(1) = vPnt(1)
        
        dUR(0) = dLL(0) + (1650 * dScale)
        dUR(1) = dLL(1) + (1050 * dScale)
        
        For Each objBlockSS In objSSBlocks
            dPnt(0) = objBlockSS.InsertionPoint(0)
            dPnt(1) = objBlockSS.InsertionPoint(1)
            
            If dPnt(0) > dLL(0) And dPnt(0) < dUR(0) Then
                If dPnt(1) > dLL(1) And dPnt(1) < dUR(1) Then
                    objBlockSS.XScaleFactor = dScale
                    objBlockSS.YScaleFactor = dScale
                    objBlockSS.ZScaleFactor = dScale
                    
                    objBlockSS.Update
                End If
            End If
        Next objBlockSS
    Next objBlock
    
Exit_Sub:
    objSSSS.Clear
    objSSSS.Delete
    
    objSSBlocks.Clear
    objSSBlocks.Delete
    
    Me.show
End Sub

Private Sub cbSelectLayer_Click()
    If lbBlocks.ListCount < 1 Then Exit Sub
    
    Dim objEntity As AcadEntity
    Dim objBlock As AcadBlockReference
    Dim vReturnPnt As Variant
    Dim strName As String
    
    On Error Resume Next
    
    Me.Hide
    
Get_Another:
    
    ThisDrawing.Utility.GetEntity objEntity, vReturnPnt, vbCr & "Select Blocks:"
    If Not Err = 0 Then GoTo Exit_Sub
    
    If TypeOf objEntity Is AcadBlockReference Then
        Set objBlock = objEntity
    
        strName = objBlock.Name
    
        For i = 0 To lbBlocks.ListCount - 1
            If lbBlocks.List(i, 0) = strName Then
                lbBlocks.List(i, 1) = "YES"
                GoTo Get_Another
            End If
        Next i
    End If
    
    GoTo Get_Another
    
Exit_Sub:
    Me.show
End Sub

Private Sub Label5_Click()
    If lbBlocks.ListCount < 1 Then Exit Sub
    
    Dim strName, strStatus As String
    Dim iIndex, iCount As Integer
    
    iIndex = 0
    
    For iCount = 0 To lbBlocks.ListCount - 1
        If lbBlocks.List(iCount, 1) = "YES" Then
            strName = lbBlocks.List(iCount, 0)
            strStatus = lbBlocks.List(iCount, 1)
            
            lbBlocks.RemoveItem iCount
            lbBlocks.AddItem strName, iIndex
            lbBlocks.List(iIndex, 1) = strStatus
            iIndex = iIndex + 1
        End If
    Next iCount
    
    lbBlocks.ListIndex = 0
End Sub

Private Sub lbBlocks_DblClick(ByVal Cancel As MSForms.ReturnBoolean)
    Select Case lbBlocks.List(lbBlocks.ListIndex, 1)
        Case "YES"
            lbBlocks.List(lbBlocks.ListIndex, 1) = ""
        Case Else
            lbBlocks.List(lbBlocks.ListIndex, 1) = "YES"
    End Select
End Sub

Private Sub UserForm_Initialize()
    Dim strTFolder, strFile As String
    Dim vTemp As Variant
    strTFolder = "C:\Integrity\VBA\References\*.*"
    
    strFile = Dir$(strTFolder)
    
    Do While strFile <> ""
        If InStr(strFile, ".rbl") Then
            lbFiles.AddItem Replace(strFile, ".rbl", "")
        End If
        strFile = Dir$
    Loop
    
    lbBlocks.ColumnCount = 2
    lbBlocks.ColumnWidths = "126;48"
    
    Dim objBlocks As AcadBlocks
    Dim strLine As String
            
    Set objBlocks = ThisDrawing.Blocks
    For i = 0 To objBlocks.count - 1
        strLine = objBlocks(i).Name
        
        If Left(strLine, 1) = "*" Then GoTo Next_Block
        If Left(strLine, 2) = "A$" Then GoTo Next_Block
        
        lbBlocks.AddItem objBlocks(i).Name
        lbBlocks.List(lbBlocks.ListCount - 1, 1) = ""
        
Next_Block:
    Next i
    
    Call SortListBlocks
End Sub

Private Sub SortListBlocks()
    Dim a, b As Integer
    Dim iCount As Integer
    Dim strAtt(0 To 1) As String
    
    iCount = lbBlocks.ListCount - 1
    If iCount < 1 Then Exit Sub
    
    On Error Resume Next
    
    For a = iCount To 0 Step -1
        For b = 0 To a - 1
            If lbBlocks.List(b, 0) > lbBlocks.List(b + 1, 0) Then
                If Not Err = 0 Then
                    MsgBox "Error sorting list"
                    lbBlocks.Selected(b) = True
                    lbBlocks.ListIndex = b
                    Exit Sub
                End If
                
                strAtt(0) = lbBlocks.List(b + 1, 0)
                strAtt(1) = lbBlocks.List(b + 1, 1)
                
                lbBlocks.List(b + 1, 0) = lbBlocks.List(b, 0)
                lbBlocks.List(b + 1, 1) = lbBlocks.List(b, 1)
                
                lbBlocks.List(b, 0) = strAtt(0)
                lbBlocks.List(b, 1) = strAtt(1)
            End If
        Next b
    Next a
End Sub

Private Function FindDWGNumber(vPnt As Variant)
    Dim objSS As AcadSelectionSet
    Dim objBlock As AcadBlockReference
    Dim filterType, filterValue As Variant
    Dim grpCode(0) As Integer
    Dim grpValue(0) As Variant
    Dim vAttList As Variant
    Dim dLL(2), dUR(2) As Double
    Dim dPnt(1) As Double
    Dim dScale As Double
    Dim strDWG As String
    
    On Error Resume Next
    
    strDWG = "??"
    dPnt(0) = vPnt(0)
    dPnt(1) = vPnt(1)
    
    grpCode(0) = 2
    grpValue(0) = "SS-11x17"
    filterType = grpCode
    filterValue = grpValue
    
    Err = 0
    Set objSS = ThisDrawing.SelectionSets.Add("objSS")
    If Not Err = 0 Then
        Set objSS = ThisDrawing.SelectionSets.Item("objSS")
        Err = 0
    End If
    
    objSS.Select acSelectionSetAll, , , filterType, filterValue
    
    For Each objBlock In objSS
        vAttList = objBlock.GetAttributes
        dScale = objBlock.XScaleFactor
        
        dLL(0) = objBlock.InsertionPoint(0)
        dLL(1) = objBlock.InsertionPoint(1)
        
        dUR(0) = dLL(0) + (1650 * dScale)
        dUR(1) = dLL(1) + (1050 * dScale)
        
        If dPnt(0) > dLL(0) And dPnt(0) < dUR(0) Then
            If dPnt(1) > dLL(1) And dPnt(1) < dUR(1) Then
                strDWG = vAttList(0).TextString
                'MsgBox "Found:" & strDWG
                GoTo Exit_Sub
            End If
        End If
    Next objBlock
    
Exit_Sub:
    objSS.Clear
    objSS.Delete
    
    FindDWGNumber = strDWG
End Function

Attribute VB_Name = "Revision"
Attribute VB_Base = "0{8014D6DA-D984-41A6-B597-06F33CB4A02B}{B74A5ABB-F4CB-4ADD-9FDF-D46A4469B061}"
Attribute VB_GlobalNameSpace = False
Attribute VB_Creatable = False
Attribute VB_PredeclaredId = True
Attribute VB_Exposed = False
Attribute VB_TemplateDerived = False
Attribute VB_Customizable = False
Dim objSS As AcadSelectionSet
    
Private Sub cbAddNote_Click()
    Dim objBlock As AcadBlockReference
    Dim vAttList, vReturnPnt As Variant
    
    On Error Resume Next
    
    Me.Hide
    
Place_Another:
    
    vReturnPnt = ThisDrawing.Utility.GetPoint(, vbCr & "Place note:")
    If Not Err = 0 Then GoTo Exit_Sub
    
    Set objBlock = ThisDrawing.ModelSpace.InsertBlock(vReturnPnt, "Revision", 1#, 1#, 1#, 0#)
    objBlock.Layer = "Integrity Notes"
    
    vAttList = objBlock.GetAttributes
    vAttList(0).TextString = cbNumber.Value
    vAttList(1).TextString = tbDate.Value
    vAttList(2).TextString = UCase(tbInitials.Value)
    vAttList(3).TextString = UCase(tbNote.Value)
    objBlock.Update
    
    GoTo Place_Another
    
Exit_Sub:
    Me.show
End Sub

Private Sub cbNumber_Exit(ByVal Cancel As MSForms.ReturnBoolean)
    If cbNumber.ListCount < 1 Then Exit Sub
    
    For i = 0 To cbNumber.ListCount - 1
        If cbNumber.Value = cbNumber.List(i) Then GoTo Found_Revision
    Next i
    
    cbUpdateNote.Enabled = False
    Exit Sub
    
Found_Revision:
    
    Dim objBlock As AcadBlockReference
    Dim vAttList As Variant
    
    For Each objBlock In objSS
        vAttList = objBlock.GetAttributes
        If vAttList(0).TextString = cbNumber.Value Then
            tbDate.Value = vAttList(1).TextString
            tbInitials.Value = vAttList(2).TextString
            tbNote.Value = vAttList(3).TextString
    
            cbUpdateNote.Enabled = True
            cbAddNote.Enabled = False
            cbNumber.Enabled = False
            Exit Sub
        End If
    Next objBlock
    
End Sub

Private Sub cbUpdateNote_Click()
    Dim objBlock As AcadBlockReference
    Dim vAttList As Variant
    
    For Each objBlock In objSS
        vAttList = objBlock.GetAttributes
        If vAttList(0).TextString = cbNumber.Value Then
            vAttList(1).TextString = tbDate.Value
            vAttList(2).TextString = UCase(tbInitials.Value)
            vAttList(3).TextString = UCase(tbNote.Value)
    
            objBlock.Update
        End If
    Next objBlock
    
    cbUpdateNote.Enabled = False
    cbAddNote.Enabled = True
    cbNumber.Enabled = True
    
    cbNumber.Value = ""
    tbDate.Value = ""
    tbInitials.Value = ""
    tbNote.Value = ""
End Sub

Private Sub Label2_Click()
    tbDate.Value = Date
End Sub

Private Sub tbNote_Change()
    tbNote.Value = UCase(tbNote.Value)
End Sub

Private Sub UserForm_Deactivate()
    objSS.Clear
    objSS.Delete
End Sub

Private Sub UserForm_Initialize()
    Dim filterType, filterValue As Variant
    Dim grpCode(0) As Integer
    Dim grpValue(0) As Variant
    Dim objBlock As AcadBlockReference
    Dim vAttList As Variant
    Dim strNumber As String
    Dim iNumber, iNext As Integer
    
    On Error Resume Next
    
    Set objSS = ThisDrawing.SelectionSets.Add("objSS")
    If Not Err = 0 Then
        Set objSS = ThisDrawing.SelectionSets.Item("objSS")
        objSS.Clear
    End If
    
    grpCode(0) = 2
    grpValue(0) = "Revision"
    filterType = grpCode
    filterValue = grpValue
    
    Set objSS = ThisDrawing.SelectionSets.Add("objSS")
    objSS.Select acSelectionSetAll, , , filterType, filterValue
    
    iNumber = 0
    
    For Each objBlock In objSS
        vAttList = objBlock.GetAttributes
        
        strNumber = vAttList(0).TextString
        iNext = CInt(strNumber)
        If iNext > iNumber Then iNumber = iNext
        
        If cbNumber.ListCount < 1 Then
            cbNumber.AddItem strNumber
        Else
            For i = 0 To cbNumber.ListCount - 1
                If cbNumber.List(i) = strNumber Then GoTo Next_objBlock
            Next i
            
            cbNumber.AddItem vAttList(0).TextString
        End If
Next_objBlock:
    Next objBlock
    
    cbNumber.Value = iNumber + 1
End Sub

Attribute VB_Name = "SPIDAminSearch"
Attribute VB_Base = "0{301F674A-2F40-4899-82CA-CFF5C7AA6086}{1205CD85-FE4A-470A-AC11-85365D87F22A}"
Attribute VB_GlobalNameSpace = False
Attribute VB_Creatable = False
Attribute VB_PredeclaredId = True
Attribute VB_Exposed = False
Attribute VB_TemplateDerived = False
Attribute VB_Customizable = False

Private Sub cbCreateReports_Click()
    Dim vLine As Variant
    Dim strHeader, strMiddle, strEnd As String
    Dim strLine, strTemp, strSearch As String
    Dim strFileName, strFileBase, strJob As String
    Dim iCounter As Integer
    
    iCounter = 1
    
    strJob = tbJobNumber.Value & " SEARCH "
    strFileBase = ThisDrawing.Path & "\"
    
    strHeader = "{""id"":699858,""userID"":" & tbUserID.Value & ",""name"":"""
    strMiddle = """,""service"":""OH Structure"",""groups"":[{""id"":699859,""entries"":[{""field"":""FID Number"",""id"":699860,""unit"":null,""value"":"""
    strEnd = """,""operator"":""is in the list""}]}]}"
    
    strTemp = Replace(tbResult.Value, vbLf, "")
    vLine = Split(strTemp, vbCr)
    
    For i = 0 To UBound(vLine)
        If vLine(i) = "" Then GoTo Next_line
        
        If iCounter < 10 Then
            strSearch = strJob & "0" & iCounter
        Else
            strSearch = strJob & iCounter
        End If
        
        strLine = strHeader
        strLine = strLine & strSearch & strMiddle & vLine(i) & strEnd
        
        strFileName = strFileBase & strSearch & ".json"
        Open strFileName For Output As #1
        Print #1, strLine
        Close #1
        
        'MsgBox strFilename & vbCr & vbCr & strLine
        iCounter = iCounter + 1
Next_line:
    Next i
End Sub

Private Sub cbFromList_Change()
    Dim amap As AcadMap
    Dim ODRcs As ODRecords
    Dim ODRc As ODRecord
    Dim tbl As ODTable
    Dim tbls As ODTables
    Dim refColumn As ODFieldDef
    Dim objEntity As AcadEntity
    Dim boolVal As Boolean
    Dim iCount As Integer
    Dim strTest As String
    
    On Error Resume Next
    
    Set amap = ThisDrawing.Application.GetInterfaceObject("AutoCADMap.Application")
    
    Set tbls = amap.Projects(ThisDrawing).ODTables
    If tbls.count > 0 Then
        For Each tbl In tbls
            If tbl.Name = cbFromList.Value Then GoTo Exit_For
        Next
    End If
Exit_For:

    Set ODRcs = tbl.GetODRecords
        
    iCount = 0
    Err = 0
        
    While Err = 0
        Set refColumn = tbl.ODFieldDefs(iCount)
        strTest = refColumn.Name
        If Not Err = 0 Then GoTo Exit_objEntity
            
        lbFrom.AddItem
        lbFrom.List(iCount, 0) = iCount
        lbFrom.List(iCount, 1) = strTest
        iCount = iCount + 1
    Wend
Exit_objEntity:
    
    For i = 0 To lbFrom.ListCount - 1
        If lbFrom.List(i, 1) = "FID_NUMBER" Then
            lbFrom.Selected(i) = True
            Exit Sub
        End If
    Next i
End Sub

Private Sub cbGetPolygon_Click()
    Dim amap As AcadMap
    Dim tbl As ODTable
    Dim tbls As ODTables
    
    Dim filterType, filterValue As Variant
    Dim grpCode(0) As Integer
    Dim grpValue(0) As Variant
    Dim objSS As AcadSelectionSet
    Dim objEntity As AcadEntity
    Dim objLWP As AcadLWPolyline
    Dim objPoint As AcadPoint
    Dim vReturnPnt As Variant
    Dim vLine As Variant
    Dim strLine, strTemp As String
    Dim iIndex As Integer
    Dim dCoords() As Double
    Dim iCounter, iTotal As Integer
    Dim iNPG, iGN As Integer
    
    On Error Resume Next
    
    iNPG = CInt(tbNPG.Value)
    iGN = 0
    iTotal = 0
    
    If lbFrom.ListIndex < 0 Then Exit Sub
    iIndex = CInt(lbFrom.List(lbFrom.ListIndex, 0))
    
    strLine = ""
    
    Set amap = ThisDrawing.Application.GetInterfaceObject("AutoCADMap.Application")
    
    Set tbls = amap.Projects(ThisDrawing).ODTables
    If tbls.count > 0 Then
        For Each tbl In tbls
            If tbl.Name = cbFromList.Value Then GoTo Exit_For
        Next
    End If
    
    Exit Sub
    
Exit_For:
    
    Set ODRcs = tbl.GetODRecords
    
    Me.Hide
    
    ThisDrawing.Utility.GetEntity objEntity, vReturnPnt, "Select Polygon Border: "
    If Not objEntity.ObjectName = "AcDbPolyline" Then
        MsgBox "Error: Invalid Selection."
        Me.show
        Exit Sub
    End If
    
    Set objLWP = objEntity
    vCoords = objLWP.Coordinates
    
    iTemp = (UBound(vCoords) + 1) / 2 * 3 - 1
    ReDim dCoords(iTemp) As Double
    
    iCounter = 0
    For i = 0 To UBound(vCoords) Step 2
        dCoords(iCounter) = vCoords(i)
        iCounter = iCounter + 1
        dCoords(iCounter) = vCoords(i + 1)
        iCounter = iCounter + 1
        dCoords(iCounter) = 0#
        iCounter = iCounter + 1
    Next i
    
    grpCode(0) = 8
    grpValue(0) = cbFromList.Value
    filterType = grpCode
    filterValue = grpValue
    
    Err = 0
    Set objSS = ThisDrawing.SelectionSets.Add("objSS")
    If Not Err = 0 Then Set objSS = ThisDrawing.SelectionSets.Item("objSS")
    
    objSS.SelectByPolygon acSelectionSetWindowPolygon, dCoords, filterType, filterValue
    
    For Each objEntity In objSS
        If TypeOf objEntity Is AcadPoint Then
            Set objPoint = objEntity
            
            boolVal = ODRcs.Init(objEntity, True, False)
            Set ODRc = ODRcs.Record
            
            strTemp = ODRc.Item(iIndex).Value
            If strTemp = "" Then GoTo Next_Object
            
            iGN = iGN + 1
            iTotal = iTotal + 1
            
            If strLine = "" Then
                strLine = strTemp
            Else
                If iGN > iNPG Then
                    strLine = strLine & vbCr & vbCr & strTemp
                    iGN = 1
                Else
                    strLine = strLine & "," & strTemp
                End If
            End If
        End If
Next_Object:
    Next objEntity
    
    tbResult.Value = strLine
    
    cbCreateReports.Enabled = True
    tbListCount.Value = iTotal
Exit_Sub:
    objSS.Clear
    objSS.Delete
    
    Me.show
End Sub

Private Sub tbResult_DblClick(ByVal Cancel As MSForms.ReturnBoolean)
    tbResult.SelStart = 0
    tbResult.SelLength = Len(tbResult.Value)
End Sub

Private Sub UserForm_DblClick(ByVal Cancel As MSForms.ReturnBoolean)
    tbResult.SelStart = 0
    tbResult.SelLength = Len(tbResult.Value)
End Sub

Private Sub UserForm_Initialize()
    lbFrom.Clear
    lbFrom.ColumnCount = 2
    lbFrom.ColumnWidths = "20;90"
    
    Dim amap As AcadMap
    Dim tbl As ODTable
    Dim tbls As ODTables
    
    Set amap = ThisDrawing.Application.GetInterfaceObject("AutoCADMap.Application")
    
    Set tbls = amap.Projects(ThisDrawing).ODTables
    If tbls.count > 0 Then
        cbFromList.Clear
        For Each tbl In tbls
            cbFromList.AddItem tbl.Name
        Next
    End If
    
    Dim vLine As Variant
    Dim strLine, strName, strTemp As String
    
    strName = ""
    strTemp = LCase(ThisDrawing.Path)
    If InStr(strTemp, "united") > 0 Then strName = "UTC"
    'If InStr(strTemp, "mastec") > 0 Then strName = "MAS"
    'If InStr(strTemp, "ecc ") > 0 Then strName = "ECC"
    
    vLine = Split(ThisDrawing.Name, " ")
    strName = strName & vLine(0)
    
    tbJobNumber.Value = strName
    
    If cbFromList.ListCount > 0 Then
        For i = 0 To cbFromList.ListCount - 1
            strName = LCase(cbFromList.List(i))
            If InStr(strName, "structure") > 0 Then
                If InStr(strName, "oh") > 0 Then
                    cbFromList.Value = cbFromList.List(i)
                    GoTo Past_Structure
                End If
            End If
        Next i
    End If
Past_Structure:
    
End Sub

Attribute VB_Name = "ScopeOfWork"
Attribute VB_Base = "0{6C87FACA-74E8-4195-A120-B9EEEEDE7052}{C5ADC72A-3813-4E68-922C-F1D15CC26F68}"
Attribute VB_GlobalNameSpace = False
Attribute VB_Creatable = False
Attribute VB_PredeclaredId = True
Attribute VB_Exposed = False
Attribute VB_TemplateDerived = False
Attribute VB_Customizable = False

Dim strTFolder As String

Private Sub cbEmail_Click()
    Dim objOutlook As Outlook.Application
    Dim objMail As Outlook.MailItem
    Dim strTo, strCC, strSubject, strBody As String
    'Dim strVerb As String
    Dim strCompany, strPath As String
    'Dim vTemp As Variant
    Dim iNumber, iEmailSelf As Integer
    Dim iMTEMC, iOther, iDWG As Integer
    Dim iRevision As Integer
    
    On Error Resume Next
    
    Me.Hide
    
    strPath = ThisDrawing.Path
    strCompany = ""
    If InStr(UCase(strPath), "UNITED") Then strCompany = "UTC "
    If InStr(UCase(strPath), "LORETTO") Then strCompany = "Loretto "
    
    If Right(tbNumber.Value, 1) = "*" Then
        strSubject = "<Project Update> " & strCompany & tbNumber.Value & " - " & " Scope Revised"
        strBody = "<b>" & tbNumber.Value & " " & tbTitle.Value & "</b> " & " has been revised." & vbCr
    Else
        strSubject = "<Project Update> " & strCompany & tbNumber.Value & " - " & " Planning Review Complete"
        strBody = "<b>" & tbNumber.Value & " " & tbTitle.Value & "</b> " & " is ready for the next stage." & vbCr
        'strBody = strBody & vbCr & "# LU = UNKNOWN"
        tbNumber.Value = tbNumber.Value & "*"
    End If
    
    'strSubject = "<Project Update> " & strCompany & tbNumber.Value & " " & tbTitle.Value & " - " & " Planning Review Complete"
    strTo = "jon.wilburn@integrity-us.com;adam.kemper@integrity-us.com;rich.taylor@integrity-us.com"

    Load ProjectStatusEmail
    
    ProjectStatusEmail.Caption = "Planning"
    ProjectStatusEmail.tbBody.Value = Replace(strBody, "<br>", vbCr)
    ProjectStatusEmail.tbSubject.Value = strSubject
    ProjectStatusEmail.lbCC.AddItem "Wade.Hampton@integrity-us.com"
    ProjectStatusEmail.show
    
    strBody = Replace(ProjectStatusEmail.tbBody.Value, vbCr, "<br>")
    If strBody = "" Then
        MsgBox "Email Cancelled."
        Me.show
        Exit Sub
    End If
    
    If ProjectStatusEmail.cbCcSelf.Value = True Then
        iEmailSelf = 1
    Else
        iEmailSelf = 0
    End If
    
    For n = 0 To ProjectStatusEmail.lbCC.ListCount - 1
        'If ProjectStatusEmail.lbCC.Selected(n) = True Then
            strCC = strCC & ProjectStatusEmail.lbCC.List(n) & ";"
        'End If
    Next n
    
    Unload ProjectStatusEmail
    
    Set objOutlook = New Outlook.Application
    Set objMail = objOutlook.CreateItem(olMailItem)
    
    objMail.To = strTo
    If iEmailSelf = 1 Then strCC = strCC & objOutlook.Session.CurrentUser.Address
    objMail.CC = strCC  'objOutlook.Session.CurrentUser.Address
    objMail.Subject = strSubject
    objMail.HTMLBody = strBody
    
    'objMail.Display
    objMail.Send
    Me.show
End Sub

Private Sub cbFind_Exit(ByVal Cancel As MSForms.ReturnBoolean)
    If cbFind.Value = "" Then Exit Sub
    
    cbReplaceText.Clear
    cbReplaceText.MatchRequired = False
    
    Dim vLine, vItem As Variant
    
    For i = 0 To lbVariables.ListCount - 1
        If lbVariables.List(i, 0) = cbFind.Value Then
            If lbVariables.List(i, 0) = "<Empty>" Then Exit Sub
            GoTo Found_Line
        End If
    Next i
    
Found_Line:
    'vLine = Split(lbVariables.List(i, 1), ",")
    'If UBound(vLine) = 0 Then Exit Sub
    
    vItem = Split(lbVariables.List(i, 1), ",")
    For i = 0 To UBound(vItem)
        cbReplaceText.AddItem vItem(i)
    Next i
    
    If UBound(vItem) > 0 Then cbReplaceText.MatchRequired = True
End Sub

Private Sub cbJobType_Exit(ByVal Cancel As MSForms.ReturnBoolean)
    'If Not tbSOW.Value = "" Then Exit Sub
    If strTFolder = "" Then Exit Sub
    If cbJobType.Value = "" Then Exit Sub
    
    If Len(tbSOW.Value) > 1 Then
        Dim result As Integer
    
        result = MsgBox("Overwrite Notes and Scope?", vbYesNo, "Overwrite Existing")
        If result = vbNo Then
            Exit Sub
        End If
    End If
    
    Dim strPath, strLine As String
    Dim fName As String
    Dim iStatus As Integer
    Dim vLine, vTemp As Variant
    Dim vVar, vCond As Variant
    
    tbSpecial.Value = ""
    tbSOW.Value = ""
    
    lbVariables.Clear
    lbCond.Clear
    
    iStatus = 0
    strPath = Replace(strTFolder, "*.*", "") & cbJobType.Value & ".swt"
    
    fName = Dir(strPath)
    If fName = "" Then
        Exit Sub
    End If
    
    Open strPath For Input As #1
    
    While Not EOF(1)
        Line Input #1, strLine
        
        If InStr(strLine, ">>") > 0 And Not iStatus = 3 Then
            vLine = Split(strLine, ">>")
            For j = 0 To UBound(vLine) - 1
            
                vTemp = Split(vLine(j), "<<")
                vVar = Split(vTemp(1), "/")
            
                'If lbVariables.ListCount < 0 Then
                    For i = 0 To lbVariables.ListCount - 1
                        If lbVariables.List(i, 0) = vVar(0) Then GoTo Skip_Adding_Var
                    Next i
                'End If
            
                lbVariables.AddItem vVar(0)
                If UBound(vVar) > 0 Then
                    lbVariables.List(lbVariables.ListCount - 1, 1) = Replace(vVar(1), ">>", "")
                Else
                    lbVariables.List(lbVariables.ListCount - 1, 1) = "<Empty>"
                End If
        
Skip_Adding_Var:
            Next j
            
            If UBound(vLine) > 2 Then
                For i = 1 To UBound(vLine) - 1
                    vTemp = Split(vLine(i), "<<")
                    vVar = Split(vTemp(1), "/")
            
                    'For j = 0 To lbVariables.ListCount - 1
                        'If lbVariables.List(j, 0) = vVar(0) Then GoTo Skip_Adding_This
                    'Next j
            
                    lbVariables.AddItem vVar(0)
                    If UBound(vVar) > 0 Then
                        lbVariables.List(lbVariables.ListCount - 1, 1) = Replace(vVar(1), ">>", "")
                    Else
                        lbVariables.List(lbVariables.ListCount - 1, 1) = "<Empty>"
                    End If
Skip_Adding_This:
                    'cbFind.AddItem "<<" & vTemp(1) & ">>"
                Next i
            End If
        End If
        
        If Left(strLine, 2) = "[[" Then
            Select Case Left(strLine, 3)
                Case "[[I"
                    iStatus = 1
                Case "[[S"
                    iStatus = 2
                Case "[[C"
                    iStatus = 3
            End Select
        Else
            Select Case iStatus
                Case Is = 1
                    If tbSpecial.Value = "" Then
                        tbSpecial.Value = strLine
                    Else
                        tbSpecial.Value = tbSpecial.Value & vbCr & strLine
                    End If
                Case Is = 2
                    If tbSOW.Value = "" Then
                        tbSOW.Value = strLine
                    Else
                        tbSOW.Value = tbSOW.Value & vbCr & strLine
                    End If
                Case Is = 3
                    '<---------------------------------------------------------------------
                    vCond = Split(strLine, "=")
                    lbCond.AddItem vCond(0)
                    lbCond.List(lbCond.ListCount - 1, 1) = vCond(1)
                    lbCond.List(lbCond.ListCount - 1, 2) = vCond(2)
            End Select
        End If
    Wend
    
    Close #1
    
    For i = 0 To lbVariables.ListCount - 1
        cbFind.AddItem lbVariables.List(i, 0)
    Next i
End Sub

Private Sub cbQuit_Click()
    Me.Hide
End Sub

Private Sub cbReplaceAll_Click()
    If cbReplaceText.Value = "" Then Exit Sub
    
    cbReplaceText.MatchRequired = False
    
    Dim strTemp, strFind As String
    
    For i = 0 To lbVariables.ListCount - 1
        If lbVariables.List(i, 0) = cbFind.Value Then GoTo Found_Var
    Next i
    
Found_Var:
    
    strFind = "<<" & lbVariables.List(i, 0) '& "/" & lbVariables.List(i, 1) & ">>"
    If lbVariables.List(i, 1) = "<Empty>" Then
        strFind = strFind & ">>"
    Else
        strFind = strFind & "/" & lbVariables.List(i, 1) & ">>"
    End If
    
    strTemp = Replace(tbSpecial.Value, strFind, "<b>" & cbReplaceText.Value & "</b>")
    tbSpecial.Value = strTemp
    
    strTemp = Replace(tbSOW.Value, strFind, "<b>" & cbReplaceText.Value & "</b>")
    tbSOW.Value = strTemp
    
    For n = 0 To lbCond.ListCount - 1
        If lbCond.List(n, 0) = lbVariables.List(i, 0) Then
            'MsgBox "Found Variable"
            
            If lbCond.List(n, 1) = cbReplaceText.Value Then
                'MsgBox "Found Condition." & vbCr & lbCond.List(n, 2)
                strFind = "{{" & cbFind.Value & "}}"
                
                strTemp = Replace(tbSpecial.Value, strFind, "<b>" & lbCond.List(n, 2) & "</b>")
                tbSpecial.Value = strTemp
                
                strTemp = Replace(tbSOW.Value, strFind, "<b>" & lbCond.List(n, 2) & "</b>")
                tbSOW.Value = strTemp
                
                If InStr(lbCond.List(n, 2), ">>") > 0 Then
                    vLine = Split(lbCond.List(n, 2), ">>")
                    vTemp = Split(vLine(0), "<<")
                    vVar = Split(vTemp(1), "/")
            
                    lbVariables.AddItem vVar(0)
                    If UBound(vVar) > 0 Then
                        lbVariables.List(lbVariables.ListCount - 1, 1) = Replace(vVar(1), ">>", "")
                    Else
                        lbVariables.List(lbVariables.ListCount - 1, 1) = "<Empty>"
                    End If
                End If
            End If
        End If
    Next n
    
    lbVariables.RemoveItem i
    
    cbFind.Clear
    For j = 0 To lbVariables.ListCount - 1
        cbFind.AddItem lbVariables.List(j, 0)
    Next j
    cbFind.Value = ""
    
    cbReplaceText.Clear
    cbReplaceText.Value = ""
End Sub

Private Sub cbUpdate_Click()
    'Dim objSS As AcadSelectionSet
    'Dim objSOW As AcadBlockReference
    'Dim vAttList As Variant
    'Dim filterType, filterValue As Variant
    'Dim grpCode(0) As Integer
    'Dim grpValue(0) As Variant
    
    'GoTo Skip_Block

'    grpCode(0) = 2
'    grpValue(0) = "scope of work"
'    filterType = grpCode
'    filterValue = grpValue
'
'    On Error Resume Next
'    Err = 0
'
'    Set objSS = ThisDrawing.SelectionSets.Add("objSS")
'    If Not Err = 0 Then
'        Set objSS = ThisDrawing.SelectionSets.Item("objSS")
'        Err = 0
'    End If
'
'    objSS.Select acSelectionSetAll, , , filterType, filterValue
'    If objSS.count < 1 Then GoTo Exit_Sub
'
'    For Each objBlock In objSS
'        vAttList = objBlock.GetAttributes
'
'        vAttList(0).TextString = tbNumber.Value
'        vAttList(1).TextString = tbTitle.Value
'        vAttList(2).TextString = cbJobType.Value & "^" & tbDescription.Value
'        vAttList(3).TextString = tbStart.Value
'        vAttList(4).TextString = tbEnd.Value
'        vAttList(5).TextString = tbWirecenter.Value
'        vAttList(6).TextString = cbStructure.Value
'        vAttList(7).TextString = cbPlanner.Value
'        vAttList(8).TextString = tbDate.Value
'        vAttList(9).TextString = tbReferences.Value
'        vAttList(10).TextString = tbSpecial.Value
'        vAttList(11).TextString = tbSOW.Value
'        vAttList(12).TextString = tbRevision.Value
'    Next objBlock
    
'Skip_Block:
    
    'Dim strFileName As String
    'Dim strDWGName As String
    'Dim strPath As String
    'Dim vTemp As Variant
    
    'strPath = ThisDrawing.Path & "\"
    'vTemp = Split(ThisDrawing.Name, " ")
    'strDWGName = Left(ThisDrawing.Name, 9)
    'strFileName = strPath & vTemp(0) & " Scope of Work.txt"

    'Open strFileName For Output As #1
    
    'If tbNumber.Value = "" Then tbNumber.Value = "<Blank>"
    'Print #1, "Job Number:" & vbTab & tbNumber.Value
    'If tbTitle.Value = "" Then tbTitle.Value = "<Blank>"
    'Print #1, "Job Title:" & vbTab & tbTitle.Value
    'If cbJobType.Value = "" Then cbJobType.Value = "<Blank>"
    'Print #1, "Job Type:" & vbTab & cbJobType.Value
    'If tbDescription.Value = "" Then tbDescription.Value = "<Blank>"
    'Print #1, "Job Description:" & vbTab & tbDescription.Value & vbCr
    'If tbWirecenter.Value = "" Then tbWirecenter.Value = "<Blank>"
    'Print #1, "Wirecenter:" & vbTab & tbWirecenter.Value
    'If cbStructure.Value = "" Then cbStructure.Value = "<Blank>"
    'Print #1, "Structure:" & vbTab & cbStructure.Value & vbCr
    'If tbStart.Value = "" Then tbStart.Value = "<Blank>"
    'Print #1, "Handoff:" & vbTab & tbStart.Value
    'If tbEnd.Value = "" Then tbEnd.Value = "<Blank>"
    'Print #1, "Due Date:" & vbTab & tbEnd.Value & vbCr
    'Print #1, "Planner:" & vbTab & cbPlanner.Value
    'Print #1, "Approved:" & vbTab & tbDate.Value & vbCr
    'Print #1, "References:" & vbCr & tbReferences.Value & vbCr
    'Print #1, "Notes:" & vbCr & tbSpecial.Value & vbCr
    'Print #1, "Scope of Work:" & vbCr & tbSOW.Value & vbCr
    'Print #1, "Revisions:" & vbCr & tbRevision.Value & vbCr
    
    'Close #1
    
    Call CreateHTML
    
    If tbEnd.Value = "<Blank>" Then
        Frame1.ForeColor = &HFF
        Frame1.BorderColor = &HFF
        Label7.ForeColor = &HFF
    Else
        'Exit Sub
        If CDate(tbEnd.Value) <= Date Then
            tbEnd.ForeColor = &HFF
            Frame1.ForeColor = &HFF
            Frame1.BorderColor = &HFF
            Label7.ForeColor = &HFF
        Else
            tbEnd.ForeColor = &H80000012
            Frame1.ForeColor = &H80000012
            Frame1.BorderColor = &H80000012
            Label7.ForeColor = &H80000012
        End If
    End If
    
    'If tbEnd.Value = "" Then
        'Frame1.ForeColor = &HFF
        'Frame1.BorderColor = &HFF
        'Label7.ForeColor = &HFF
    'End If
    
    If tbNumber.Value = "" Then
        Label1.ForeColor = &HFF
    Else
        Label1.ForeColor = &H80000012
    End If
    
    If tbSOW.Value = "" Then
        Label9.ForeColor = &HFF
    Else
        Label9.ForeColor = &H80000012
    End If
Exit_Sub:
    MsgBox "Done"
End Sub

Private Sub Label1_Click()
    Dim strTemp As String
    Dim vTemp As Variant
    
    strTemp = Replace(UCase(ThisDrawing.Name), ".DWG", "")
    vTemp = Split(strTemp, " ")
    tbNumber.Value = vTemp(0)
    
    If UBound(vTemp) = 0 Then
        tbTitle.Value = ""
    Else
        strTemp = ""
        For i = 1 To UBound(vTemp)
            If strTemp = "" Then
                strTemp = vTemp(i)
            Else
                strTemp = strTemp & " " & vTemp(i)
            End If
        Next i
        tbTitle.Value = strTemp
    End If
End Sub

Private Sub Label16_Click()
    tbDate.Value = Date
End Sub

Private Sub LabelPan_Click()
    Dim entPole As AcadObject
    Dim basePnt As Variant
    
    Me.Hide
  On Error Resume Next
    
    ThisDrawing.Utility.GetEntity entPole, basePnt, "Left Click to Exit: "
    
    Me.show
End Sub

Private Sub UserForm_Initialize()
    lbVariables.ColumnCount = 2
    lbVariables.ColumnWidths = "144;144"
    
    lbCond.ColumnCount = 3
    lbCond.ColumnWidths = "84;84;120"
    
    cbStructure.AddItem ""
    cbStructure.AddItem "96 FDH"
    cbStructure.AddItem "144 FDH"
    cbStructure.AddItem "288 FDH"
    cbStructure.AddItem "432 FDH"
    cbStructure.AddItem "576 FDH"
    cbStructure.AddItem "CO Panel"
    cbStructure.AddItem "RST Panel"
    
    cbF1.AddItem ""
    cbF1.AddItem "NA"
    cbF1.AddItem "Unknown"
    
    cbF2.AddItem ""
    cbF2.AddItem "NA"
    cbF2.AddItem "Unknown"
    
    'cbJobType.AddItem "DSPLIT"
    'cbJobType.AddItem "FDH-ALL"
    'cbJobType.AddItem "FDH-F1"
    'cbJobType.AddItem "FDH-F2"
    'cbJobType.AddItem "TRUNK"
    'cbJobType.AddItem "BUS"
    
    cbPlanner.AddItem "Adam Kemper"
    cbPlanner.AddItem "Byron Auer"
    cbPlanner.AddItem "Franklin Angulo"
    cbPlanner.AddItem "Matt Snyder"
    
    Call RetreiveData
    If tbNumber.Value = "<Blank>" Or tbNumber.Value = "" Then GoTo Skip_Block_Entry
    
'    Dim objSS As AcadSelectionSet
'    Dim objSOW As AcadBlockReference
'    Dim vAttList As Variant
'    Dim filterType, filterValue As Variant
'    Dim grpCode(0) As Integer
'    Dim grpValue(0) As Variant
'
'    grpCode(0) = 2
'    grpValue(0) = "scope of work"
'    filterType = grpCode
'    filterValue = grpValue
'
'    On Error Resume Next
'    Err = 0
'
'    Set objSS = ThisDrawing.SelectionSets.Add("objSS")
'    If Not Err = 0 Then
'        Set objSS = ThisDrawing.SelectionSets.Item("objSS")
'        Err = 0
'    End If
'
'    objSS.Select acSelectionSetAll, , , filterType, filterValue
'
'    If objSS.count < 1 Then
'        tbDescription.Value = "No Scope of Work found"
'        Exit Sub
'    End If
'
'    Dim vLine, vItem As Variant
'
'    For Each objBlock In objSS
'        vAttList = objBlock.GetAttributes
'
'        vLine = Split(vAttList(2).TextString, "^")
'        If UBound(vLine) > 0 Then
'            tbNumber.Value = vAttList(0).TextString
'            tbTitle.Value = vAttList(1).TextString
'
'            cbJobType.Value = vLine(0)
'            tbDescription.Value = vLine(1)
'            tbStart.Value = vAttList(3).TextString
'            tbEnd.Value = vAttList(4).TextString
'            tbWirecenter.Value = vAttList(5).TextString
'            cbStructure.Value = vAttList(6).TextString
'            cbPlanner.Value = vAttList(7).TextString
'            tbDate.Value = vAttList(8).TextString
'            tbReferences.Value = vAttList(9).TextString
'            tbSpecial.Value = vAttList(10).TextString
'            tbSOW.Value = vAttList(11).TextString
'            tbRevision.Value = vAttList(12).TextString
'        Else
'            tbNumber.Value = vAttList(0).TextString
'            tbTitle.Value = vAttList(1).TextString
'            tbDescription.Value = vAttList(2).TextString
'            tbStart.Value = vAttList(3).TextString
'            tbEnd.Value = vAttList(4).TextString
'            tbWirecenter.Value = vAttList(5).TextString
'            cbStructure.Value = vAttList(6).TextString
'            cbF1.Value = vAttList(7).TextString
'            cbF2.Value = vAttList(8).TextString
'            tbReferences.Value = vAttList(9).TextString
'            tbSpecial.Value = vAttList(10).TextString
'            tbSOW.Value = vAttList(11).TextString
'            tbRevision.Value = vAttList(12).TextString
'        End If
'
'    Next objBlock
    
    If tbEnd.Value = "ASAP" Then GoTo Skip_Block_Entry
    
    If tbEnd.Value = "<Blank>" Then
        Frame1.ForeColor = &HFF
        Frame1.BorderColor = &HFF
        Label7.ForeColor = &HFF
    Else
        If CDate(tbEnd.Value) <= Date Then
            tbEnd.ForeColor = &HFF
            Frame1.ForeColor = &HFF
            Frame1.BorderColor = &HFF
            Label7.ForeColor = &HFF
        End If
    End If
    
    If tbNumber.Value = "" Then
        Label1.ForeColor = &HFF
    Else
        Label1.ForeColor = &H80000012
    End If
    
    If tbSOW.Value = "" Then
        Label9.ForeColor = &HFF
    Else
        Label9.ForeColor = &H80000012
    End If
    
Skip_Block_Entry:
    
    Dim strPath, strFile As String
    Dim vTemp As Variant
    
    strTFolder = ""
    
    strPath = ThisDrawing.Path
    'MsgBox strPath
    vTemp = Split(strPath, "Dropbox")
    If UBound(vTemp) < 1 Then
        Exit Sub
    End If
    
    strTFolder = vTemp(0) & "\Dropbox\UNITED COMMUNICATIONS JOB INFORMATION\1-JOBS\PLANNING\SCOPE TEMPLATES\*.*"
    
    strFile = Dir$(strTFolder)
    
    Do While strFile <> ""
        If InStr(strFile, ".swt") Then
            cbJobType.AddItem Replace(strFile, ".swt", "")
        End If
        strFile = Dir$
    Loop
    
    Call GetVariableList
End Sub

Private Sub CreateHTML()
    Dim strFileName As String
    Dim strDWGName As String
    Dim strPath As String
    Dim vTemp As Variant
    Dim vLine As Variant
    
    On Error Resume Next
    
    strPath = ThisDrawing.Path & "\"
    vTemp = Split(ThisDrawing.Name, " ")
    'strDWGName = Left(ThisDrawing.Name, 9)
    'strDWGName = vTemp(0)
    strFileName = strPath & vTemp(0) & " Scope of Work.htm"

    Open strFileName For Output As #1
    Err = 0
    
    Print #1, "<!--"
    Print #1, ">" & vbTab & "Number" & vbTab & tbNumber.Value
    Print #1, ">" & vbTab & "Title" & vbTab & tbTitle.Value
    Print #1, ">" & vbTab & "Desc" & vbTab & tbDescription.Value
    Print #1, ">" & vbTab & "WC" & vbTab & tbWirecenter.Value
    Print #1, ">" & vbTab & "Type" & vbTab & cbJobType.Value
    Print #1, ">" & vbTab & "Start" & vbTab & tbStart.Value
    Print #1, ">" & vbTab & "End" & vbTab & tbEnd.Value
    Print #1, ">" & vbTab & "Planner" & vbTab & cbPlanner.Value
    Print #1, ">" & vbTab & "Approved" & vbTab & tbDate.Value
    Print #1, ">" & vbTab & "Reference"
    Print #1, tbReferences.Value
    Print #1, ">" & vbTab & "Notes"
    Print #1, tbSpecial.Value
    Print #1, ">" & vbTab & "Scope"
    Print #1, tbSOW.Value
    Print #1, ">" & vbTab & "Revisions"
    Print #1, tbRevision.Value
    Print #1, "-->"
    If Not Err = 0 Then
        MsgBox "Error saving Data!"
        Close #1
        Exit Sub
    End If
    
    Print #1, "<!doctype html>"
    Print #1, "<html><head><style>"
    Print #1, "h2 {text-align: center;}"
    Print #1, ".border {border: 1px solid black;}"
    Print #1, ".borderAll {border: 1px solid black; width: 1024px;}"
    Print #1, ".borderLeft {border-left: 1px solid black;}"
    Print #1, "th, td {padding: 4px;}"
    Print #1, "</style></head>"
    
    Print #1, "<body><h2>" & tbNumber.Value & " SCOPE OF WORK</h2>"
    
    Print #1, "<table class=""borderAll""><tr>"
    Print #1, "<td>Job Number </td><td><b>" & tbNumber.Value & "</b></td></tr>"
    Print #1, "<td>Job Title </td><td><b>" & tbTitle.Value & "</b></td></tr>"
    Print #1, "<td>Job Type </td><td><b>" & cbJobType.Value & "</b></td></tr>"
    Print #1, "<td>Job Description </td><td><b>" & tbDescription.Value & "</b></td></tr>"
    Print #1, "<td>Wirecenter </td><td><b>" & tbWirecenter.Value & "</b></td></tr>"
    Print #1, "</table><br>"
    
    Print #1, "<table class=""borderAll""><tr>"
    Print #1, "<td>Handoff</td><td><b>" & tbStart.Value & "</b></td>"
    Print #1, "<td class="" borderLeft"">Planner </td><td><b>" & cbPlanner.Value & "</b></td></tr>"
    Print #1, "<tr><td>Due Date</td><td><b>" & tbEnd.Value & "</b></td>"
    Print #1, "<td class=""borderLeft"">Approved </td><td><b>" & tbDate.Value & "</b></td></tr>"
    Print #1, "</table><br>"
    
    Print #1, "<table class=""borderAll""><tr>"
    Print #1, "<th class=""border"">Reference Jobs</th></tr>"
    Print #1, "<tr><td>" & Replace(tbReferences.Value, vbCr, "<br>") & "</td></tr>"
    Print #1, "</table><br>"
    Print #1, "<table class=""borderAll""><tr>"
    Print #1, "<th class=""border"">Notes</th></tr>"
    Print #1, "<tr><td>" '& Replace(tbSpecial.Value, vbCr, "<br>") & "</td></tr>"
    'Print #1, "<tr><td>" & Replace(tbSpecial.Value, vbCr, "<br>") & "</td></tr>"
    vLine = Split(tbSpecial.Value, vbCr)
    For i = 0 To UBound(vLine)
        vLine(i) = Replace(vLine(i), vbLf, "")
        If vLine(i) = "<table>" Then
            Print #1, vLine(i)
            i = i + 1
            vLine(i) = Replace(vLine(i), vbLf, "")
            While Not Left(vLine(i), 3) = "</t"
                vLine(i) = Replace(vLine(i), "<tr>", "<tr><td>")
                vLine(i) = Replace(vLine(i), " == ", "</td><td>")
                vLine(i) = Replace(vLine(i), " = ", "</td><td class=""border"">")
                vLine(i) = vLine(i) & "</td></tr>"
                Print #1, vLine(i)
            
                i = i + 1
                vLine(i) = Replace(vLine(i), vbLf, "")
                'MsgBox "Left(vLine(i), 4)= " & Left(vLine(i), 4)
            Wend
            Print #1, vLine(i) & "<br>"
            i = i + 1
        End If
        Print #1, vLine(i) & "<br>"
    Next i
    Print #1, "</td></tr>"
    Print #1, "</table><br>"
    Print #1, "<table class=""borderAll""><tr>"
    
    Print #1, "<th class=""border"">Scope of Work</th></tr>"
    Print #1, "<tr><td>" '& Replace(tbSOW.Value, vbCr, "<br>") & "</td></tr>"
    vLine = Split(tbSOW.Value, vbCr)
    For i = 0 To UBound(vLine)
        vLine(i) = Replace(vLine(i), vbLf, "")
        If vLine(i) = "<table>" Then
            Print #1, vLine(i)
            i = i + 1
            vLine(i) = Replace(vLine(i), vbLf, "")
            While Not Left(vLine(i), 3) = "</t"
                vLine(i) = Replace(vLine(i), "<tr>", "<tr><td>")
                vLine(i) = Replace(vLine(i), " = ", "</td><td class=""border"">")
                vLine(i) = vLine(i) & "</td></tr>"
                Print #1, vLine(i)
            
                i = i + 1
                vLine(i) = Replace(vLine(i), vbLf, "")
                'MsgBox "Left(vLine(i), 4)= " & Left(vLine(i), 4)
            Wend
            Print #1, vLine(i) & "<br>"
            i = i + 1
        End If
        Print #1, vLine(i) & "<br>"
    Next i
    Print #1, "</td></tr>"
    Print #1, "</table><br>"
    
    Print #1, "<table class=""borderAll""><tr>"
    Print #1, "<th class=""border"">Revisions</th></tr>"
    Print #1, "<tr><td>" & Replace(tbRevision.Value, vbCr, "<br>") & "</td></tr>"
    Print #1, "</table></body></html>"
    Print #1, ""
    If Not Err = 0 Then
        MsgBox "Error creating Scope!"
    End If
    
    Close #1
End Sub

Private Sub RetreiveData()
    Dim strFileName As String
    Dim strPath As String
    Dim strLine As String
    Dim vTemp As Variant
    Dim vLine As Variant
    Dim fName As String
    Dim iCount As Integer
    
    'On Error Resume Next
    
    iCount = 0
    tbReferences.Value = ""
    tbSpecial.Value = ""
    tbSOW.Value = ""
    tbRevision.Value = ""
    
    strPath = ThisDrawing.Path & "\"
    vTemp = Split(ThisDrawing.Name, " ")
    strFileName = strPath & vTemp(0) & " Scope of Work.htm"
    
    'strFileName = LabelFileName.Caption & cbFileList.Value
    
    fName = Dir(strFileName)
    If fName = "" Then
        MsgBox "No Scope of Work File found."
        'Call GetDataFromBlock
        Exit Sub
    End If
    
    Open strFileName For Input As #2
    
    While Not EOF(2)
        Line Input #2, strLine
        vLine = Split(strLine, vbTab)
        
        If vLine(0) = ">" Then
Check_vLine1:
            'MsgBox strLine
            If UBound(vLine) > 1 Then
                If vLine(2) = "" Then vLine(2) = "<Blank>"
            End If
            
            Select Case vLine(1)
                Case "Number"
                    tbNumber.Value = vLine(2)
                Case "Title"
                    tbTitle.Value = vLine(2)
                Case "Desc"
                    tbDescription.Value = vLine(2)
                Case "WC"
                    tbWirecenter.Value = vLine(2)
                Case "Type"
                    cbJobType.Value = vLine(2)
                Case "Start"
                    tbStart.Value = vLine(2)
                Case "End"
                    tbEnd.Value = vLine(2)
                Case "Planner"
                    cbPlanner.Value = vLine(2)
                Case "Approved"
                    tbDate.Value = vLine(2)
                Case "Reference"
Continue_Ref:
                    Line Input #2, strLine
                    If strLine = "" Then GoTo Continue_Ref
                    
                    vLine = Split(strLine, vbTab)
                    If vLine(0) = ">" Then GoTo Check_vLine1
        
                    If tbReferences.Value = "" Then
                        tbReferences.Value = strLine
                    Else
                        tbReferences.Value = tbReferences.Value & vbCr & strLine
                    End If
                    
                    GoTo Continue_Ref
                Case "Notes"
Continue_Notes:
                    Line Input #2, strLine
                    If strLine = "" Then GoTo Continue_Notes
                    
                    vLine = Split(strLine, vbTab)
                    If vLine(0) = ">" Then GoTo Check_vLine1
                    
                    If tbSpecial.Value = "" Then
                        tbSpecial.Value = strLine
                    Else
                        tbSpecial.Value = tbSpecial.Value & vbCr & strLine
                    End If
                    
                    GoTo Continue_Notes
                Case "Scope"
Continue_SOW:
                    Line Input #2, strLine
                    If strLine = "" Then GoTo Continue_SOW
                    
                    vLine = Split(strLine, vbTab)
                    If vLine(0) = ">" Then GoTo Check_vLine1
                    
                    If tbSOW.Value = "" Then
                        tbSOW.Value = strLine
                    Else
                        tbSOW.Value = tbSOW.Value & vbCr & strLine
                    End If
                        
                    GoTo Continue_SOW
                Case "Revisions"
Continue_Revisions:
                    Line Input #2, strLine
                    If strLine = "" Then GoTo Continue_Revisions
                    If strLine = "-->" Then GoTo Exit_Sub
                        
                    vLine = Split(strLine, vbTab)
                    
                    If vLine(0) = ">" Then GoTo Check_vLine1
                    
                    If tbRevision.Value = "" Then
                        tbRevision.Value = strLine
                    Else
                        tbRevision.Value = tbRevision.Value & vbCr & strLine
                    End If
                        
                    GoTo Continue_Revisions
                Case "-->"
                    GoTo Exit_Sub
            End Select
        End If
    Wend
    
Exit_Sub:
    Close #2
End Sub

Private Sub GetDataFromBlock()
    Dim objSS As AcadSelectionSet
    Dim objSOW As AcadBlockReference
    Dim vAttList As Variant
    Dim filterType, filterValue As Variant
    Dim grpCode(0) As Integer
    Dim grpValue(0) As Variant
    Dim strTemp As String

    grpCode(0) = 2
    grpValue(0) = "scope of work"
    filterType = grpCode
    filterValue = grpValue

    On Error Resume Next
    Err = 0

    Set objSS = ThisDrawing.SelectionSets.Add("objSS")
    If Not Err = 0 Then
        Set objSS = ThisDrawing.SelectionSets.Item("objSS")
        Err = 0
    End If

    objSS.Select acSelectionSetAll, , , filterType, filterValue

    If objSS.count < 1 Then
        MsgBox "No Scope of Work Block found"
        Exit Sub
    End If

    If objSS.count < 1 Then Exit Sub

    Dim vLine, vItem As Variant

    For Each objBlock In objSS
        vAttList = objBlock.GetAttributes

        If vAttList(2).TextString = "" Then Exit Sub
        
        For k = 0 To 12
            If vAttList(k).TextString = "" Then vAttList(k).TextString = "<Empty>"
        Next k
        
        objBlock.Update

        vLine = Split(vAttList(2).TextString, "^")
        
        If UBound(vLine) > 0 Then
        strTemp = vAttList(0).TextString
        MsgBox strTemp
            tbNumber.Value = strTemp    'vAttList(0).TextString
        Exit Sub
            tbTitle.Value = vAttList(1).TextString

            cbJobType.Value = vLine(0)
            tbDescription.Value = vLine(1)
            tbStart.Value = vAttList(3).TextString
            tbEnd.Value = vAttList(4).TextString
            tbWirecenter.Value = vAttList(5).TextString
            cbStructure.Value = vAttList(6).TextString
            cbPlanner.Value = vAttList(7).TextString
            tbDate.Value = vAttList(8).TextString
            tbReferences.Value = vAttList(9).TextString
            tbSpecial.Value = vAttList(10).TextString
            tbSOW.Value = vAttList(11).TextString
            tbRevision.Value = vAttList(12).TextString
        Else
            tbNumber.Value = vAttList(0).TextString
            tbTitle.Value = vAttList(1).TextString
            tbDescription.Value = vAttList(2).TextString
            tbStart.Value = vAttList(3).TextString
            tbEnd.Value = vAttList(4).TextString
            tbWirecenter.Value = vAttList(5).TextString
            cbStructure.Value = vAttList(6).TextString
            cbF1.Value = vAttList(7).TextString
            cbF2.Value = vAttList(8).TextString
            tbReferences.Value = vAttList(9).TextString
            tbSpecial.Value = vAttList(10).TextString
            tbSOW.Value = vAttList(11).TextString
            tbRevision.Value = vAttList(12).TextString
        End If

    Next objBlock
End Sub

Private Sub GetVariableList()
    If cbJobType.Value = "" Then Exit Sub
    
    Dim vText, vLine, vTemp As Variant
    Dim vVar, vCond As Variant
    Dim strLine As String
    
    lbVariables.Clear
    lbCond.Clear
    
    strLine = Replace(tbSpecial.Value, vbLf, "")
    vText = Split(strLine, vbCr)
    
    For n = 0 To UBound(vText)
        If InStr(vText(n), ">>") > 0 And Not iStatus = 3 Then
            vLine = Split(vText(n), ">>")
            For j = 0 To UBound(vLine) - 1
            
                vTemp = Split(vLine(j), "<<")
                vVar = Split(vTemp(1), "/")
            
                'If lbVariables.ListCount < 0 Then
                    For i = 0 To lbVariables.ListCount - 1
                        If lbVariables.List(i, 0) = vVar(0) Then GoTo Skip_Adding_Var
                    Next i
                'End If
            
                lbVariables.AddItem vVar(0)
                If UBound(vVar) > 0 Then
                    lbVariables.List(lbVariables.ListCount - 1, 1) = Replace(vVar(1), ">>", "")
                Else
                    lbVariables.List(lbVariables.ListCount - 1, 1) = "<Empty>"
                End If
        
Skip_Adding_Var:
            Next j
            
            If UBound(vLine) > 2 Then
                For i = 1 To UBound(vLine) - 1
                    vTemp = Split(vLine(i), "<<")
                    vVar = Split(vTemp(1), "/")
            
                    lbVariables.AddItem vVar(0)
                    If UBound(vVar) > 0 Then
                        lbVariables.List(lbVariables.ListCount - 1, 1) = Replace(vVar(1), ">>", "")
                    Else
                        lbVariables.List(lbVariables.ListCount - 1, 1) = "<Empty>"
                    End If
Skip_Adding_This:
                    'cbFind.AddItem "<<" & vTemp(1) & ">>"
                Next i
            End If
        End If
    Next n
    
    For i = 0 To lbVariables.ListCount - 1
        cbFind.AddItem lbVariables.List(i, 0)
    Next i
End Sub

Attribute VB_Name = "SelectAttach"
Attribute VB_Base = "0{491A490B-98C7-430E-932F-AFE4D88AA339}{C8EF0A12-0FFB-4C9E-94F4-A90E8E576F5F}"
Attribute VB_GlobalNameSpace = False
Attribute VB_Creatable = False
Attribute VB_PredeclaredId = True
Attribute VB_Exposed = False
Attribute VB_TemplateDerived = False
Attribute VB_Customizable = False
Private Sub lbAttach_DblClick(ByVal Cancel As MSForms.ReturnBoolean)
    Me.Hide
End Sub

Private Sub lbAttach_KeyDown(ByVal KeyCode As MSForms.ReturnInteger, ByVal Shift As Integer)
    Select Case KeyCode
        Case vbKeyReturn
            Me.Hide
    End Select
End Sub

Private Sub UserForm_Initialize()
    lbAttach.ColumnCount = 3
    lbAttach.ColumnWidths = "72;48;48"
End Sub

Attribute VB_Name = "SelectCable"
Attribute VB_Base = "0{2965F7A3-60A8-4540-AF33-2C2F7E16D619}{ACA9B03F-BF2D-495B-9681-5AE82A84287B}"
Attribute VB_GlobalNameSpace = False
Attribute VB_Creatable = False
Attribute VB_PredeclaredId = True
Attribute VB_Exposed = False
Attribute VB_TemplateDerived = False
Attribute VB_Customizable = False
Private Sub cbNewCable_Click()
    lbCable.Clear
    
    Me.Hide
End Sub

Private Sub lbCable_DblClick(ByVal Cancel As MSForms.ReturnBoolean)
    Me.Hide
End Sub

Attribute VB_Name = "SpidaAddPNumber"
Attribute VB_Base = "0{ED0300FB-ADFC-45DB-A156-F34EDC6ADFA5}{118619DC-6D6E-4977-981B-23CE6962770B}"
Attribute VB_GlobalNameSpace = False
Attribute VB_Creatable = False
Attribute VB_PredeclaredId = True
Attribute VB_Exposed = False
Attribute VB_TemplateDerived = False
Attribute VB_Customizable = False
Private Sub cbFindFID_Click()
    If tbFID.Value = "" Then Exit Sub
    If lbPoles.ListCount < 1 Then Exit Sub
    
    Dim strFID As String
    
    strFID = tbFID.Value
    For i = 0 To lbPoles.ListCount - 1
        If strFID = lbPoles.List(i, 2) Then
            lbPoles.Selected(i) = True
            lbPoles.ListIndex = i
            tbPoleNumber.Value = lbPoles.List(i, 3)
            
            GoTo Found_FID
        End If
    Next i
    
Found_FID:
    
End Sub

Private Sub cbGetData_Click()
    Dim filterType, filterValue As Variant
    Dim grpCode(0) As Integer
    Dim grpValue(0) As Variant
    
    Dim objEntity As AcadEntity
    Dim objLWP As AcadLWPolyline
    Dim objPoint As AcadPoint
    Dim objBlock As AcadBlockReference
    Dim vAttList As Variant
    
    Dim amap As AcadMap
    Dim ODRcs As ODRecords
    Dim ODRc As ODRecord
    Dim tbl As ODTable
    Dim tbls As ODTables
    
    Dim vReturnPnt, vCoords As Variant
    Dim dCoords() As Double
    Dim iTemp, iCounter As Integer
    
    Dim strFID, strCoords, strTest As String
    
    On Error Resume Next
    
    Set objSS = ThisDrawing.SelectionSets.Add("objSS")
    If Not Err = 0 Then
        Set objSS = ThisDrawing.SelectionSets.Item("objSS")
        objSS.Clear
        Err = 0
    End If
    
    grpCode(0) = 8
    grpValue(0) = "OHStructure"
    filterType = grpCode
    filterValue = grpValue
    
    Me.Hide
    
    ThisDrawing.Utility.GetEntity objEntity, vReturnPnt, "Select Polygon Border: "
    If Not objEntity.ObjectName = "AcDbPolyline" Then
        MsgBox "Error: Invalid Selection."
        Me.show
        Exit Sub
    End If
    
    Set objLWP = objEntity
    vCoords = objLWP.Coordinates
    
    iTemp = (UBound(vCoords) + 1) / 2 * 3 - 1
    ReDim dCoords(iTemp) As Double
    
    iCounter = 0
    For i = 0 To UBound(vCoords) Step 2
        dCoords(iCounter) = vCoords(i)
        iCounter = iCounter + 1
        dCoords(iCounter) = vCoords(i + 1)
        iCounter = iCounter + 1
        dCoords(iCounter) = 0#
        iCounter = iCounter + 1
    Next i
    
    objSS.SelectByPolygon acSelectionSetCrossingPolygon, dCoords, filterType, filterValue
    
    'MsgBox objSS.count
    
    Set amap = ThisDrawing.Application.GetInterfaceObject("AutoCADMap.Application")
    
    Set tbls = amap.Projects(ThisDrawing).ODTables
    If tbls.count > 0 Then
        For Each tbl In tbls
            If tbl.Name = "OHStructure" Then GoTo Exit_For
        Next
    End If
Exit_For:
    
    'Set ODRcs = tbl.GetODRecords
    
    For Each objEntity In objSS
        If TypeOf objEntity Is AcadPoint Then
            Set objPoint = objEntity
            strCoords = objPoint.Coordinates(1) & "," & objPoint.Coordinates(0)
            
            Set ODRcs = tbl.GetODRecords
            boolVal = ODRcs.Init(objEntity, True, False)
            Set ODRc = ODRcs.Record
            
            strFID = ODRc.Item(10).Value
            
            'MsgBox strFID
            'GoTo Exit_Sub
            
            For i = 0 To lbPoles.ListCount - 1
                If lbPoles.List(i, 2) = strFID Then
                    lbPoles.List(i, 0) = strCoords
                    lbPoles.List(i, 1) = ODRc.Item(11).Value
                    GoTo Found_FID
                End If
            Next i
Found_FID:
        End If
Next_Object:
    Next objEntity
    
    objSS.Clear
    
    grpCode(0) = 2
    grpValue(0) = "sPole"
    filterType = grpCode
    filterValue = grpValue
    
    objSS.SelectByPolygon acSelectionSetCrossingPolygon, dCoords, filterType, filterValue
    
    For Each objBlock In objSS
        strTest = objBlock.InsertionPoint(1) & "," & objBlock.InsertionPoint(0)
        
        For i = 0 To lbPoles.ListCount - 1
            If lbPoles.List(i, 0) = strTest Then
                vAttList = objBlock.GetAttributes
                lbPoles.List(i, 3) = vAttList(0).TextString
                
                GoTo Found_Block
            End If
        Next i
Found_Block:
    Next objBlock
    
Exit_Sub:
    
    objSS.Clear
    objSS.Delete
    Me.show
End Sub

Private Sub cbNextLine_Click()
    If lbPoles.ListIndex = lbPoles.ListCount - 1 Then Exit Sub
    
    Dim iIndex As Integer
    
    iIndex = lbPoles.ListIndex + 1
    lbPoles.ListIndex = iIndex
    lbPoles.Selected(iIndex) = True
    
    tbFID.Value = lbPoles.List(iIndex, 2)
    tbPoleNumber.Value = lbPoles.List(iIndex, 3)
    
    tbPoleNumber.SelStart = 0
    tbPoleNumber.SelLength = Len(tbPoleNumber.Value)
    tbPoleNumber.SetFocus
End Sub

Private Sub lbPoles_Click()
    If lbPoles.ListIndex < 0 Then Exit Sub
    
    tbFID.Value = lbPoles.List(lbPoles.ListIndex, 2)
    tbPoleNumber.Value = lbPoles.List(lbPoles.ListIndex, 3)
    
    tbPoleNumber.SelStart = 0
    tbPoleNumber.SelLength = Len(tbPoleNumber.Value)
    tbPoleNumber.SetFocus
End Sub

Private Sub tbPasted_Change()
    If tbPasted.Value = "" Then Exit Sub
    
    Dim vLine, vItem, vTemp As Variant
    Dim strLine As String
    Dim iIndex As Integer
    
    lbPoles.Clear
    
    strLine = Replace(tbPasted.Value, vbLf, "")
    vLine = Split(strLine, vbCr)
    
    For i = 0 To UBound(vLine)
        If InStr(vLine(i), ",") < 1 Then GoTo Next_line
        
        vItem = Split(vLine(i), ",")
        
        'For j = 0 To UBound(vItem)
            'vItem(j) = Replace(vItem(j), ";;", ",")
        'Next j
        
        lbPoles.AddItem "0,0"
        iIndex = lbPoles.ListCount - 1
        lbPoles.List(iIndex, 1) = ""
        lbPoles.List(iIndex, 2) = vItem(1)
        lbPoles.List(iIndex, 3) = vItem(2)
        
Next_line:
    Next i
    
    tbListCount.Value = lbPoles.ListCount
End Sub

Private Sub UserForm_Initialize()
    lbPoles.ColumnCount = 4
    lbPoles.ColumnWidths = "144;60;120;114"
End Sub

Attribute VB_Name = "TDOT"
Attribute VB_Base = "0{6D971BAD-64A2-425C-8309-1BC5B55A6621}{5200FD2B-760D-4FB1-ADD0-31C7B73D3FC5}"
Attribute VB_GlobalNameSpace = False
Attribute VB_Creatable = False
Attribute VB_PredeclaredId = True
Attribute VB_Exposed = False
Attribute VB_TemplateDerived = False
Attribute VB_Customizable = False


Private Sub cbAddSheets_Click() '<------------------------------------------------ Add Permit Layer if it doesn't exist
    Dim entPole As AcadObject
    Dim objLayer As AcadLayer
    Dim obrGSS As AcadBlockReference
    Dim obrSSInfo As AcadBlockReference
    Dim obrSSDWG1 As AcadBlockReference
    Dim attItem, attItem1, basePnt, returnPnt As Variant
    Dim vEmail As Variant
    Dim insertPnt(0 To 2) As Double
    Dim dScale As Double
    Dim iDWGNum, iNextNum As Long
    Dim str, str2 As String
    Dim strType, strLayer As String
    
    If cbDWG.Value = "" Then Exit Sub
    
    Me.Hide
  On Error Resume Next
    
    Call CreateLayer("Integrity Permits-" & cbDWG.Value)
  
    Err = 0
  
    iNextNum = 1
    iDWGNum = 1
    strType = cbDWG.Value
    
While Err = 0
    ThisDrawing.Utility.GetEntity entPole, basePnt, "Select Staking Sheet: "
    If TypeOf entPole Is AcadBlockReference Then
        Set obrGSS = entPole
    Else
        GoTo Exit_Sub
    End If
    
    If Not Err = 0 Then GoTo Exit_Sub
    If Not obrGSS.Name = "SS-11x17" Then GoTo Exit_Sub
    
    obrGSS.Layer = "Integrity Permits-" & cbDWG.Value
    attItem = obrGSS.GetAttributes
    
    Err = 0
    iDWGNum = ThisDrawing.Utility.GetInteger(vbCr & "Enter Drawing Number(" & iNextNum & "): ")
    If Not Err = 0 Then iDWGNum = iNextNum
    iNextNum = iDWGNum + 1
    
    Select Case iDWGNum
        Case Is < 10
            attItem(0).TextString = strType & " 00" & iDWGNum
        Case Is > 99
            attItem(0).TextString = strType & " " & iDWGNum
        Case Else
            attItem(0).TextString = strType & " 0" & iDWGNum
    End Select
    
    obrGSS.Update
    dScale = obrGSS.XScaleFactor
    
    lbSheets.AddItem attItem(0).TextString & vbTab & dScale & vbTab & obrGSS.Name & vbTab & obrGSS.InsertionPoint(0) & vbTab & obrGSS.InsertionPoint(1)
  
    insertPnt(0) = obrGSS.InsertionPoint(0) + 20 * dScale
    insertPnt(1) = obrGSS.InsertionPoint(1) + 20 * dScale
    insertPnt(2) = obrGSS.InsertionPoint(2)
    
    Set obrSSInfo = ThisDrawing.ModelSpace.InsertBlock(insertPnt, "ss info", dScale, dScale, dScale, 0#)
    obrSSInfo.Layer = "Integrity Permits-" & cbDWG.Value
    
    attItem = obrSSInfo.GetAttributes
    attItem(0).TextString = tbProject.Value
    attItem(1).TextString = tbWO.Value
    attItem(2).TextString = cbExchange.Value
    attItem(3).TextString = tbRST.Value
    attItem(4).TextString = cbCounty.Value
    attItem(5).TextString = tbCity.Value
    attItem(6).TextString = iDWGNum
    attItem(7).TextString = tbTotalDWG.Value
    obrSSInfo.Update
    
    If iDWGNum = 1 Then
        insertPnt(0) = obrGSS.InsertionPoint(0) + 20 * dScale
        insertPnt(1) = obrGSS.InsertionPoint(1) + 280 * dScale
        insertPnt(2) = obrGSS.InsertionPoint(2)
    
        Set obrSSDWG1 = ThisDrawing.ModelSpace.InsertBlock(insertPnt, "ss dwg1", dScale, dScale, dScale, 0#)
        obrSSDWG1.Layer = "Integrity Permits-" & cbDWG.Value
    
        attItem1 = obrSSDWG1.GetAttributes
        
        vEmail = Split(cbDesigner.Value, " ")
        If UBound(vEmail) = 1 Then
            str2 = LCase(vEmail(0)) & "." & LCase(vEmail(1)) & "@integrity-us.com"
        Else
            str2 = "NA"
        End If
        str = cbDesigner.Value & "\P" & str2 & "\P" & tbPhoneNumber.Value & "\P"
        str = str & "730 Middle Tennessee Blvd - Suite 6\PMurfreesboro, TN 37130"
        attItem1(0).TextString = str
        obrSSDWG1.Update
    End If
    Err = 0
Wend
    'layerObj.Delete
    
Exit_Sub:
    Set layerObj = ThisDrawing.Layers.Add("0")
    ThisDrawing.ActiveLayer = layerObj
    Me.show
End Sub

Private Sub PlaceSSBlock(strName As String, vInsertPnt As Variant, strLayer As String)
    Dim obrGSS As AcadBlockReference
    Dim obrSSInfo As AcadBlockReference
    Dim obrSSDWG1 As AcadBlockReference
    Dim attItem, attItem1 As Variant
    Dim vEmail, vTemp As Variant
    Dim insertPnt(0 To 2) As Double
    Dim dScale As Double
    Dim str, str2 As String
    Dim iDWG As Integer
    
  On Error Resume Next
    
    'Call CreateLayer("Integrity Permits-" & cbDWG.Value)
  
    Err = 0
    
    vTemp = Split(strName, " ")
    iDWG = CInt(vTemp(1))
    
    insertPnt(0) = vInsertPnt(0)
    insertPnt(1) = vInsertPnt(1)
    insertPnt(2) = vInsertPnt(2)
    dScale = CInt(cbScale.Value) / 100 'obrGSS.XScaleFactor
    
    If Not Err = o Then Exit Sub
    
    
    Set obrGSS = ThisDrawing.ModelSpace.InsertBlock(insertPnt, "SS-11x17", dScale, dScale, dScale, 0#)
    obrGSS.Layer = strLayer
    attItem = obrGSS.GetAttributes
    attItem(0).TextString = strName
    obrGSS.Update
    
    insertPnt(0) = obrGSS.InsertionPoint(0) + 20 * dScale
    insertPnt(1) = obrGSS.InsertionPoint(1) + 20 * dScale
    insertPnt(2) = obrGSS.InsertionPoint(2)
    
    Set obrSSInfo = ThisDrawing.ModelSpace.InsertBlock(insertPnt, "ss info", dScale, dScale, dScale, 0#)
    obrSSInfo.Layer = strLayer
    
    attItem = obrSSInfo.GetAttributes
    attItem(0).TextString = tbProject.Value
    attItem(1).TextString = tbWO.Value
    attItem(2).TextString = cbExchange.Value
    attItem(3).TextString = tbRST.Value
    attItem(4).TextString = cbCounty.Value
    attItem(5).TextString = tbCity.Value
    attItem(6).TextString = iDWG
    attItem(7).TextString = tbTotalDWG.Value
    obrSSInfo.Update
    
    If iDWG = 1 Then
        insertPnt(0) = obrGSS.InsertionPoint(0) + 20 * dScale
        insertPnt(1) = obrGSS.InsertionPoint(1) + 280 * dScale
        insertPnt(2) = obrGSS.InsertionPoint(2)
    
        Set obrSSDWG1 = ThisDrawing.ModelSpace.InsertBlock(insertPnt, "ss dwg1", dScale, dScale, dScale, 0#)
        obrSSDWG1.Layer = strLayer
    
        attItem1 = obrSSDWG1.GetAttributes
        
        vEmail = Split(cbDesigner.Value, " ")
        If UBound(vEmail) = 1 Then
            str2 = LCase(vEmail(0)) & "." & LCase(vEmail(1)) & "@integrity-us.com"
        Else
            str2 = "NA"
        End If
        str = cbDesigner.Value & "\P" & str2 & "\P" & tbPhoneNumber.Value & "\P"
        str = str & "730 Middle Tennessee Blvd - Suite 6\PMurfreesboro, TN 37130"
        attItem1(0).TextString = str
        obrSSDWG1.Update
    End If
               
        str = strName & vbTab & obrGSS.XScaleFactor
        str = str & vbTab & obrGSS.InsertionPoint(0) & vbTab & obrGSS.InsertionPoint(1)
        lbSheets.AddItem str
End Sub

Private Sub cbArray_Click()
    Dim objSSBlock As AcadBlockReference
    Dim vReturnPnt, vAttList As Variant
    Dim vSSData, vDWGNum As Variant
    Dim strLast As String
    Dim strLayer As String
    Dim str As String
    Dim dInsertPnt(0 To 2) As Double
    Dim dScale, dTest As Double
    Dim iDWG, iLastDWG, iTest As Integer
    
    If cbDWG.Value = "" Then Exit Sub
    If tbTotalDWG.Value = "" Then Exit Sub
    iLastDWG = CInt(tbTotalDWG.Value)
    
    'MsgBox lbSheets.ListCount & vbCr & lbSheets.List(0) & "--"
    'Exit Sub
    
    If lbSheets.ListCount = 1 Then
        If lbSheets.List(0) = "" Then lbSheets.Clear
    End If
    
    Me.Hide
    
    If lbSheets.ListCount < 1 Then
        Call CreateLayer("Integrity Permits-" & cbDWG.Value)
        cbDWG.AddItem cbDWG.Value
        vReturnPnt = ThisDrawing.Utility.GetPoint(, "Insertion Point of " & cbDWG.Value & ":")
        iDWG = 1
        dScale = CDbl(cbScale.Value) / 100
        dInsertPnt(0) = vReturnPnt(0)
        dInsertPnt(1) = vReturnPnt(1)
    Else
        strLast = lbSheets.List(lbSheets.ListCount - 1)
        vSSData = Split(strLast, vbTab)
        vDWGNum = Split(vSSData(0), " ")
        iDWG = CInt(vDWGNum(1)) + 1
        
        If iDWG > iLastDWG Then GoTo Exit_Sub2
        
        dScale = CDbl(vSSData(1))
        dTest = iDWG / 10
        dTest = (dTest - CInt(dTest)) * 10
        If dTest = 1 Then
            dInsertPnt(0) = CDbl(vSSData(2)) + (2000 * dScale)
            dInsertPnt(1) = CDbl(vSSData(3)) + (10800 * dScale)
        Else
            dInsertPnt(0) = CDbl(vSSData(2))
            dInsertPnt(1) = CDbl(vSSData(3)) - (1200 * dScale)
        End If
    End If
    dInsertPnt(2) = 0#
    
    If cbDWG.Value = "DWG" Then
        strLayer = "Integrity Sheets"
    Else
        strLayer = "Integrity Permits-" & cbDWG.Value
    End If
    
    For i = iDWG To iLastDWG
        strLast = cbDWG.Value
        Select Case i
            Case Is < 10
                strLast = strLast & " 00" & i
            Case Is > 99
                strLast = strLast & " " & i
            Case Else
                strLast = strLast & " 0" & i
        End Select
        
        Call PlaceSSBlock(strLast, dInsertPnt, strLayer)
         
        'Set objSSBlock = ThisDrawing.ModelSpace.InsertBlock(dInsertPnt, "SS-11x17", dScale, dScale, dScale, 0#)
        'objSSBlock.Layer = strLayer
        
        'vAttList = objSSBlock.GetAttributes
        
        
        'vAttList(0).TextString = strLast
        'objSSBlock.Update
        
        dTest = i / 10
        dTest = (dTest - CInt(dTest)) * 10
        'MsgBox dTest
        If dTest = 0 Then
            dInsertPnt(0) = dInsertPnt(0) + (2000 * dScale)
            dInsertPnt(1) = dInsertPnt(1) + (10800 * dScale)
        Else
            dInsertPnt(1) = dInsertPnt(1) - (1200 * dScale)
        End If
    Next i
    
    Call SortLBItems
Exit_Sub2:
    Call UpdateAllDWGs
    Me.show
End Sub

Private Sub cbCreateDWG_Click()
    Me.Hide
        Load CreateTDOT
            CreateTDOT.show
        Unload CreateTDOT
    Me.show
    
    Exit Sub
    
    
    
    Dim objSS4 As AcadSelectionSet
    Dim objEntity As AcadEntity
    Dim objBlock As AcadBlockReference
    Dim returnPnt As Variant
    Dim dCoords(0 To 8) As Double
    Dim dStartPnt(0 To 2) As Double
    Dim dEndPnt(0 To 2) As Double
    Dim dLL(0 To 2) As Double
    Dim dUR(0 To 2) As Double
    Dim dTo(0 To 2) As Double
    Dim dScale As Double
    Dim filterType, filterValue As Variant
    Dim grpCode(0) As Integer
    Dim grpValue(0) As Variant
    Dim strCommand As String
    
    'If cbDWG.Value = "DWG" Then Exit Sub
    
  On Error Resume Next
    
    Me.Hide
    
    ThisDrawing.Utility.GetEntity objEntity, returnPnt, "Select DWG: "
    
    If TypeOf objEntity Is AcadBlockReference Then
        Set objBlock = objEntity
        If Not objBlock.Name = "SS-11x17" Then
            MsgBox "Not a valid DWG."
            Me.show
            Exit Sub
        End If
        
        Set obrBlock = objEntity
        dCoords(0) = objBlock.InsertionPoint(0)
        dCoords(1) = objBlock.InsertionPoint(1)
        dCoords(2) = objBlock.InsertionPoint(2)
        'dLL(0) = objBlock.InsertionPoint(0)
        'dLL(1) = objBlock.InsertionPoint(1)
        'dLL(2) = objBlock.InsertionPoint(2)
        
        dScale = objBlock.XScaleFactor
        
        dCoords(3) = dCoords(0) + (1652 * dScale)
        dCoords(4) = dCoords(1) + (1052 * dScale)
        dCoords(5) = 0#
        'dUR(0) = dStartPnt(0) + (1652 * dScale)
        'dUR(1) = dStartPnt(1) + (1052 * dScale)
        'dUR(2) = 0#
    Else
        MsgBox "Not a valid DWG."
        Exit Sub
    End If
    
    ThisDrawing.Utility.GetEntity objEntity, returnPnt, "Select TDOT: "
    If TypeOf objEntity Is AcadBlockReference Then
        Set objBlock = objEntity
        If Not objBlock.Name = "SS-11x17" Then
            MsgBox "Not a valid DWG."
            Me.show
            Exit Sub
        End If
        
        Set obrBlock = objEntity
        dCoords(6) = objBlock.InsertionPoint(0)
        dCoords(7) = objBlock.InsertionPoint(1)
        dCoords(8) = objBlock.InsertionPoint(2)
        'dTO(0) = objBlock.InsertionPoint(0)
        'dTO(1) = objBlock.InsertionPoint(1)
        'dTO(2) = objBlock.InsertionPoint(2)
    Else
        MsgBox "Not a valid Permit."
        Exit Sub
    End If
    
    If Not Err = 0 Then
        Me.show
        Exit Sub
    End If
    
'    grpCode(0) = 8
'    grpValue(0) = strLayer  '"Integrity Roads-EOP"
'    filterType = grpCode
'    filterValue = grpValue
    
'    Set objSS4 = ThisDrawing.SelectionSets.Add("objSS3")
'    objSS4.Select acSelectionSetWindow, dLL, dUR, filterType, filterValue
    
'    strCommand = "COPY" & vbCr & "P" & vbCr & vbCr
'    strCommand = strCommand & dLL(0) & "," & dLL(1) & ",0" & vbCr
'    strCommand = strCommand & dTO(0) & "," & dTO(1) & ",0" & vbCr & vbCr
    
'    ThisDrawing.SendCommand strCommand
    
'    objSS4.Clear
'    objSS4.Delete
    
    Call CopyDWGtoPermit(dCoords, "Integrity Roads-EOP,Integrity Roads-Clearance,Roads_MText")
    Call CopyDWGtoPermit(dCoords, "Integrity Poles-Others,Integrity Poles-Power,Integrity Poles-UTC")
    Call CopyDWGtoPermit(dCoords, "Integrity Cable,Integrity Cable-Aerial,Integrity Cable-Aerial Text")
    Call CopyDWGtoPermit(dCoords, "Parcels,Integrity Cable-Buried,Integrity Cable-Buried Text")
    Call CopyDWGtoPermit(dCoords, "Integrity Building,Integrity Business,Integrity Building Misc")
    Call CopyDWGtoPermit(dCoords, "Integrity Building-BUS,Integrity Building-SCH,Integrity Building-CHU")
    Call CopyDWGtoPermit(dCoords, "Integrity Building-RES,Integrity Building-TRL,Integrity Building-MDU")
    'Call CopyDWGtoPermit(dCoords, "Integrity Roads-Clearance")
    'Call CopyDWGtoPermit(dCoords, "Roads_MText")
    'Call CopyDWGtoPermit(dCoords, "Integrity Poles-Power")
    'Call CopyDWGtoPermit(dCoords, "Integrity Cable-Aerial")
    'Call CopyDWGtoPermit(dCoords, "Integrity Cable-Aerial Text")
    'Call CopyDWGtoPermit(dCoords, "Integrity Cable-Buried")
    'Call CopyDWGtoPermit(dCoords, "Integrity Cable-Buried Text")
    'Call CopyDWGtoPermit(dCoords, "Integrity Building-SCH")
    'Call CopyDWGtoPermit(dCoords, "Integrity Building-TRL")
    'Call CopyDWGtoPermit(dCoords, "Integrity Building-CHU")
    'Call CopyDWGtoPermit(dCoords, "Integrity Building-MDU")
    'Call CopyDWGtoPermit(dCoords, "Integrity Business")
    'Call CopyDWGtoPermit(dCoords, "Integrity Building Misc")
    'Call CopyDWGtoPermit(dCoords, "Integrity Sheets")
    
    Me.show
End Sub

Private Sub cbDWG_Change()
    Call FillOutDrawingList
End Sub

Private Sub GetDWGList(strLayer As String)
    Dim objSS3 As AcadSelectionSet
    Dim entBlock As AcadObject
    Dim obrTemp As AcadBlockReference
    Dim attItem2, vTemp As Variant
    Dim filterType, filterValue As Variant
    Dim grpCode(0) As Integer
    Dim grpValue(0) As Variant
    Dim str As String
    
  On Error Resume Next
    lbSheets.Clear
    
    grpCode(0) = 8
    grpValue(0) = "Integrity Sheets"    'strLayer  '"Integrity Permits"
    filterType = grpCode
    filterValue = grpValue
    
    Err = 0
    
    Set objSS3 = ThisDrawing.SelectionSets.Add("objSS3")
    objSS3.Select acSelectionSetAll, , , filterType, filterValue
    
    If Not Err = 0 Then MsgBox "Error"
    
    For Each entBlock In objSS3
        Set obrTemp = entBlock
        
        If obrTemp.Name = "SS-11x17" Then
            attItem2 = obrTemp.GetAttributes
            'vTemp = Split(attItem2(0).TextString, " ")
               
            str = attItem2(0).TextString & vbTab & obrTemp.XScaleFactor
            str = str & vbTab & obrTemp.InsertionPoint(0) & vbTab & obrTemp.InsertionPoint(1)
            lbSheets.AddItem str
        End If
Next_entBlock:
    Next entBlock
    
    Call SortLBItems
Exit_Sub:
    objSS3.Delete
End Sub

Private Sub cbHighlight_Click()
    Dim objBlock As AcadBlockReference
    Dim objEntity As AcadEntity
    Dim vAttList, vBasePnt As Variant
    Dim objMText As AcadMText
    Dim strMText As String
    Dim dInsertPnt(0 To 2) As Double
    
    Me.Hide
    On Error Resume Next
    ThisDrawing.SetVariable "DIMTFILLCOLOR", 50
    Err = 0
    
    ThisDrawing.Utility.GetEntity objEntity, vBasePnt, vbCr & "Select Pole Text:"
    If Not Err = 0 Then GoTo Exit_Sub
    
    Set objBlock = objEntity
    If Not Err = 0 Then GoTo Exit_Sub
    
    vAttList = objBlock.GetAttributes
    strMText = vAttList(0).TextString
    vAttList(0).TextString = ""
    objBlock.Update
    
    dInsertPnt(0) = vBasePnt(0)
    dInsertPnt(1) = vBasePnt(1)
    dInsertPnt(2) = 0#
    
    Set objMText = ThisDrawing.ModelSpace.AddMText(dInsertPnt, 15, strMText)

    objMText.Layer = "Integrity Poles-Power"
    objMText.Height = 6
    objMText.AttachmentPoint = acAttachmentPointMiddleCenter
    objMText.InsertionPoint = dInsertPnt
    'objMText.Rotation = dRotate
    objMText.BackgroundFill = True
    'objMText.BackgroundFill = acYellow
    'objMText.Highlight
    objMText.Update
    
Exit_Sub:
    Me.show
End Sub

Private Sub cbMatchlines_Click()
    Me.Hide
    Call Module1.AddMatchlines
    Me.show
    Exit Sub
    
    Dim objLWP As AcadLWPolyline
    Dim objText As AcadText
    Dim basePnt, returnPnt As Variant
    Dim vLWPO As Variant
    Dim lwpCoords(0 To 3) As Double
    Dim dTextInsert(0 To 2) As Double
    Dim xDiff, yDiff, zDiff As Double
    Dim dRaotate As Double
    Dim strLine As String
    Dim strLayer As String
    
    If cbDWG.Value = "" Then Exit Sub
    
  On Error Resume Next
    
    Me.Hide
    
    If cbDWG.Value = "DWG" Then
        strLayer = "Integrity Sheets"
    Else
        strLayer = "Integrity Permits-" & cbDWG.Value
        Call CreateLayer(strLayer)
    End If
    
    While Err = 0
        returnPnt = ThisDrawing.Utility.GetPoint(, "Select Mid Point: ")
        lwpCoords(0) = returnPnt(0)
        lwpCoords(1) = returnPnt(1)
        
        If Not Err = 0 Then GoTo Exit_Sub
        
        returnPnt = ThisDrawing.Utility.GetPoint(, "Select Point: ")
        lwpCoords(2) = returnPnt(0)
        lwpCoords(3) = returnPnt(1)
        
        dTextInsert(0) = (lwpCoords(0) + lwpCoords(2)) / 2
        dTextInsert(1) = (lwpCoords(1) + lwpCoords(3)) / 2
        dTextInsert(2) = 0#
        
        If Not Err = 0 Then GoTo Exit_Sub
        
        xDiff = lwpCoords(2) - lwpCoords(0)
        yDiff = lwpCoords(3) - lwpCoords(1)
        zDiff = Sqr((xDiff * xDiff) + (yDiff * yDiff))
            
        Select Case xDiff
            Case Is < 0
                If yDiff = 0 Then
                    dRotate = 0#
                ElseIf yDiff < 0 Then
                    dRotate = Atn(yDiff / xDiff)
                Else
                    dRotate = Atn(yDiff / xDiff) '+ 3.14159265359
                End If
            Case Is = 0
                dRotate = 1.570796327
            Case Is > 0
                If yDiff = 0 Then
                    dRotate = 0#
                ElseIf yDiff > 0 Then
                    dRotate = Atn(yDiff / xDiff)
                Else
                    dRotate = Atn(yDiff / xDiff) '+ 3.14159265359
                End If
        End Select
        
        If xDiff < 0 Then
            dTextInsert(0) = dTextInsert(0) - 13.5 * yDiff / zDiff
            dTextInsert(1) = dTextInsert(1) + 13.5 * xDiff / zDiff
        Else
            dTextInsert(0) = dTextInsert(0) - 7.5 * yDiff / zDiff
            dTextInsert(1) = dTextInsert(1) + 7.5 * xDiff / zDiff
        End If
        
        lwpCoords(2) = lwpCoords(0) + (zDiff + 10) * xDiff / zDiff
        lwpCoords(3) = lwpCoords(1) + (zDiff + 10) * yDiff / zDiff
        lwpCoords(0) = lwpCoords(2) - (zDiff + 20) * xDiff / zDiff
        lwpCoords(1) = lwpCoords(3) - (zDiff + 20) * yDiff / zDiff
        
        Set objLWP = ThisDrawing.ModelSpace.AddLightWeightPolyline(lwpCoords)
        objLWP.Layer = strLayer
        objLWP.Update
        
        vLWPO = objLWP.Offset(-5)
        
        strLine = ThisDrawing.Utility.GetString(0, "Matches Drawing #: ")
        
        If Not Err = 0 Then GoTo Exit_Sub
        
        Select Case Len(strLine)
            Case Is = 1
                strLine = "SEE DWG 00" & strLine
            Case Is = 2
                strLine = "SEE DWG 0" & strLine
            Case Is = 3
                strLine = "SEE DWG " & strLine
        End Select
            
        Set objText = ThisDrawing.ModelSpace.AddText(strLine, dTextInsert, 6)
        objText.Layer = strLayer
        objText.Alignment = acAlignmentCenter
        objText.TextAlignmentPoint = dTextInsert
        objText.Rotation = dRotate
        objText.Update
    Wend
Exit_Sub:
    Me.show
End Sub

Private Sub cbPrintSelected_Click()
    Dim strArraySheets() As String
    Dim attTotalLine, attTotalSplit As Variant
    Dim str, str1 As String
    Dim strDWG As String
    Dim dScale As Double
    Dim dLL(0 To 1), dUR(0 To 1) As Double
    Dim strPlot(0 To 24) As String
    Dim i As Integer
    Dim iCount As Integer
    Dim iResult As Integer
    Dim strCommand As String
    Dim strPath As String
    Dim strFileName As String
    Dim strArray As Variant
    Dim viewCoordsB(0 To 2) As Double
    Dim viewCoordsE(0 To 2) As Double
    
    strPath = ThisDrawing.Path & "\"
    
    iCount = 0
    
    strPlot(0) = "-plot"
    strPlot(1) = "y"
    strPlot(2) = ""
    'strPlot(3) = "Microsoft Print to PDF"
    strPlot(4) = "TABLOID"
    strPlot(5) = "i" '"i"
    strPlot(6) = "LANDSCAPE"
    strPlot(7) = "n"
    strPlot(8) = "w"
    'strPlot(9) = ""
    'strPlot(10) = ""
    'strPlot(11) = "" '"1=75"
    strPlot(12) = "c"
    strPlot(13) = "y"
    strPlot(14) = ""    '"United.ctb"
    strPlot(15) = "y"
    strPlot(16) = "a"
    strPlot(17) = "n"
    strPlot(18) = "n"
    strPlot(19) = "y"
    'strPlot(20) = ""
    strPlot(21) = ""
    strPlot(22) = ""
    strPlot(23) = ""
    strPlot(24) = ""
    
    ThisDrawing.SetVariable "FILEDIA", 0
    ThisDrawing.SetVariable "CMDDIA", 0
    
    For i = 0 To lbSheets.ListCount - 1
        If lbSheets.Selected(i) Then
            iCount = iCount + 1
            
            str = lbSheets.List(i)
            attTotalSplit = Split(str, vbTab)
            strDWG = attTotalSplit(0)
            dScale = CDbl(attTotalSplit(1))
            dLL(0) = CDbl(attTotalSplit(2))
            dLL(1) = CDbl(attTotalSplit(3))
            dUR(0) = dLL(0) + (1652 * dScale)
            dUR(1) = dLL(1) + (1052 * dScale)
    
            viewCoordsB(0) = dLL(0)
            viewCoordsB(1) = dLL(1)
            viewCoordsB(2) = 0#
            viewCoordsE(0) = dUR(0)
            viewCoordsE(1) = dUR(1)
            viewCoordsE(2) = 0#
    
            ThisDrawing.Application.ZoomWindow viewCoordsB, viewCoordsE
            
            strPlot(9) = (dLL(0) - (1 * dScale)) & "," & (dLL(1) - (1 * dScale))
            strPlot(10) = (dUR(0) + (1 * dScale)) & "," & (dUR(1) + (1 * dScale))
            strPlot(11) = "1=" & CStr((dScale + 0.02) * 100)
    
            strFileName = """" & strPath & "Individual Sheets\" & strDWG & ".pdf"""
            strFileName = Replace(strFileName, "/", "\")
            'strFileName = Replace(strFileName, "\", "/")
            strPlot(20) = strFileName
            'MsgBox strFileName
            'Exit Sub
            
            strCommand = ""
            For j = 0 To 19
                If strPlot(j) = "" Then
                    strCommand = strCommand & vbCr
                Else
                    strCommand = strCommand & strPlot(j) & vbCr
                End If
            Next j
            
            ThisDrawing.SendCommand strCommand
            
            Select Case iCount
                Case Is = 2, Is = 10, Is = 20
                    iResult = MsgBox("Continue Plotting?", vbYesNo, "Continue Plotting")
                        If iResult = vbNo Then GoTo Exit_Next
            End Select
        End If
    Next i
Exit_Next:
    
    ThisDrawing.SetVariable "FILEDIA", 1
    ThisDrawing.SetVariable "CMDDIA", 1
End Sub

Private Sub cbQuit_Click()
    Me.Hide
End Sub

Private Sub cbSelectAll_Click()
    For i = 0 To lbSheets.ListCount - 1
        If lbSheets.List(i) = "" Then GoTo Next_I
        'lbSheets.List(i).Enabled = True
        lbSheets.Selected(i) = True
Next_I:
    Next i
End Sub

Private Sub cbSelectNone_Click()
    For i = 0 To lbSheets.ListCount - 1
        lbSheets.Selected(i) = False
    Next i
End Sub

Private Sub Label3_Click()
    Dim objObject As AcadObject
    Dim obrGP2 As AcadBlockReference
    Dim basePnt, attItem As Variant
    
    Me.Hide
  On Error Resume Next
    
    ThisDrawing.Utility.GetEntity objObject, basePnt, "Select SS Info: "
    If TypeOf objObject Is AcadBlockReference Then
        Set obrGP2 = objObject
    Else
        Me.show
        Exit Sub
    End If
    attItem = obrGP2.GetAttributes
    
    tbProject.Value = attItem(0).TextString
    tbWO.Value = attItem(1).TextString
    cbExchange.Value = attItem(2).TextString
    tbRST.Value = attItem(3).TextString
    cbCounty.Value = attItem(4).TextString
    tbCity.Value = attItem(5).TextString
    tbTotalDWG = attItem(7).TextString
    
    Me.show
End Sub

Private Sub lbSheets_DblClick(ByVal Cancel As MSForms.ReturnBoolean)
    Dim str As String
    Dim strArray As Variant
    Dim viewCoordsB(0 To 2) As Double
    Dim viewCoordsE(0 To 2) As Double
    
    Me.Hide
    
    str = lbSheets.List(lbSheets.ListIndex)
    strArray = Split(str, vbTab)
    
    viewCoordsB(0) = strArray(2)
    viewCoordsB(1) = strArray(3)
    viewCoordsB(2) = 0#
    viewCoordsE(0) = viewCoordsB(0) + 1650 * CDbl(strArray(1))
    viewCoordsE(1) = viewCoordsB(1) + 1050 * CDbl(strArray(1))
    viewCoordsE(2) = 0#
    
    ThisDrawing.Application.ZoomWindow viewCoordsB, viewCoordsE
    Me.show
End Sub

Private Sub UserForm_Initialize()
    cbExchange.AddItem "FLOR"
    cbExchange.AddItem "INTE"
    cbExchange.AddItem "SMYR"
    cbExchange.AddItem "ALMA"
    cbExchange.AddItem "MRBO"
    cbExchange.AddItem "AIR"
    cbExchange.AddItem "ROCK"
    cbExchange.AddItem "CHRI"
    cbExchange.AddItem "KITT"
    cbExchange.AddItem "CAIT"
    cbExchange.AddItem "LAK"
    cbExchange.AddItem "LAS"
    cbExchange.AddItem "LEB"
    cbExchange.AddItem "MAR"
    cbExchange.AddItem "NOR"
    cbExchange.AddItem "SOU"
    cbExchange.AddItem "VES"
    cbExchange.AddItem "WAT"
    cbExchange.AddItem "Belfast"
    cbExchange.AddItem "Bell Buckle"
    cbExchange.AddItem "Chapel Hill"
    cbExchange.AddItem "Chapel Hill-CLEC"
    cbExchange.AddItem "College Grove"
    cbExchange.AddItem "College Grove-CLEC"
    cbExchange.AddItem "Flat Creek"
    cbExchange.AddItem "Fosterville"
    cbExchange.AddItem "Franklin-CLEC"
    cbExchange.AddItem "Nolensville"
    cbExchange.AddItem "Nolensville-CLEC"
    cbExchange.AddItem "Shelbyville-CLEC"
    cbExchange.AddItem "Triune"
    cbExchange.AddItem "Unionville"
    
    cbCounty.AddItem "Bedford"
    cbCounty.AddItem "Davidson"
    cbCounty.AddItem "Marshall"
    cbCounty.AddItem "Maury"
    cbCounty.AddItem "Rutherford"
    cbCounty.AddItem "Williamson"
    cbCounty.AddItem "Wilson"
    
    cbDesigner.AddItem "Dylan Spears"
    cbDesigner.AddItem "Jeremy Pafford"
    cbDesigner.AddItem "Ronn Elliott"
    cbDesigner.AddItem "Rich Taylor"
    cbDesigner.AddItem "Jason Pafford"
    cbDesigner.AddItem "Adam Kemper"
    cbDesigner.AddItem "Byron Auer"
    cbDesigner.AddItem "Jon Wilburn"
    cbDesigner.AddItem "Franklin Angulo"
    cbDesigner.AddItem "Jay Penny"
    cbDesigner.AddItem "Sam Jackson"
    
    cbScale.AddItem "50"
    cbScale.AddItem "75"
    cbScale.AddItem "100"
    cbScale.Value = "75"
    
    Dim objSS3 As AcadSelectionSet
    Dim entBlock As AcadObject
    Dim obrTemp As AcadBlockReference
    Dim attItem2, vTemp As Variant
    Dim mode As Integer
    'Dim str As String
    Dim filterType, filterValue As Variant
    Dim grpCode(0) As Integer
    Dim grpValue(0) As Variant
    Dim str, strList As String
    'Dim vTemp As Variant
    
  On Error Resume Next
  
    strList = ""
    
    str = ThisDrawing.Name
    vTemp = Split(str, " ")
    tbWO.Value = vTemp(0)
    
    Select Case UBound(vTemp)
        Case Is = 1
            str = vTemp(1)
        Case Is > 1
            str = vTemp(1)
            For i = 2 To UBound(vTemp)
                str = str & " " & vTemp(i)
            Next i
    End Select
    tbProject.Value = str
    
    'grpCode(0) = 8
    'grpValue(0) = "Integrity Permits"
    grpCode(0) = 2
    grpValue(0) = "SS-11x17"
    filterType = grpCode
    filterValue = grpValue
    
    Set objSS3 = ThisDrawing.SelectionSets.Add("objSS3")
    objSS3.Select acSelectionSetAll, , , filterType, filterValue
    
    For Each entBlock In objSS3
        Set obrTemp = entBlock
        attItem2 = obrTemp.GetAttributes
        
        vTemp = Split(attItem2(0).TextString, " ")
        If vTemp(0) = "dwg" Then GoTo Next_entBlock
        If Asc(vTemp(0)) > 47 And Asc(vTemp(0)) < 58 Then GoTo Next_entBlock
        
        If InStr(strLine, vTemp(0)) = 0 Then
            strLine = strLine & vTemp(0) & "<>"
        End If
Next_entBlock:
    Next entBlock
    
    cbDWG.AddItem ""
    vTemp = Split(strLine, "<>")
    For i = LBound(vTemp) To UBound(vTemp)
        If Not vTemp(i) = "" Then
            If vTemp(i) = "DWG" Then
                cbDWG.AddItem vTemp(i), 1
                'cbDWG.Value = "DWG"
            Else
                cbDWG.AddItem vTemp(i)
            End If
        'If vTemp(i) = "DWG" Then
            'cbDWG.Value = "DWG"
            'Call GetDWGList("Integrity Sheets")
        End If
    Next i
    
    Call FillOutDrawingList
    'Call SortLBItems
Exit_Sub:
    objSS3.Delete
End Sub

Private Sub cbUpdateAllSS_Click()
    Dim objSS3 As AcadSelectionSet
    Dim entBlock As AcadObject
    Dim obrTemp As AcadBlockReference
    Dim attItem2 As Variant
    Dim mode As Integer
    Dim filterType, filterValue As Variant
    Dim grpCode(0) As Integer
    Dim grpValue(0) As Variant
    Dim str As String
    
  On Error Resume Next
    
    grpCode(0) = 8
    If cbDWG.Value = "DWG" Then
        grpValue(0) = "Integrity Sheets"
    Else
        grpValue(0) = "Integrity Permits-" & cbDWG.Value
    End If
    filterType = grpCode
    filterValue = grpValue
    
    Set objSS3 = ThisDrawing.SelectionSets.Add("objSS3")
    objSS3.Select acSelectionSetAll, , , filterType, filterValue
    
    For Each entBlock In objSS3
        Set obrTemp = entBlock
        
        If obrTemp.Name = "SS Info" Then
            attItem2 = obrTemp.GetAttributes
            attItem2(0).TextString = tbProject.Value
            attItem2(1).TextString = tbWO.Value
            attItem2(2).TextString = cbExchange.Value
            attItem2(3).TextString = tbRST.Value
            attItem2(4).TextString = cbCounty.Value
            attItem2(5).TextString = tbCity.Value
            attItem2(7).TextString = tbTotalDWG.Value
            
            obrTemp.Update
        End If
    Next entBlock
    
    Call SortLBItems
Exit_Sub:
    objSS3.Delete
End Sub

Private Sub cbLineCallout_Click()
    Dim objEntity As AcadEntity
    Dim objLWP As AcadLWPolyline
    Dim objPolyline As AcadPolyline
    Dim objLine As AcadLine
    Dim objMText As AcadMText
    Dim objText As AcadText
    Dim vBasePnt As Variant
    Dim vStartPnt, vEndPnt As Variant
    Dim vCoords As Variant
    Dim dRotate, dScale, Pi As Double
    Dim dInsertPnt(0 To 2) As Double
    Dim dStartPnt(0 To 2) As Double
    Dim dEndPnt(0 To 2) As Double
    Dim dDiff(0 To 2) As Double
    Dim dToText(0 To 2) As Double
    Dim dFromText(0 To 2) As Double
    Dim dTemp, dDistance As Double
    Dim strLine, strLayer As String
    
    On Error Resume Next
    
    Me.Hide
  
    Pi = 3.14159265359
    strLine = ""
    
    While Err = 0
    
    ThisDrawing.Utility.GetEntity objEntity, vBasePnt, "Get Line or Polyline"
    If Not Err = 0 Then
        Me.show
        Exit Sub
    End If
    
    If Not Err = 0 Then
        Me.show
        Exit Sub
    End If
    
    Select Case objEntity.ObjectName
        Case "AcDbLine"
            Set objLine = objEntity
            'iLength = CInt(objLine.Length)
            vStartPnt = objLine.StartPoint
            vEndPnt = objLine.EndPoint
            
            dDiff(0) = vEndPnt(0) - vStartPnt(0)
            dDiff(1) = vEndPnt(1) - vStartPnt(1)
            dDiff(2) = Sqr((dDiff(0) * dDiff(0)) + (dDiff(1) * dDiff(1)))
            
            If vBasePnt(0) > vStartPnt(0) Then
                dToText(0) = vBasePnt(0) - vStartPnt(0)
                dToText(1) = vBasePnt(1) - vStartPnt(1)
            Else
                dToText(0) = vStartPnt(0) - vBasePnt(0)
                dToText(1) = vStartPnt(1) - vBasePnt(1)
            End If
            dToText(2) = Sqr((dToText(0) * dToText(0)) + (dToText(1) * dToText(1)))
            
            dScale = Abs(dToText(2) / dDiff(2))
            dInsertPnt(0) = vStartPnt(0) + (dDiff(0) * dScale)
            dInsertPnt(1) = vStartPnt(1) + (dDiff(1) * dScale)
            dInsertPnt(2) = 0#
            
            If dToText(0) = 0 Then
                dRotate = Pi / 2
            Else
                dRotate = Atn(dToText(1) / dToText(0))
            End If
            
            strLayer = objLine.Layer
            Select Case strLayer
                Case "Parcels"
                    strLine = "R/W"
                Case "Integrity Roads-EOP"
                    strLine = "EOP"
                Case "Integrity Roads-CL"
                    strLine = "C/L"
                Case "Integrity Cable-Aerial", "Integrity Cable"
                    strLine = "CABLE"
                Case Else
                    strLine = tbLTText.Value
            End Select
        Case "AcDbPolyline"
            Set objLWP = objEntity
            vCoords = objLWP.Coordinates
            
            For i = 3 To UBound(vCoords) Step 2
                dDiff(0) = vCoords(i - 1) - vCoords(i - 3)
                dDiff(1) = vCoords(i) - vCoords(i - 2)
                dDiff(2) = Sqr((dDiff(0) * dDiff(0)) + (dDiff(1) * dDiff(1)))
            
                dToText(0) = vBasePnt(0) - vCoords(i - 3)
                dToText(1) = vBasePnt(1) - vCoords(i - 2)
                dToText(2) = Sqr((dToText(0) * dToText(0)) + (dToText(1) * dToText(1)))
                
                If dDiff(2) > dToText(2) Then
                    dFromText(0) = vBasePnt(0) - vCoords(i - 1)
                    dFromText(1) = vBasePnt(1) - vCoords(i)
                    dFromText(2) = Sqr((dFromText(0) * dFromText(0)) + (dFromText(1) * dFromText(1)))
                    
                    dTemp = (dFromText(2) + dToText(2)) / dDiff(2)
                    If dTemp < 1.01 Then
                        GoTo Exit_First_Next
                    End If
                End If
            Next i
Exit_First_Next:
            
            dScale = Abs(dToText(2) / dDiff(2))
            dInsertPnt(0) = vCoords(i - 3) + (dDiff(0) * dScale)
            dInsertPnt(1) = vCoords(i - 2) + (dDiff(1) * dScale)
            dInsertPnt(2) = 0#
            
            If dToText(0) = 0 Then
                dRotate = Pi / 2
            Else
                dRotate = Atn(dToText(1) / dToText(0))
            End If
            
            strLayer = objLWP.Layer
            Select Case strLayer
                Case "Parcels"
                    strLine = "R/W"
                Case "Integrity Roads-EOP"
                    strLine = "EOP"
                Case "Integrity Roads-CL"
                    strLine = "C/L"
                Case "Integrity Cable-Aerial", "Integrity Cable", "IS_Fiber"
                    strLine = "CABLE"
                Case Else
                    strLine = tbLTText.Value
            End Select
    End Select
            
'    Set objText = ThisDrawing.ModelSpace.AddText(strLine, dInsertPnt, 4.5)
'    objText.Layer = strLayer
'    objText.Alignment = acAlignmentMiddle
'    objText.TextAlignmentPoint = dInsertPnt
'    objText.Rotation = dRotate
'    objText.Update

    dScale = CInt(cbScale.Value) / 100

    Set objMText = ThisDrawing.ModelSpace.AddMText(dInsertPnt, 15, strLine)
    objMText.Layer = strLayer
    objMText.Height = 6 * dScale
    objMText.AttachmentPoint = acAttachmentPointMiddleCenter
    objMText.InsertionPoint = dInsertPnt
    objMText.Rotation = dRotate
    objMText.BackgroundFill = True
    objMText.Update
    
    Wend
    
    Me.show
End Sub

Private Sub SortLBItems()
    Dim iCount As Integer
    Dim vItem, vItem1 As Variant
    Dim strTemp As String
    
    iCount = lbSheets.ListCount - 1
    If iCount < 1 Then Exit Sub
    
    On Error Resume Next
    
    For a = iCount To 0 Step -1
        For b = 0 To a - 1
            vItem = Split(lbSheets.List(b), vbTab)
            vItem1 = Split(lbSheets.List(b + 1), vbTab)
            If vItem(0) > vItem1(0) Then
                
                strTemp = lbSheets.List(b + 1)
                lbSheets.List(b + 1) = lbSheets.List(b)
                lbSheets.List(b) = strTemp
            End If
        Next b
    Next a
End Sub

Private Sub CreateLayer(strLayer As String)
    Dim objLayer As AcadLayer
    
    On Error Resume Next
    
    Set objLayer = ThisDrawing.Layers.Add(strLayer)
    
    If Not Err = 0 Then Set objLayer = ThisDrawing.Layers.Item(strLayer)
    
    objLayer.color = acGreen
End Sub

Private Sub CopyDWGtoPermit(vCoords As Variant, strLayer As String)
    Dim objSS4 As AcadSelectionSet
    Dim entBlock As AcadEntity
    Dim objEMove As AcadEntity
    Dim dLL(0 To 2) As Double
    Dim dUR(0 To 2) As Double
    Dim dTo(0 To 2) As Double
    Dim filterType, filterValue As Variant
    Dim grpCode(0) As Integer
    Dim grpValue(0) As Variant
    Dim strCommand As String
    
  'On Error Resume Next
    
    dLL(0) = vCoords(0)
    dLL(1) = vCoords(1)
    dLL(2) = vCoords(2)
    
    dUR(0) = vCoords(3)
    dUR(1) = vCoords(4)
    dUR(2) = vCoords(5)
    
    dTo(0) = vCoords(6)
    dTo(1) = vCoords(7)
    dTo(2) = vCoords(8)
    
    grpCode(0) = 8
    grpValue(0) = strLayer
    filterType = grpCode
    filterValue = grpValue
    
    Set objSS4 = ThisDrawing.SelectionSets.Add("objSS3")
    objSS4.Select acSelectionSetWindow, dLL, dUR, filterType, filterValue
    
    If objSS4.count = 0 Then GoTo Exit_Sub
    
    strCommand = "COPY" & vbCr & "P" & vbCr & vbCr
    strCommand = strCommand & dLL(0) & "," & dLL(1) & ",0" & vbCr
    strCommand = strCommand & dTo(0) & "," & dTo(1) & ",0" & vbCr & vbCr
    
    ThisDrawing.SendCommand strCommand
    
    
Exit_Sub:
    objSS4.Clear
    objSS4.Delete
End Sub

Private Sub FillOutDrawingList()
    Dim objSS3 As AcadSelectionSet
    Dim entBlock As AcadObject
    Dim obrTemp As AcadBlockReference
    Dim attItem2, vTemp As Variant
    Dim mode As Integer
    'Dim str As String
    Dim filterType, filterValue As Variant
    Dim grpCode(0) As Integer
    Dim grpValue(0) As Variant
    Dim str, strList As String
    Dim strLayer As String
    
  On Error Resume Next
    lbSheets.Clear
    
    If cbDWG.Value = "DWG" Then
        strLayer = "Integrity Sheets"
    Else
        strLayer = "Integrity Permits-" & cbDWG.Value
    End If
    
    grpCode(0) = 8
    grpValue(0) = strLayer
    filterType = grpCode
    filterValue = grpValue
    
    Set objSS3 = ThisDrawing.SelectionSets.Add("objSS3")
    objSS3.Select acSelectionSetAll, , , filterType, filterValue
    
    For Each entBlock In objSS3
        If Not TypeOf entBlock Is AcadBlockReference Then GoTo Next_entBlock
        Set obrTemp = entBlock
        attItem2 = obrTemp.GetAttributes
        
        Select Case obrTemp.Name
            Case "SS Info"
                tbProject.Value = attItem2(0).TextString
                tbWO.Value = attItem2(1).TextString
                cbExchange.Value = attItem2(2).TextString
                tbRST.Value = attItem2(3).TextString
                cbCounty.Value = attItem2(4).TextString
                tbCity.Value = attItem2(5).TextString
                If tbTotalDWG.Value < attItem2(7).TextString Then tbTotalDWG.Value = attItem2(7).TextString
            Case "SS-11x17"
                vTemp = Split(attItem2(0).TextString, " ")
            
                'If Not vTemp(0) = cbDWG.Value Then GoTo Next_entBlock
               
                str = attItem2(0).TextString & vbTab & obrTemp.XScaleFactor
                str = str & vbTab & obrTemp.InsertionPoint(0) & vbTab & obrTemp.InsertionPoint(1)
                lbSheets.AddItem str
        End Select
Next_entBlock:
    Next entBlock
    
    Call SortLBItems
Exit_Sub:
    objSS3.Delete
End Sub

Private Sub UpdateAllDWGs()
    Dim objSS3 As AcadSelectionSet
    Dim entBlock As AcadObject
    Dim obrTemp As AcadBlockReference
    Dim attItem2 As Variant
    Dim mode As Integer
    Dim filterType, filterValue As Variant
    Dim grpCode(0) As Integer
    Dim grpValue(0) As Variant
    Dim str As String
    
  On Error Resume Next
    
    grpCode(0) = 8
    If cbDWG.Value = "DWG" Then
        grpValue(0) = "Integrity Sheets"
    Else
        grpValue(0) = "Integrity Permits-" & cbDWG.Value
    End If
    filterType = grpCode
    filterValue = grpValue
    
    Set objSS3 = ThisDrawing.SelectionSets.Add("objSS3")
    objSS3.Select acSelectionSetAll, , , filterType, filterValue
    
    For Each entBlock In objSS3
        Set obrTemp = entBlock
        
        If obrTemp.Name = "SS Info" Then
            attItem2 = obrTemp.GetAttributes
            attItem2(0).TextString = tbProject.Value
            attItem2(1).TextString = tbWO.Value
            attItem2(2).TextString = cbExchange.Value
            attItem2(3).TextString = tbRST.Value
            attItem2(4).TextString = cbCounty.Value
            attItem2(5).TextString = tbCity.Value
            attItem2(7).TextString = tbTotalDWG.Value
            
            obrTemp.Update
        End If
    Next entBlock
    
    Call SortLBItems
Exit_Sub:
    objSS3.Delete
End Sub

Attribute VB_Name = "TabGeneric"
Attribute VB_Base = "0{7D1272A0-1FE7-45F0-A6AE-3C5D274B9760}{F2B8B6C9-153B-4AF7-B131-4BB614AF06FC}"
Attribute VB_GlobalNameSpace = False
Attribute VB_Creatable = False
Attribute VB_PredeclaredId = True
Attribute VB_Exposed = False
Attribute VB_TemplateDerived = False
Attribute VB_Customizable = False
Dim objSS As AcadSelectionSet

Private Sub cbCopyAll_Click()
    Dim strFileName As String
    Dim strDWGName As String
    Dim vLine As Variant
    Dim objData As New DataObject
    Dim strCopy, strTemp As String
    Dim vUnit As Variant
    
    If cbCopyToFile.Value = True Then
        strFileName = ThisDrawing.Path & "\"
        vLine = Split(ThisDrawing.Name, " ")
        strFileName = strFileName & vLine(0) & "-TAB Totals.txt"

        Open strFileName For Output As #1
        
        For a = 0 To lbFinal.ListCount - 1
            Print #1, lbFinal.List(a, 0) & vbTab & lbFinal.List(a, 1)
        Next a
        
        Close #1
    
        MsgBox "Saved to File"
    Else
        strCopy = lbFinal.List(0, 0) & vbTab & lbFinal.List(0, 1)
        For a = 1 To lbFinal.ListCount - 1
            strCopy = strCopy & vbCr & lbFinal.List(a, 0) & vbTab & lbFinal.List(a, 1)
        Next a
        
        objData.SetText strCopy
        objData.PutInClipboard
    
        MsgBox "Copied to Clipboard"
    End If
End Sub

Private Sub cbCopyTab_Click()
    Dim objData As New DataObject
    Dim strCopy As String
    Dim vLine As Variant
    
    If InStr(lbFinal.List(0, 0), " ") > 0 Then
       vLine = Split(lbFinal.List(0, 0), " ")
       strCopy = vLine(0) & vbTab & vLine(1) & vbTab & lbFinal.List(0, 1)
    Else
        strCopy = lbFinal.List(0, 0) & vbTab & vbTab & lbFinal.List(0, 1)
    End If
    
    For a = 1 To lbFinal.ListCount - 1
        If InStr(lbFinal.List(a, 0), " ") > 0 Then
            vLine = Split(lbFinal.List(a, 0), " ")
            strCopy = strCopy & vbCr & vLine(0) & vbTab & vLine(1) & vbTab & lbFinal.List(a, 1)
        Else
            strCopy = strCopy & vbCr & lbFinal.List(a, 0) & vbTab & vbTab & lbFinal.List(a, 1)
        End If
    Next a
        
    objData.SetText strCopy
    objData.PutInClipboard
    
    MsgBox "Copied to Clipboard"
End Sub

Private Sub cbExport_Click()
    Dim strFileName As String
    Dim strDWGName As String
    Dim str1, str2, str3, strLine As String
    Dim strItem2, strSize As String
    Dim vLine, vHC As Variant
    Dim iTest As Integer
    
    Load FileNameForm
    FileNameForm.show
    strFileName = FileNameForm.tbFileName.Value
    Unload FileNameForm
    
    If Right(strFileName, 4) = ".txt" Then
        strFileName = Left(strFileName, Len(strFileName) - 4)
    End If
    strFileName = strFileName & "-TAB.txt"

    Open strFileName For Output As #1
    
    iTest = 0
    
    For i = 0 To (lbUnits.ListCount - 1)
        strLine = lbUnits.List(i)
        
        Print #1, strLine
    Next i
    
    If lbNotFound.ListCount > 0 Then
        For i = 0 To (lbNotFound.ListCount - 1)
            strLine = lbNotFound.List(i)
        
            Print #1, strLine
        Next i
    End If
    
    MsgBox "Export Complete"
    Close #1
End Sub

Private Sub cbExportTab_Click()
    Dim strFileName As String
    'Dim strDWGName As String
    Dim vLine As Variant
    'Dim objData As New DataObject
    'Dim strCopy, strTemp As String
    'Dim vUnit As Variant
    
    strFileName = ThisDrawing.Path & "\"
    vLine = Split(ThisDrawing.Name, " ")
    strFileName = strFileName & vLine(0) & "-TAB Totals.txt"

    Open strFileName For Output As #1
        
    For a = 0 To lbFinal.ListCount - 1
        Print #1, Replace(lbFinal.List(a, 0), "  ", vbTab) & vbTab & lbFinal.List(a, 1)
    Next a
        
    Close #1
    
    MsgBox "Saved to File"
End Sub

Private Sub cbGetFromBlocks_Click()
    Dim objEntity As AcadEntity
    Dim objBlock As AcadBlockReference
    Dim objLWP As AcadLWPolyline
    Dim vAttList, vUnits, vClosure As Variant
    Dim vItem, vTemp, vRich As Variant
    Dim vReturnPnt, vCoords As Variant
    Dim filterType, filterValue As Variant
    Dim vPnt1, vPnt2 As Variant
    Dim grpValue(0) As Variant
    Dim grpCode(0) As Integer
    Dim str1, str2, strUnit As String
    Dim strExchange As String
    Dim dPnt1(0 To 2) As Double
    Dim dPnt2(0 To 2) As Double
    Dim iRes, iBus As Integer
    Dim iAF, iBF, iUF, iUNK As Integer
    Dim iHO1A, iHO1B As Integer
    Dim iTemp, iCounter As Integer
    Dim dCoords() As Double
    
    iRes = 0: iBus = 0
    iAF = 0: iBF = 0: iUF = 0: iUNK = 0
    strExchange = ""

    grpCode(0) = 2
    grpValue(0) = "sPole,sPed,sHH,sPanel,sMH,Customer,cable_span,SS Info"
    filterType = grpCode
    filterValue = grpValue
    
    lbUnits.Clear
    lbNotFound.Clear
    
  On Error Resume Next
    Me.Hide
    
    objSS.Clear
    
    Select Case cbSelection.Value
        Case "Window"
            vPnt1 = ThisDrawing.Utility.GetPoint(, "Get BL Corner: ")
            vPnt2 = ThisDrawing.Utility.GetCorner(vPnt1, vbCr & "Get UR Corner: ")
            
            dPnt1(0) = vPnt1(0)
            dPnt1(1) = vPnt1(1)
            dPnt1(2) = vPnt1(2)
            
            dPnt2(0) = vPnt2(0)
            dPnt2(1) = vPnt2(1)
            dPnt2(2) = vPnt2(2)
            
            objSS.Select acSelectionSetWindow, dPnt1, dPnt2, filterType, filterValue
        Case Else
                ThisDrawing.Utility.GetEntity objEntity, vReturnPnt, "Select Polygon Border: "
                If Not objEntity.ObjectName = "AcDbPolyline" Then
                    MsgBox "Error: Invalid Selection."
                    Me.show
                    Exit Sub
                End If
            
                Set objLWP = objEntity
                vCoords = objLWP.Coordinates
                
                iTemp = (UBound(vCoords) + 1) / 2 * 3 - 1
                ReDim dCoords(iTemp) As Double
                
                iCounter = 0
                For i = 0 To UBound(vCoords) Step 2
                    dCoords(iCounter) = vCoords(i)
                    iCounter = iCounter + 1
                    dCoords(iCounter) = vCoords(i + 1)
                    iCounter = iCounter + 1
                    dCoords(iCounter) = 0#
                    iCounter = iCounter + 1
                Next i
                
                objSS.SelectByPolygon acSelectionSetCrossingPolygon, dCoords, filterType, filterValue
    End Select
    
    
  
    'Err = 0
    
    For Each objEntity In objSS
        If TypeOf objEntity Is AcadBlockReference Then
            Set objBlock = objEntity
            
            If objBlock.Layer = "Integrity Future" Then GoTo Next_Object
            
            Select Case objBlock.Name
                Case "SS Info"
                    vAttList = objBlock.GetAttributes
                    If Not vAttList(2).TextString = "" Then strExchange = vAttList(2).TextString
                Case "sPole"
                    iHO1A = 0
                    iHO1B = 0
                    vAttList = objBlock.GetAttributes
                    
                    If vAttList(0).TextString = "POLE" Then GoTo Next_Object
                    If vAttList(27).TextString = "" Then GoTo Next_Object
                    
                    str1 = vAttList(0).TextString & vbTab & "sPole" & vbTab
                    vUnits = Split(vAttList(27).TextString, ";;")
                    
                    'MsgBox vAttList(0).TextString & vbCr & UBound(vUnits)
                    
                    For i = 0 To UBound(vUnits)
                        vItem = Split(vUnits(i), "=")
                        If UBound(vItem) = 0 Then
                            str2 = str1 & vItem(0) & vbTab & "1" & vbTab
                        Else
                            vTemp = Split(vItem(1), "  ")
                            If UBound(vTemp) = 0 Then
                                str2 = str1 & vItem(0) & vbTab & vItem(1) & vbTab
                            Else
                                str2 = str1 & vItem(0) & vbTab & vTemp(0) & vbTab & vTemp(1)
                            End If
                            str2 = Replace(str2, "'", "")
                        End If
                        str2 = Replace(str2, "+", "")
                        'MsgBox str2
                        'lbUnits.AddItem str2
                        
                        vRich = Split(str2, vbTab)
                        
                        lbUnits.AddItem vRich(0)
                        lbUnits.List(lbUnits.ListCount - 1, 1) = vRich(1)
                        lbUnits.List(lbUnits.ListCount - 1, 2) = vRich(2)
                        lbUnits.List(lbUnits.ListCount - 1, 3) = vRich(3)
                        lbUnits.List(lbUnits.ListCount - 1, 4) = vRich(4)
                    Next i
                    
                    vUnits = Split(vAttList(26).TextString, " + ")
                    For i = 0 To UBound(vUnits)
                        vItem = Split(vUnits(i), ": ")
                        If UBound(vItem) = 0 Then GoTo Next_sPole_HO1
                        vTemp = Split(vItem(1), "-")
                        If UBound(vTemp) = 0 Then
                            iHO1A = iHO1A + 1
                        Else
                            iHO1A = iHO1A + CInt(vTemp(1)) - CInt(vTemp(0)) + 1
                        End If
Next_sPole_HO1:
                    Next i
                    
                    If iHO1A > 0 Then
                        str2 = str1 & "HO1A" & vbTab & iHO1A & vbTab
                        'lbUnits.AddItem str2
                        
                        vRich = Split(str2, vbTab)
                        
                        lbUnits.AddItem vRich(0)
                        lbUnits.List(lbUnits.ListCount - 1, 1) = vRich(1)
                        lbUnits.List(lbUnits.ListCount - 1, 2) = vRich(2)
                        lbUnits.List(lbUnits.ListCount - 1, 3) = vRich(3)
                        lbUnits.List(lbUnits.ListCount - 1, 4) = vRich(4)
                    End If
                Case "sPed", "sHH", "sPanel", "sMH"
                    iHO1A = 0
                    iHO1B = 0
                    vAttList = objBlock.GetAttributes
                    
                    Select Case vAttList(0).TextString
                        Case "PED", "HH", "PANEL", "MH", ""
                            GoTo Next_Object
                    End Select
                    
                    If vAttList(7).TextString = "" Then GoTo Next_Object
                    
                    str1 = vAttList(0).TextString & vbTab & objBlock.Name & vbTab
                    vUnits = Split(vAttList(7).TextString, ";;")
                    
                    For i = 0 To UBound(vUnits)
                        vItem = Split(vUnits(i), "=")
                        If UBound(vItem) = 0 Then GoTo Next_sPed_HO1
                        If UBound(vItem) = 0 Then
                            str2 = str1 & vItem(0) & vbTab & "1" & vbTab
                        Else
                            vTemp = Split(vItem(1), "  ")
                            If UBound(vTemp) = 0 Then
                                str2 = str1 & vItem(0) & vbTab & vItem(1) & vbTab
                            Else
                                str2 = str1 & vItem(0) & vbTab & vTemp(0) & vbTab & vTemp(1)
                            End If
                            str2 = Replace(str2, "'", "")
                        End If
                        str2 = Replace(str2, "+", "")
                        'lbUnits.AddItem str2
                        
                        vRich = Split(str2, vbTab)
                        
                        lbUnits.AddItem vRich(0)
                        lbUnits.List(lbUnits.ListCount - 1, 1) = vRich(1)
                        lbUnits.List(lbUnits.ListCount - 1, 2) = vRich(2)
                        lbUnits.List(lbUnits.ListCount - 1, 3) = vRich(3)
                        lbUnits.List(lbUnits.ListCount - 1, 4) = vRich(4)
                    Next i
                    
                    vUnits = Split(vAttList(6).TextString, " + ")
                    For i = 0 To UBound(vUnits)
                        vItem = Split(vUnits(i), ": ")
                        vTemp = Split(vItem(1), "-")
                        If UBound(vTemp) = 0 Then
                            iHO1B = iHO1B + 1
                        Else
                            iHO1B = iHO1B + CInt(vTemp(1)) - CInt(vTemp(0)) + 1
                        End If
Next_sPed_HO1:
                    Next i
                    
                    If iHO1B > 0 Then
                        str2 = str1 & "HO1B" & vbTab & iHO1B & vbTab
                        'lbUnits.AddItem str2
                        
                        vRich = Split(str2, vbTab)
                        
                        lbUnits.AddItem vRich(0)
                        lbUnits.List(lbUnits.ListCount - 1, 1) = vRich(1)
                        lbUnits.List(lbUnits.ListCount - 1, 2) = vRich(2)
                        lbUnits.List(lbUnits.ListCount - 1, 3) = vRich(3)
                        lbUnits.List(lbUnits.ListCount - 1, 4) = vRich(4)
                    End If
                Case "Customer"
                    vAttList = objBlock.GetAttributes
                    
                    Select Case vAttList(5).TextString
                        Case "R", "C", "M", "T", ""
                            iRes = iRes + 1
                            
                            GoTo Next_Object
                        Case "B", "S"
                            iBus = iBus + 1
                            
                            GoTo Next_Object
                    End Select
                Case "cable_span"
                    vAttList = objBlock.GetAttributes
                    str1 = Replace(vAttList(2).TextString, "'", "")
                    
                    Select Case objBlock.Layer
                        Case "Integrity Cable-Aerial Text"
                            iAF = iAF + CInt(str1)
                        Case "Integrity Cable-Buried Text"
                            iBF = iBF + CInt(str1)
                        Case Else
                            iUNK = iUNK + CInt(str1)
                    End Select
                    
                    GoTo Next_Object
                Case "SS Info"
                    vAttList = objBlock.GetAttributes
                    If Not vAttList(2).TextString = "" Then strExchange = vAttList(2).TextString
                    
                    GoTo Next_Object
                Case Else
                    GoTo Next_Object
            End Select
        End If
Next_Object:
    Next objEntity
    
    'lbUnits.AddItem "Data" & vbTab & vbTab & vbTab & "RU" & vbTab & iRes & vbTab
    'lbUnits.AddItem "Data" & vbTab & vbTab & vbTab & "BU" & vbTab & iBus & vbTab
    
    'If iAF > 0 Then lbUnits.AddItem "Data" & vbTab & vbTab & vbTab & "Aerial" & vbTab & iAF & vbTab
    'If iBF > 0 Then lbUnits.AddItem "Data" & vbTab & vbTab & vbTab & "Buried" & vbTab & iBF & vbTab
    'If iUF > 0 Then lbUnits.AddItem "Data" & vbTab & vbTab & vbTab & "UG" & vbTab & iUF & vbTab
    'If iUNK > 0 Then lbUnits.AddItem "Data" & vbTab & vbTab & vbTab & "UNKNOWN" & vbTab & iUNK & vbTab
                        
    lbUnits.AddItem "Data"
    lbUnits.List(lbUnits.ListCount - 1, 1) = ""
    lbUnits.List(lbUnits.ListCount - 1, 2) = "RU"
    lbUnits.List(lbUnits.ListCount - 1, 3) = iRes
    lbUnits.List(lbUnits.ListCount - 1, 4) = ""
                        
    lbUnits.AddItem "Data"
    lbUnits.List(lbUnits.ListCount - 1, 1) = ""
    lbUnits.List(lbUnits.ListCount - 1, 2) = "BU"
    lbUnits.List(lbUnits.ListCount - 1, 3) = iBus
    lbUnits.List(lbUnits.ListCount - 1, 4) = ""
    
    If iAF > 0 Then
        lbUnits.AddItem "Data"
        lbUnits.List(lbUnits.ListCount - 1, 1) = ""
        lbUnits.List(lbUnits.ListCount - 1, 2) = "Aerial"
        lbUnits.List(lbUnits.ListCount - 1, 3) = iAF
        lbUnits.List(lbUnits.ListCount - 1, 4) = ""
    End If
    
    If iBF > 0 Then
        lbUnits.AddItem "Data"
        lbUnits.List(lbUnits.ListCount - 1, 1) = ""
        lbUnits.List(lbUnits.ListCount - 1, 2) = "Buried"
        lbUnits.List(lbUnits.ListCount - 1, 3) = iBF
        lbUnits.List(lbUnits.ListCount - 1, 4) = ""
    End If
    
    If iUF > 0 Then
        lbUnits.AddItem "Data"
        lbUnits.List(lbUnits.ListCount - 1, 1) = ""
        lbUnits.List(lbUnits.ListCount - 1, 2) = "UG"
        lbUnits.List(lbUnits.ListCount - 1, 3) = iUF
        lbUnits.List(lbUnits.ListCount - 1, 4) = ""
    End If
    
    If iUNK > 0 Then
        lbUnits.AddItem "Data"
        lbUnits.List(lbUnits.ListCount - 1, 1) = ""
        lbUnits.List(lbUnits.ListCount - 1, 2) = "Unknown"
        lbUnits.List(lbUnits.ListCount - 1, 3) = iUNK
        lbUnits.List(lbUnits.ListCount - 1, 4) = ""
    End If
    
    str1 = Replace(UCase(ThisDrawing.Name), ".DWG", "")
    'lbUnits.AddItem "Data" & vbTab & vbTab & vbTab & "Project" & vbTab & str1 & vbTab
    lbUnits.AddItem "Data"
    lbUnits.List(lbUnits.ListCount - 1, 1) = ""
    lbUnits.List(lbUnits.ListCount - 1, 2) = "Project"
    lbUnits.List(lbUnits.ListCount - 1, 3) = str1
    lbUnits.List(lbUnits.ListCount - 1, 4) = ""
    
    'lbUnits.AddItem "Data" & vbTab & vbTab & vbTab & "Exchange" & vbTab & strExchange & vbTab
    lbUnits.AddItem "Data"
    lbUnits.List(lbUnits.ListCount - 1, 1) = ""
    lbUnits.List(lbUnits.ListCount - 1, 2) = "Exchange"
    lbUnits.List(lbUnits.ListCount - 1, 3) = strExchange
    lbUnits.List(lbUnits.ListCount - 1, 4) = ""
    
Exit_Sub:

    Me.show
End Sub

Private Sub cbGetSpans_Click()
    If lbSpans.ListCount = 0 Then Exit Sub
    
    Dim strFileName As String
    Dim strDWGName As String
    Dim vLine As Variant
    
    Dim objData As New DataObject
    Dim strCopy As String
    Dim vUnit As Variant
    
    strCopy = ""
    
    For i = 0 To lbSpans.ListCount - 1
        If i = 0 Then
            strCopy = lbSpans.List(i, 0) & "," & lbSpans.List(i, 2)
        Else
            strCopy = strCopy & vbCr & lbSpans.List(i, 0) & "," & lbSpans.List(i, 2)
        End If
    Next i
    
    If cbCopyToFile.Value = True Then
        strFileName = ThisDrawing.Path & "\"
        vLine = Split(ThisDrawing.Name, " ")
        strFileName = strFileName & vLine(0) & "-TAB Spans.csv"

        Open strFileName For Output As #1
        
        Print #1, strCopy
        Close #1
    
        MsgBox "Copied to File"
    Else
        objData.SetText strCopy
        objData.PutInClipboard
    
        MsgBox "Copied to Clipboard"
    End If
End Sub

Private Sub cbGetTotals_Click()
    Dim vUnit, vTemp As Variant
    Dim strTemp As String
    
    'On Error Resume Next
    
    lbSpans.Clear
    lbFinal.Clear
    
    For i = 0 To lbUnits.ListCount - 1
        'vUnit = Split(lbUnits.List(k), vbTab)
        'If vUnit(0) = "xx" Then GoTo Next_K
        'If vUnit(0) = "Data" Then GoTo Next_K
        'If UBound(vUnit) < 3 Then GoTo Next_K
        
        If lbUnits.List(i, 0) = "xx" Then GoTo Next_K
        If lbUnits.List(i, 0) = "Data" Then GoTo Next_K
        If lbUnits.List(i, 1) = "terminal" Then GoTo Next_K
        
        'If vUnit(1) = "terminal" Then GoTo Next_K
        
        'vTemp = Split(vUnit(3), "(")
        vTemp = Split(lbUnits.List(i, 2), "(")
        
        Select Case vTemp(0)
            Case "CO", "BFO", "UO"
                lbSpans.AddItem lbUnits.List(i, 2)
                lbSpans.List(lbSpans.ListCount - 1, 1) = lbUnits.List(i, 4)
                lbSpans.List(lbSpans.ListCount - 1, 2) = lbUnits.List(i, 3)
        End Select
        
        If lbFinal.ListCount = 0 Then
            strTemp = lbUnits.List(i, 2)
            If Not lbUnits.List(i, 4) = "" Then strTemp = strTemp & "  " & lbUnits.List(i, 4)
            
            lbFinal.AddItem strTemp
            lbFinal.List(0, 1) = lbUnits.List(i, 3)
            'lbFinal.List(lbFinal.ListCount - 1, 1) = vUnit(4)
            GoTo Next_K
        End If
        
        For m = 0 To lbFinal.ListCount - 1
            strTemp = lbUnits.List(i, 2)
            'If UBound(vUnit) > 4 Then
            'If Not lbUnits.List(i, 4) = "" Then lbFinal.List(0, 0) = lbFinal.List(0, 0) & "  " & lbUnits.List(i, 4)
            If Not lbUnits.List(i, 4) = "" Then strTemp = strTemp & "  " & lbUnits.List(i, 4)
            'End If
            'If Not Err = 0 Then
            
            If lbFinal.List(m, 0) = strTemp Then
                lbFinal.List(m, 1) = CLng(lbFinal.List(m, 1)) + CLng(lbUnits.List(i, 3))
                GoTo Next_K
            End If
        Next m
        
        lbFinal.AddItem strTemp
        lbFinal.List(lbFinal.ListCount - 1, 1) = lbUnits.List(i, 3)
        'If UBound(vUnit) > 4 Then
            'If Not vUnit(5) = "" Then lbFinal.List(lbFinal.ListCount - 1, 0) = lbFinal.List(lbFinal.ListCount - 1, 0) & "  " & vUnit(5)
        'End If
Next_K:
    Next i
End Sub

Private Sub cbGetUnits_Click()
    Dim objEntity As AcadEntity
    Dim obrTemp As AcadBlockReference
    Dim objLWP As AcadLWPolyline
    Dim attList, vUnit, vClosure As Variant
    Dim vReturnPnt, vCoords As Variant
    Dim vTemp, vRich As Variant
    Dim str1, str2, strUnit As String
    Dim strExchange As String
    Dim filterType, filterValue As Variant
    Dim vPnt1, vPnt2 As Variant
    Dim grpCode(0) As Integer
    Dim grpValue(0) As Variant
    Dim dPnt1(0 To 2) As Double
    Dim dPnt2(0 To 2) As Double
    Dim iRes, iBus As Integer
    Dim iAF, iBF, iUF, iUNK As Integer
    Dim iTemp, iCounter As Integer
    Dim dCoords() As Double
    
    iRes = 0: iBus = 0
    iAF = 0: iBF = 0: iUF = 0: iUNK = 0
    strExchange = ""

    grpCode(0) = 2
    grpValue(0) = "pole_unit,cable_span,SS Info,Customer,Callout"
    'grpValue(0) = "pole_unit,terminal,RES,BUSINESS,TRLR,MDU,CHURCH,SCHOOL,cable_span,SS Info,Customer,Callout"
    filterType = grpCode
    filterValue = grpValue
    
    lbUnits.Clear
    lbNotFound.Clear
    
  On Error Resume Next
    Me.Hide
    
    objSS.Clear
    
    Select Case cbSelection.Value
        Case "Window"
            vPnt1 = ThisDrawing.Utility.GetPoint(, "Get BL Corner: ")
            vPnt2 = ThisDrawing.Utility.GetCorner(vPnt1, vbCr & "Get UR Corner: ")
            
            dPnt1(0) = vPnt1(0)
            dPnt1(1) = vPnt1(1)
            dPnt1(2) = vPnt1(2)
            
            dPnt2(0) = vPnt2(0)
            dPnt2(1) = vPnt2(1)
            dPnt2(2) = vPnt2(2)
            
            objSS.Select acSelectionSetWindow, dPnt1, dPnt2, filterType, filterValue
        Case Else
            ThisDrawing.Utility.GetEntity objEntity, vReturnPnt, "Select Polygon Border: "
            If Not objEntity.ObjectName = "AcDbPolyline" Then
                MsgBox "Error: Invalid Selection."
                Me.show
                Exit Sub
            End If
            
            Set objLWP = objEntity
            vCoords = objLWP.Coordinates
            
            iTemp = (UBound(vCoords) + 1) / 2 * 3 - 1
            ReDim dCoords(iTemp) As Double
            
            iCounter = 0
            For i = 0 To UBound(vCoords) Step 2
                dCoords(iCounter) = vCoords(i)
                iCounter = iCounter + 1
                dCoords(iCounter) = vCoords(i + 1)
                iCounter = iCounter + 1
                dCoords(iCounter) = 0#
                iCounter = iCounter + 1
            Next i
            
            objSS.SelectByPolygon acSelectionSetCrossingPolygon, dCoords, filterType, filterValue
    End Select
    
    
    For Each objEntity In objSS
        If TypeOf objEntity Is AcadBlockReference Then
            Set obrTemp = objEntity
            
            If obrTemp.Layer = "Integrity Future" Then GoTo Next_Object
            
            Select Case obrTemp.Name
                Case "pole_unit"
                    attList = obrTemp.GetAttributes
                    
                    If attList(0).TextString = "xx" Then GoTo Next_Object
                    If attList(3).TextString = "" Then GoTo Next_Object
                    
                    str1 = attList(0).TextString & vbTab & obrTemp.Name
                    str2 = attList(3).TextString
                    
                    strUnit = Replace(str2, "+", "")
                    vUnit = Split(strUnit, "=")
                    If UBound(vUnit) > 0 Then
                        vUnit(1) = Replace(vUnit(1), "'", "")
                    Else
                        lbNotFound.AddItem str1 & vbTab & strUnit
                        GoTo Next_Object
                    End If
                    
                    If Left(vUnit(0), 4) = "HACO" Or Left(vUnit(0), 4) = "HBFO" Then
                        vClosure = Split(vUnit(1), "  ")
                        str1 = str1 & vbTab & vUnit(0) & vbTab & vClosure(0)
                        If UBound(vClosure) > 0 Then
                            str1 = str1 & vbTab & vClosure(1)
                        Else
                            str1 = str1 & vbTab & vbTab
                        End If
                    Else
                        Select Case Right(vUnit(1), 1)
                            Case "'"
                                vUnit(1) = Left(vUnit(1), Len(vUnit(1)) - 1)
                                str1 = str1 & vbTab & vUnit(0) & vbTab & vUnit(1) & vbTab
                            Case ")"
                                vTemp = Split(vUnit(1), " (")
                                If Right(vTemp(0), 1) = "'" Then vTemp(0) = Left(vTemp(0), Len(vTemp(0)) - 1)
                                vUnit(1) = vTemp(0)
                                str1 = str1 & vbTab & vUnit(0) & vbTab & vTemp(0) & vbTab & Left(vTemp(1), Len(vTemp(1)) - 1)
                            Case Else
                                If InStr(vUnit(1), "  ") > 0 Then
                                    vUnit(1) = Replace(vUnit(1), "  ", vbTab)
                                    str1 = str1 & vbTab & vUnit(0) & vbTab & vUnit(1)
                                Else
                                    str1 = str1 & vbTab & vUnit(0) & vbTab & vUnit(1) & vbTab
                                End If
                        End Select
                    End If
                Case "Callout"
                    attList = obrTemp.GetAttributes
                    
                    If obrTemp.Layer = "Integrity Existing" Then GoTo Next_Object
                    
                    If Not Left(attList(1).TextString, 1) = "+" Then GoTo Next_Object
                    'If InStr(attList(1).TextString, "+HO1") < 1 Then GoTo Next_Object
                    
                    str1 = vbTab & vbTab
                    str2 = Replace(attList(1).TextString, "+", "")
                    vUnit = Split(str2, "=")
                    
                    If UBound(vUnit) > 0 Then
                        str1 = str1 & vUnit(0) & vbTab & vUnit(1) & vbTab
                    Else
                        lbNotFound.AddItem str1 & vbTab & strUnit
                        GoTo Next_Object
                    End If
                Case "Customer"
                    attList = obrTemp.GetAttributes
                    
                    Select Case attList(5).TextString
                        Case "R", "C", "M", "T", "L", ""
                            iRes = iRes + 1
                        Case "B", "S"
                            iBus = iBus + 1
                    End Select
                    
                    GoTo Next_Object
                Case "cable_span"
                    attList = obrTemp.GetAttributes
                    str1 = Replace(attList(2).TextString, "'", "")
                    
                    Select Case obrTemp.Layer
                        Case "Integrity Cable-Aerial Text"
                            iAF = iAF + CInt(str1)
                        Case "Integrity Cable-Buried Text"
                            iBF = iBF + CInt(str1)
                        Case Else
                            iUNK = iUNK + CInt(str1)
                    End Select
                    
                    GoTo Next_Object
                Case "SS Info"
                    attList = obrTemp.GetAttributes
                    If Not attList(2).TextString = "" Then strExchange = attList(2).TextString
                    
                    GoTo Next_Object
                Case Else
                    GoTo Next_Object
            End Select
            
            'lbUnits.AddItem str1
                        
            vRich = Split(str1, vbTab)
                        
            lbUnits.AddItem vRich(0)
            lbUnits.List(lbUnits.ListCount - 1, 1) = vRich(1)
            lbUnits.List(lbUnits.ListCount - 1, 2) = vRich(2)
            lbUnits.List(lbUnits.ListCount - 1, 3) = vRich(3)
            lbUnits.List(lbUnits.ListCount - 1, 4) = vRich(4)
            
        End If
Next_Object:
    Next objEntity
    
    'lbUnits.AddItem "Data" & vbTab & vbTab & vbTab & "RU" & vbTab & iRes & vbTab
    'lbUnits.AddItem "Data" & vbTab & vbTab & vbTab & "BU" & vbTab & iBus & vbTab
    
    'If iAF > 0 Then lbUnits.AddItem "Data" & vbTab & vbTab & vbTab & "Aerial" & vbTab & iAF & vbTab
    'If iBF > 0 Then lbUnits.AddItem "Data" & vbTab & vbTab & vbTab & "Buried" & vbTab & iBF & vbTab
    'If iUF > 0 Then lbUnits.AddItem "Data" & vbTab & vbTab & vbTab & "UG" & vbTab & iUF & vbTab
    'If iUNK > 0 Then lbUnits.AddItem "Data" & vbTab & vbTab & vbTab & "UNKNOWN" & vbTab & iUNK & vbTab
                        
    lbUnits.AddItem "Data"
    lbUnits.List(lbUnits.ListCount - 1, 1) = ""
    lbUnits.List(lbUnits.ListCount - 1, 2) = "RU"
    lbUnits.List(lbUnits.ListCount - 1, 3) = iRes
    lbUnits.List(lbUnits.ListCount - 1, 4) = ""
                        
    lbUnits.AddItem "Data"
    lbUnits.List(lbUnits.ListCount - 1, 1) = ""
    lbUnits.List(lbUnits.ListCount - 1, 2) = "BU"
    lbUnits.List(lbUnits.ListCount - 1, 3) = iBus
    lbUnits.List(lbUnits.ListCount - 1, 4) = ""
    
    If iAF > 0 Then
        lbUnits.AddItem "Data"
        lbUnits.List(lbUnits.ListCount - 1, 1) = ""
        lbUnits.List(lbUnits.ListCount - 1, 2) = "Aerial"
        lbUnits.List(lbUnits.ListCount - 1, 3) = iAF
        lbUnits.List(lbUnits.ListCount - 1, 4) = ""
    End If
    
    If iBF > 0 Then
        lbUnits.AddItem "Data"
        lbUnits.List(lbUnits.ListCount - 1, 1) = ""
        lbUnits.List(lbUnits.ListCount - 1, 2) = "Buried"
        lbUnits.List(lbUnits.ListCount - 1, 3) = iBF
        lbUnits.List(lbUnits.ListCount - 1, 4) = ""
    End If
    
    If iUF > 0 Then
        lbUnits.AddItem "Data"
        lbUnits.List(lbUnits.ListCount - 1, 1) = ""
        lbUnits.List(lbUnits.ListCount - 1, 2) = "UG"
        lbUnits.List(lbUnits.ListCount - 1, 3) = iUF
        lbUnits.List(lbUnits.ListCount - 1, 4) = ""
    End If
    
    If iUNK > 0 Then
        lbUnits.AddItem "Data"
        lbUnits.List(lbUnits.ListCount - 1, 1) = ""
        lbUnits.List(lbUnits.ListCount - 1, 2) = "Unknown"
        lbUnits.List(lbUnits.ListCount - 1, 3) = iUNK
        lbUnits.List(lbUnits.ListCount - 1, 4) = ""
    End If
    
    str1 = Replace(UCase(ThisDrawing.Name), ".DWG", "")
    'lbUnits.AddItem "Data" & vbTab & vbTab & vbTab & "Project" & vbTab & str1 & vbTab
    lbUnits.AddItem "Data"
    lbUnits.List(lbUnits.ListCount - 1, 1) = ""
    lbUnits.List(lbUnits.ListCount - 1, 2) = "Project"
    lbUnits.List(lbUnits.ListCount - 1, 3) = str1
    lbUnits.List(lbUnits.ListCount - 1, 4) = ""
    
    'lbUnits.AddItem "Data" & vbTab & vbTab & vbTab & "Exchange" & vbTab & strExchange & vbTab
    lbUnits.AddItem "Data"
    lbUnits.List(lbUnits.ListCount - 1, 1) = ""
    lbUnits.List(lbUnits.ListCount - 1, 2) = "Exchange"
    lbUnits.List(lbUnits.ListCount - 1, 3) = strExchange
    lbUnits.List(lbUnits.ListCount - 1, 4) = ""
    
    'str1 = Replace(UCase(ThisDrawing.Name), ".DWG", "")
    'lbUnits.AddItem "Data" & vbTab & vbTab & vbTab & "Project" & vbTab & str1 & vbTab
    
    'lbUnits.AddItem "Data" & vbTab & vbTab & vbTab & "Exchange" & vbTab & strExchange & vbTab
    
Exit_Sub:
    
    Me.show
    
    'If Not Err = 0 Then MsgBox Err.Number & vbCr & Err.Description
End Sub

Private Sub cbQuit_Click()
    Me.Hide
End Sub

Private Sub cbSort_Click()
    Dim strTemp, strTotal As String
    Dim iCount, iOffset As Integer
    Dim iIndex As Integer
    
    iCount = lbFinal.ListCount - 1
    
    For a = iCount To 0 Step -1
        For b = 0 To a - 1
            If lbFinal.List(b, 0) > lbFinal.List(b + 1, 0) Then
                strTemp = lbFinal.List(b + 1, 0)
                strTotal = lbFinal.List(b + 1, 1)
                
                lbFinal.List(b + 1, 0) = lbFinal.List(b, 0)
                lbFinal.List(b + 1, 1) = lbFinal.List(b, 1)
                
                lbFinal.List(b, 0) = strTemp
                lbFinal.List(b, 1) = strTotal
            End If
        Next b
    Next a
    
    iOffset = 0
    For c = 1 To lbFinal.ListCount - 1
        iIndex = c - iOffset
        If lbFinal.List(iIndex, 0) = lbFinal.List(iIndex - 1, 0) Then
            lbFinal.List(iIndex - 1, 1) = CInt(lbFinal.List(iIndex - 1, 1)) + CInt(lbFinal.List(iIndex, 1))
            lbFinal.RemoveItem iIndex
            iOffset = iOffset + 1
        End If
    Next c
End Sub

Private Sub cbUpdate_Click()
    Dim iListIndex As Integer
    Dim strLine As String
    
    'strLine = tbPole.Value & vbTab & tbPosition.Value & vbTab & tbDWG.Value & vbTab & tbLine.Value & vbTab & tbAmount.Value & vbTab & tbNote.Value
    
    iListIndex = lbFinal.ListIndex
    
    lbFinal.List(iListIndex, 0) = tbLine.Value
    lbFinal.List(iListIndex, 1) = tbAmount.Value
    
    'lbNotFound.RemoveItem iListIndex
    'lbUnits.AddItem strLine 'tbUnit.Value
    'lbNotFound.ListIndex = iListIndex
    
    tbLine.Value = ""
    tbAmount.Value = ""
End Sub

Private Sub lbFinal_DblClick(ByVal Cancel As MSForms.ReturnBoolean)
    'Dim vUnit, vTemp As Variant
    
    'vUnit = Split(lbNotFound.Value, vbTab)
    
    tbLine.Value = lbFinal.List(lbFinal.ListIndex, 0)
    tbAmount.Value = lbFinal.List(lbFinal.ListIndex, 1)
End Sub

Private Sub lbUnits_KeyDown(ByVal KeyCode As MSForms.ReturnInteger, ByVal Shift As Integer)
    'tbNewValue.Value = ""
    'tbNewValue.Enabled = False
    
    Select Case KeyCode
        Case vbKeyDelete
            lbUnits.RemoveItem lbUnits.ListIndex
    End Select
End Sub

Private Sub UserForm_Initialize()
    lbSpans.Clear
    lbSpans.ColumnCount = 3
    lbSpans.ColumnWidths = "80;30;50"
    
    lbFinal.Clear
    lbFinal.ColumnCount = 2
    lbFinal.ColumnWidths = "140;40"
    
    lbUnits.Clear
    lbUnits.ColumnCount = 5
    lbUnits.ColumnWidths = "108;30;96;48;42"
    
    cbSelection.AddItem "Window"
    cbSelection.AddItem "Polygon"
    cbSelection.Value = "Window"
    
    On Error Resume Next
    
    Set objSS = ThisDrawing.SelectionSets.Add("objSS")
    If Not Err = 0 Then
        Set objSS = ThisDrawing.SelectionSets.Item("objSS")
        Err = 0
    End If
End Sub

Private Sub UserForm_Terminate()
    objSS.Clear
    objSS.Delete
End Sub

Attribute VB_Name = "TemplateEditor"
Attribute VB_Base = "0{BC4C6479-7DCC-45E4-B04D-FD48C2BD3133}{19A708B6-618E-44E9-BED9-791451CB3B90}"
Attribute VB_GlobalNameSpace = False
Attribute VB_Creatable = False
Attribute VB_PredeclaredId = True
Attribute VB_Exposed = False
Attribute VB_TemplateDerived = False
Attribute VB_Customizable = False

Dim iIsVar As Integer
Dim strFLetter, strLLetter As String

Private Sub cbAdd_Click()
    Call AllOn
    
    lbCond.List(lbCond.ListIndex, 2) = tbValue.Value
    tbValue.Value = ""
    cbAdd.Enabled = False
    tbValue.Enabled = False
End Sub

Private Sub cbAddNoteColor_Click()
    Dim strLine, strText, strFront, strEnd As String
    Dim iStart, iEnd As Integer
    
    strLine = Replace(tbSpecial.Value, vbLf, "")
    strText = Replace(tbSpecial.SelText, vbLf, "")
    If Right(strText, 1) = vbCr Then strText = Left(strText, Len(strText) - 1)
    
    iStart = InStr(strLine, strText) - 1
    iEnd = iStart + Len(strText)
    
    strFront = Left(strLine, iStart)
    strEnd = Right(strLine, Len(strLine) - iEnd)
    
    'MsgBox "Total: " & Len(strLine) & vbCr & "Start: " & iStart & vbCr & "End: " & iEnd
    
    tbSpecial.Value = strFront & "<p style=""color:" & cbNoteColor.Value & """>" & strText & "</p>" & strEnd
    
    
    
    
    'Dim strText As String
    'Dim iStart, iLength, iTemp As Integer
    'Dim vTemp As Variant
    
    'vTemp = Split(tbSpecial.Value, vbCrLf)
    'iTemp = UBound(vTemp)
    
    'tbSpecial.Value = tbSpecial.Value & "<p style=""color:" & cbNoteColor.Value & """>**add text here**</p>"
    'iStart = Len(tbSpecial.Value) - 21 - iTemp
    'iLength = 17
    'tbSpecial.SelStart = iStart
    'tbSpecial.SelLength = iLength
End Sub

Private Sub cbAddNotesTable_Click()
    Dim strText, strLine As String
    Dim iSelStart As Integer
    
    iSelStart = tbSpecial.SelStart
    strText = Replace(tbSpecial.Value, vbCr, "")
    
    strLine = "<table>" & vbCr & "<tr>Item = Value" & vbCr & "<tr>Item = Value" & vbCr & "<tr>Item = Value" & vbCr & "<tr>Item = Value" & vbCr & "</table>"
    tbSpecial.Value = Left(strText, iSelStart) & strLine & Mid(strText, iSelStart + 1)
End Sub

Private Sub cbAddSOWColor_Click()
    Dim strLine, strText, strFront, strEnd As String
    Dim iStart, iEnd As Integer
    
    strLine = Replace(tbSOW.Value, vbLf, "")
    strText = Replace(tbSOW.SelText, vbLf, "")
    If Right(strText, 1) = vbCr Then strText = Left(strText, Len(strText) - 1)
    
    iStart = InStr(strLine, strText) - 1
    iEnd = iStart + Len(strText)
    
    strFront = Left(strLine, iStart)
    strEnd = Right(strLine, Len(strLine) - iEnd)
    
    'MsgBox "Total: " & Len(strLine) & vbCr & "Start: " & iStart & vbCr & "End: " & iEnd
    
    tbSOW.Value = strFront & "<p style=""color:" & cbSOWColor.Value & """>" & strText & "</p>" & strEnd
End Sub

Private Sub cbAddTable_Click()
    Dim strText, strLine As String
    Dim iSelStart As Integer
    
    iSelStart = tbSOW.SelStart
    strText = Replace(tbSOW.Value, vbCr, "")
    
    strLine = "<table>" & vbCr & "<tr>Item = Value" & vbCr & "<tr>Item = Value" & vbCr & "<tr>Item = Value" & vbCr & "<tr>Item = Value" & vbCr & "</table>"
    tbSOW.Value = Left(strText, iSelStart) & strLine & Mid(strText, iSelStart + 1)
End Sub

Private Sub cbCreate_Click()
    If cbName.Value = "" Then Exit Sub
    
    Dim strFileName As String
    Dim strPath As String
    Dim strLine As String
    Dim vTemp As Variant
    
    strPath = ThisDrawing.Path & "\"
    vTemp = Split(LCase(strPath), "dropbox")
    strFileName = vTemp(0) & "Dropbox\UNITED COMMUNICATIONS JOB INFORMATION\1-JOBS\PLANNING\SCOPE TEMPLATES\"
    strFileName = strFileName & cbName.Value & ".swt"
    
    'MsgBox strFileName
    'Exit Sub

    Open strFileName For Output As #1
    
    Print #1, "[[INSTRUCTIONS]]"
    Print #1, tbSpecial.Value
    Print #1, "[[SCOPE]]"
    Print #1, tbSOW.Value
    Print #1, "[[CONDITIONS]]"
    If lbCond.ListCount > 0 Then
        For i = 0 To lbCond.ListCount - 1
            strLine = lbCond.List(i, 0) & "=" & lbCond.List(i, 1) & "=" & lbCond.List(i, 2)
            Print #1, strLine
        Next i
    End If
    
    Close #1
    
    MsgBox "Saved"
End Sub

Private Sub cbGetExisting_Click()
    If cbName.Value = "" Then Exit Sub
    
    lbVar.Clear
    lbCond.Clear
    tbSpecial.Value = ""
    tbSOW.Value = ""
    
    Dim strFileName As String
    Dim strPath As String
    Dim strLine As String
    Dim vLine, vTemp, vVar As Variant
    Dim fName As String
    Dim iStatus As Integer
    
    iStatus = 0
    
    strPath = ThisDrawing.Path & "\"
    vTemp = Split(LCase(strPath), "dropbox")
    strFileName = vTemp(0) & "Dropbox\UNITED COMMUNICATIONS JOB INFORMATION\1-JOBS\PLANNING\SCOPE TEMPLATES\"
    strFileName = strFileName & cbName.Value & ".swt"
    
    fName = Dir(strFileName)
    If fName = "" Then
        Exit Sub
    End If
    
    Open strFileName For Input As #2
    
    'MsgBox strFileName
    'Exit Sub
    
    While Not EOF(2)
        Line Input #2, strLine
        
        If InStr(strLine, ">>") > 0 And Not iStatus = 3 Then
            vLine = Split(strLine, ">>")
            For j = 0 To UBound(vLine) - 1
                vTemp = Split(vLine(j), "<<")
                vVar = Split(vTemp(1), "/")
            
                'If lbVariables.ListCount < 0 Then
                    For i = 0 To lbVar.ListCount - 1
                        If lbVar.List(i, 0) = vVar(0) Then GoTo Skip_Adding_Var
                    Next i
                'End If
            
                lbVar.AddItem vVar(0)
                If UBound(vVar) > 0 Then
                    lbVar.List(lbVar.ListCount - 1, 1) = Replace(vVar(1), ">>", "")
                Else
                    lbVar.List(lbVar.ListCount - 1, 1) = "<Empty>"
                End If
        
Skip_Adding_Var:
            Next j
            
            If UBound(vLine) > 2 Then
                For i = 1 To UBound(vLine) - 1
                    vTemp = Split(vLine(i), "<<")
                    vVar = Split(vTemp(1), "/")
            
                    'For j = 0 To lbVariables.ListCount - 1
                        'If lbVariables.List(j, 0) = vVar(0) Then GoTo Skip_Adding_This
                    'Next j
            
                    lbVar.AddItem vVar(0)
                    If UBound(vVar) > 0 Then
                        lbVar.List(lbVar.ListCount - 1, 1) = Replace(vVar(1), ">>", "")
                    Else
                        lbVar.List(lbVar.ListCount - 1, 1) = "<Empty>"
                    End If
Skip_Adding_This:
                    'cbFind.AddItem "<<" & vTemp(1) & ">>"
                Next i
            End If
        End If
        
        If Left(strLine, 2) = "[[" Then
            Select Case Left(strLine, 3)
                Case "[[I"
                    iStatus = 1
                Case "[[S"
                    iStatus = 2
                Case "[[C"
                    iStatus = 3
            End Select
        Else
            Select Case iStatus
                Case Is = 1
                    If tbSpecial.Value = "" Then
                        tbSpecial.Value = strLine
                    Else
                        tbSpecial.Value = tbSpecial.Value & vbCr & strLine
                    End If
                Case Is = 2
                    If tbSOW.Value = "" Then
                        tbSOW.Value = strLine
                    Else
                        tbSOW.Value = tbSOW.Value & vbCr & strLine
                    End If
                Case Is = 3
                    '<---------------------------------------------------------------------
                    vCond = Split(strLine, "=")
                    lbCond.AddItem vCond(0)
                    lbCond.List(lbCond.ListCount - 1, 1) = vCond(1)
                    lbCond.List(lbCond.ListCount - 1, 2) = vCond(2)
            End Select
        End If
    Wend
    
    Close #2
End Sub

Private Sub cbQuit_Click()
    Me.Hide
End Sub

Private Sub Label24_Click()
    tbValue.Value = "<p style=""color:orange"">" & tbValue.Value & "</P>"
End Sub

Private Sub Label25_Click()
    tbValue.Value = "<p style=""color:green"">" & tbValue.Value & "</P>"
End Sub

Private Sub Label26_Click()
    tbValue.Value = "<p style=""color:blue"">" & tbValue.Value & "</P>"
End Sub

Private Sub Label27_Click()
    tbValue.Value = "<p style=""color:purple"">" & tbValue.Value & "</P>"
End Sub

Private Sub LabelPan_Click()
    Dim entPole As AcadObject
    Dim basePnt As Variant
    
    Me.Hide
  On Error Resume Next
    
    ThisDrawing.Utility.GetEntity entPole, basePnt, "Left Click to Exit: "
    
    Me.show
End Sub

Private Sub lbCond_DblClick(ByVal Cancel As MSForms.ReturnBoolean)
    Call AllOff
    
    tbValue.Enabled = True
    
    If Not lbCond.List(lbCond.ListIndex, 2) = "" Then tbValue.Value = lbCond.List(lbCond.ListIndex, 2)
    
    cbAdd.Enabled = True
    tbValue.SetFocus
End Sub

Private Sub lbCond_KeyDown(ByVal KeyCode As MSForms.ReturnInteger, ByVal Shift As Integer)
    Select Case KeyCode
        Case vbKeyDelete
            lbCond.RemoveItem lbCond.ListIndex
            'MsgBox "Deleted"
        Case Else
    End Select
End Sub

Private Sub lbVar_DblClick(ByVal Cancel As MSForms.ReturnBoolean)
    Dim strPre, strPost As String
    Dim strPVar, strPList As String
    Dim strSVar, strSList As String
    Dim strTemp As String
    Dim vList As Variant
    Dim iIndex As Integer
    
    iIndex = lbVar.ListIndex
    
    If lbVar.List(iIndex, 1) = "<Empty>" Then Exit Sub
    
    strPVar = lbVar.List(iIndex, 0)
    strPList = lbVar.List(iIndex, 1)
    strPre = "<<" & strPVar & "/" & strPList & ">>"
    
    Load TemplateVarEdit
        TemplateVarEdit.tbVar.Value = strPVar
        TemplateVarEdit.tbList.Value = Replace(strPList, ",", vbCr)
        TemplateVarEdit.show
        
        strSVar = TemplateVarEdit.tbVar.Value
        strSList = Replace(TemplateVarEdit.tbList.Value, vbCr, ",")
        strSList = Replace(strSList, vbLf, "")
    Unload TemplateVarEdit
    
    If strSVar = strPVar Then
        If strSList = strPList Then Exit Sub
    Else
        If lbCond.ListCount > 0 Then
            For i = 0 To lbCond.ListCount - 1
                If lbCond.List(i, 0) = strPVar Then lbCond.List(i, 0) = strSVar
            Next i
            
            lbVar.List(iIndex, 0) = strSVar
        
            strTemp = Replace(tbSpecial.Value, "{{" & strPVar & "}}", "{{" & strSVar & "}}")
            tbSpecial.Value = strTemp
        
            strTemp = Replace(tbSOW.Value, "{{" & strPVar & "}}", "{{" & strSVar & "}}")
            tbSOW.Value = strTemp
        End If
    End If
    
    lbVar.List(iIndex, 1) = strSList
    
    strPost = "<<" & lbVar.List(iIndex, 0) & "/" & strSList & ">>"
        
    strTemp = Replace(tbSpecial.Value, strPre, strPost)
    tbSpecial.Value = strTemp
        
    strTemp = Replace(tbSOW.Value, strPre, strPost)
    tbSOW.Value = strTemp
        
    vList = Split(strSList, ",")
        
    For i = 0 To lbCond.ListCount - 1
        If lbCond.List(i, 0) = strPVar Then GoTo Found_lbCond
    Next i
    Exit Sub
        
Found_lbCond:
    
    If lbCond.ListCount < 1 Then Exit Sub
    For j = 0 To UBound(vList)
        If i > lbCond.ListCount - 1 Then
            lbCond.AddItem strPVar
            lbCond.List(lbCond.ListCount - 1, 1) = vList(j)
        Else
            If strPVar = lbCond.List(i, 0) Then
                lbCond.List(i, 1) = vList(j)
            Else
                lbCond.AddItem strPVar, i
                lbCond.List(i, 1) = vList(j)
            End If
        End If
            
        i = i + 1
    Next j
    
End Sub

Private Sub lbVar_KeyDown(ByVal KeyCode As MSForms.ReturnInteger, ByVal Shift As Integer)
    Select Case KeyCode
        Case vbKeyDelete
            lbVar.RemoveItem lbVar.ListIndex
            'MsgBox "Deleted"
        Case Else
    End Select
End Sub

Private Sub LRedNote_Click()
    Dim strText As String
    Dim iStart, iLength, iTemp As Integer
    Dim vTemp As Variant
    
    vTemp = Split(tbSpecial.Value, vbCrLf)
    iTemp = UBound(vTemp)
    
    tbSpecial.Value = tbSpecial.Value & "<p style=""color:red"">**add text here**</p>"
    iStart = Len(tbSpecial.Value) - 21 - iTemp
    iLength = 17
    tbSpecial.SelStart = iStart
    tbSpecial.SelLength = iLength
End Sub

Private Sub LRedSOW_Click()
    Dim strLine, strText, strFront, strEnd As String
    Dim iStart, iEnd As Integer
    
    strLine = Replace(tbSOW.Value, vbLf, "")
    strText = Replace(tbSOW.SelText, vbLf, "")
    If Right(strText, 1) = vbCr Then strText = Left(strText, Len(strText) - 1)
    
    iStart = InStr(strLine, strText) - 1
    iEnd = iStart + Len(strText)
    
    strFront = Left(strLine, iStart)
    strEnd = Right(strLine, Len(strLine) - iEnd)
    
    'MsgBox "Total: " & Len(strLine) & vbCr & "Start: " & iStart & vbCr & "End: " & iEnd
    
    tbSOW.Value = strFront & "<p style=""color:red"">" & strText & "</p>" & strEnd
    
    'Dim strFind, strReplace As String
    
    'strFind = tbSOW.SelText
    'strReplace = "<p style=""color:red"">" & strFind & "</p>"
    
    'tbSOW.Value = Replace(tbSOW.Value, strFind, strReplace)
End Sub

Private Sub LRedText_Click()
    tbValue.Value = "<p style=""color:red"">" & tbValue.Value & "</P>"
End Sub

Private Sub tbSOW_KeyUp(ByVal KeyCode As MSForms.ReturnInteger, ByVal Shift As Integer)
    Dim strKey As String
    
    'MsgBox KeyCode
    
    Select Case KeyCode
        Case Is = 188
            If strFLetter = "<" Then
                iIsVar = 2
                Call AllOff
                tbVar.Enabled = True
                tbVar.SetFocus
            Else
                strFLetter = "<"
            End If
        Case Is = 219
            If strFLetter = "{" Then
                
                Load TemplateList
                    For i = 0 To lbVar.ListCount - 1
                        If Not lbVar.List(i, 1) = "<Empty>" Then
                            If lbCond.ListCount < 0 Then
                                TemplateList.cbList.AddItem lbVar.List(i, 0)
                            Else
                                For j = 0 To lbCond.ListCount - 1
                                    If lbCond.List(j, 0) = lbVar.List(i, 0) Then GoTo Found_Cond
                                Next j
                                
                                TemplateList.cbList.AddItem lbVar.List(i, 0)
                            End If
Found_Cond:
                        End If
                    Next i
                    
                    If TemplateList.cbList.ListCount < 1 Then
                        MsgBox "No Variables with a List exist."
                        Unload TemplateList
                        GoTo Exit_Sub
                    'Else
                        'If Not lbCond.ListCount < 0 Then
                            'For j = 0 To TemplateList.cbList.ListCount - 1
                                'For k = 0 To lbCond.ListCount - 1
                                    'If TemplateList.cbList.List(j, 0) = lbCond.List(k, 0) Then
                                    'End If
                                'Next k
                            'Next j
                        'End If
                    End If
                    
                    TemplateList.show
                    strTemp = TemplateList.cbList.Value
                    
                    iSelStart = tbSOW.SelStart
                    strText = Replace(tbSOW.Value, vbCr, "")
                    tbSOW.Value = Left(strText, iSelStart) & strTemp & "}}" & Mid(strText, iSelStart + 1)
                    tbSOW.SelStart = iSelStart + Len(strTemp) + 2
                    tbSOW.SetFocus
                    
                    For i = 0 To lbVar.ListCount - 1
                        If lbVar.List(i, 0) = strTemp Then
                            vLine = Split(lbVar.List(i, 1), ",")
                            
                            For n = 0 To UBound(vLine)
                                lbCond.AddItem lbVar.List(i, 0)
                                lbCond.List(lbCond.ListCount - 1, 1) = vLine(n)
                            Next n
                        End If
                    Next i
                    
                Unload TemplateList
                iIsVar = 0
            Else
                strFLetter = "{"
            End If
        Case Else
            strFLetter = ""
    End Select
Exit_Sub:
    
End Sub

Private Sub tbSpecial_KeyUp(ByVal KeyCode As MSForms.ReturnInteger, ByVal Shift As Integer)
    Dim vLine As Variant
    Dim strKey As String
    Dim strText, strTemp As String
    Dim iSelStart As Integer
    
    'MsgBox KeyCode
    
    Select Case KeyCode
        Case Is = 188
            If strFLetter = "<" Then
                iIsVar = 1
                Call AllOff
                tbVar.Enabled = True
                tbVar.SetFocus
            Else
                strFLetter = "<"
            End If
        Case Is = 219
            If strFLetter = "{" Then
                
                Load TemplateList
                    For i = 0 To lbVar.ListCount - 1
                        If Not lbVar.List(i, 1) = "<Empty>" Then
                            TemplateList.cbList.AddItem lbVar.List(i, 0)
                        End If
                    Next i
                    
                    If TemplateList.cbList.ListCount < 1 Then
                        MsgBox "No Variables with a List exist."
                        Unload TemplateList
                        GoTo Exit_Sub
                    End If
                    
                    TemplateList.show
                    strTemp = TemplateList.cbList.Value
                    
                    iSelStart = tbSpecial.SelStart
                    strText = Replace(tbSpecial.Value, vbCr, "")
                    tbSpecial.Value = Left(strText, iSelStart) & strTemp & "}}" & Mid(strText, iSelStart + 1)
                    tbSpecial.SelStart = iSelStart + Len(strTemp) + 2
                    tbSpecial.SetFocus
                    
                    For i = 0 To lbVar.ListCount - 1
                        If lbVar.List(i, 0) = strTemp Then
                            vLine = Split(lbVar.List(i, 1), ",")
                            
                            For n = 0 To UBound(vLine)
                                lbCond.AddItem lbVar.List(i, 0)
                                lbCond.List(lbCond.ListCount - 1, 1) = vLine(n)
                            Next n
                        End If
                    Next i
                    
                Unload TemplateList
                iIsVar = 0
            Else
                strFLetter = "{"
            End If
        Case Else
            strFLetter = ""
    End Select
Exit_Sub:
    
End Sub

Private Sub tbVar_Change()
    Dim vLine As Variant
    Dim strText As String
    Dim iSelStart As Integer
    
    If Right(tbVar.Value, 1) = "/" Then
        Call AllOn
        strText = Left(tbVar.Value, Len(tbVar.Value) - 1)
        For i = 0 To lbVar.ListCount - 1
            If lbVar.List(i, 0) = strText Then
                tbVar.Value = tbVar.Value & lbVar.List(i, 1)
        
                Select Case iIsVar
                    Case Is = 1
                        iSelStart = tbSpecial.SelStart
                        strText = Replace(tbSpecial.Value, vbCr, "")
                        tbSpecial.Value = Left(strText, iSelStart) & tbVar.Value & ">>" & Mid(strText, iSelStart + 1)
                        tbSpecial.SelStart = iSelStart + Len(tbVar.Value) + 2
                        tbSpecial.SetFocus
                    Case Is = 2
                        iSelStart = tbSOW.SelStart
                        strText = Replace(tbSOW.Value, vbCr, "")
                        tbSOW.Value = Left(strText, iSelStart) & tbVar.Value & ">>" & Mid(strText, iSelStart + 1)
                        tbSOW.SelStart = iSelStart + Len(tbVar.Value) + 2
                        tbSOW.SetFocus
                End Select
        
                tbVar.Value = ""
                iIsVar = 0
                strFLetter = ""
                tbVar.Enabled = False
                
                GoTo Found_Item
            End If
        Next i
    End If
    
    If Right(tbVar.Value, 2) = ">>" Then
        Call AllOn
        
        Select Case iIsVar
            Case Is = 1
                iSelStart = tbSpecial.SelStart
                strText = Replace(tbSpecial.Value, vbCr, "")
                tbSpecial.Value = Left(strText, iSelStart) & tbVar.Value & Mid(strText, iSelStart + 1)
                tbSpecial.SelStart = iSelStart + Len(tbVar.Value)
                tbSpecial.SetFocus
            Case Is = 2
                iSelStart = tbSOW.SelStart
                strText = Replace(tbSOW.Value, vbCr, "")
                tbSOW.Value = Left(strText, iSelStart) & tbVar.Value & Mid(strText, iSelStart + 1)
                tbSOW.SelStart = iSelStart + Len(tbVar.Value)
                tbSOW.SetFocus
        End Select
        
        
        tbVar.Value = Left(tbVar.Value, Len(tbVar.Value) - 2)
        
        For i = 0 To lbVar.ListCount - 1
            If lbVar.List(i, 0) = tbVar.Value Then GoTo Skip_This
        Next i
        
        If InStr(tbVar.Value, "/") < 1 Then
            lbVar.AddItem tbVar.Value
            lbVar.List(lbVar.ListCount - 1, 1) = "<Empty>"
        Else
            vLine = Split(tbVar.Value, "/")

            lbVar.AddItem vLine(0)

            lbVar.List(lbVar.ListCount - 1, 1) = vLine(1)
        End If
        
Skip_This:
        
        tbVar.Value = ""
        iIsVar = 0
        strFLetter = ""
        tbVar.Enabled = False
    End If
Found_Item:

End Sub

Private Sub UserForm_Initialize()
    lbVar.ColumnCount = 2
    lbVar.ColumnWidths = "120;360"
    
    lbCond.ColumnCount = 3
    lbCond.ColumnWidths = "120;120;240"
    
    cbNoteColor.AddItem "RED"
    cbNoteColor.AddItem "ORANGE"
    cbNoteColor.AddItem "GREEN"
    cbNoteColor.AddItem "BLUE"
    cbNoteColor.AddItem "PURPLE"
    'cbNoteColor.AddItem "GRAY"
    cbNoteColor.Value = "RED"
    
    cbSOWColor.AddItem "RED"
    cbSOWColor.AddItem "ORANGE"
    cbSOWColor.AddItem "GREEN"
    cbSOWColor.AddItem "BLUE"
    cbSOWColor.AddItem "PURPLE"
    'cbSOWColor.AddItem "GRAY"
    cbSOWColor.Value = "RED"
    
    iIsVar = 0
    strFLetter = ""
    
    Dim strPath, strFile As String
    Dim strTFolder As String
    Dim vTemp As Variant
    
    strTFolder = ""
    
    strPath = LCase(ThisDrawing.Path)
    'MsgBox strPath
    vTemp = Split(strPath, "dropbox")
    If UBound(vTemp) < 1 Then
        Exit Sub
    End If
    
    strTFolder = vTemp(0) & "\Dropbox\UNITED COMMUNICATIONS JOB INFORMATION\1-JOBS\PLANNING\SCOPE TEMPLATES\*.*"
    
    strFile = Dir$(strTFolder)
    
    Do While strFile <> ""
        If InStr(strFile, ".swt") Then
            cbName.AddItem Replace(strFile, ".swt", "")
        End If
        strFile = Dir$
    Loop
End Sub

Private Sub AllOn()
    tbSpecial.Enabled = True
    tbSOW.Enabled = True
    cbAddTable.Enabled = True
    tbVar.Enabled = True
    cbScan.Enabled = True
    lbVar.Enabled = True
    lbCond.Enabled = True
    'tbValue.Enabled = True
    'cbAdd.Enabled = True
    cbCreate.Enabled = True
End Sub

Private Sub AllOff()
    tbSpecial.Enabled = False
    tbSOW.Enabled = False
    cbAddTable.Enabled = False
    tbVar.Enabled = False
    cbScan.Enabled = False
    lbVar.Enabled = False
    lbCond.Enabled = False
    'tbValue.Enabled = False
    'cbAdd.Enabled = False
    cbCreate.Enabled = False
End Sub

Attribute VB_Name = "TemplateList"
Attribute VB_Base = "0{CEB178F5-404A-41D6-B5EC-1AD16E2CABDE}{417FA890-0FF9-417D-B6B0-F4208604A34A}"
Attribute VB_GlobalNameSpace = False
Attribute VB_Creatable = False
Attribute VB_PredeclaredId = True
Attribute VB_Exposed = False
Attribute VB_TemplateDerived = False
Attribute VB_Customizable = False

Private Sub cbAdd_Click()
    Me.Hide
End Sub

Attribute VB_Name = "TemplateVarEdit"
Attribute VB_Base = "0{0934344D-F457-441A-B171-03CF3A976C54}{07E114F9-857A-4454-B18E-BDD787EFAB62}"
Attribute VB_GlobalNameSpace = False
Attribute VB_Creatable = False
Attribute VB_PredeclaredId = True
Attribute VB_Exposed = False
Attribute VB_TemplateDerived = False
Attribute VB_Customizable = False

Private Sub cbUpdate_Click()
    Me.Hide
End Sub

Private Sub cbVar_Exit(ByVal Cancel As MSForms.ReturnBoolean)
    If Not Me.Caption = "New Variable" Then Exit Sub
    If cbVar.ListCount = 0 Then Exit Sub
    
    Dim strTemp As String
    
    For i = 0 To cbVar.ListCount - 1
        If cbVar.List(i) = cbVar.Value Then
            For j = 0 To TemplateEditor.lbVar.ListCount - 1
                If TemplateEditor.lbVar.List(j, 0) = cbVar.Value Then
                    strTemp = Replace(TemplateEditor.lbVar.List(j, 1), ",", vbCr)
                    tbList.Value = strTemp
                    Exit Sub
                End If
            Next j
        End If
    Next i
End Sub

Attribute VB_Name = "TraceForm"
Attribute VB_Base = "0{CC2F81A1-D4A9-430A-ACEC-E3B4BEB7D845}{84683ABA-DA69-4906-96B6-8FF211CDFC21}"
Attribute VB_GlobalNameSpace = False
Attribute VB_Creatable = False
Attribute VB_PredeclaredId = True
Attribute VB_Exposed = False
Attribute VB_TemplateDerived = False
Attribute VB_Customizable = False
Dim bResidence As Boolean

Private Sub cbGet_Click()
    If tbName.Value = "" Then Exit Sub
    If tbCount.Value = "" Then Exit Sub
    
    If bResidence = True Then
        Call CustomerTrace
        
        Exit Sub
    End If
    
    Dim filterType, filterValue As Variant
    Dim grpCode(0) As Integer
    Dim grpValue(0) As Variant
    Dim objSS As AcadSelectionSet
    Dim objBlock As AcadBlockReference
    Dim vAttList As Variant
    Dim vLine, vCable, vBlock, vItems, vCounts, vTemp As Variant
    Dim strName, strCount, strCable, strCustomer, strTest, strTemp As String
    Dim iCount, iLow, iHigh, iAtt As Integer
    Dim bFeeder As Boolean
    Dim vPnt1, vPnt2 As Variant
    
    On Error Resume Next
    
    lbSpans.Clear
    bFeeder = False
    
    iCount = CInt(tbCount.Value)
    strName = tbName.Value
    
    grpCode(0) = 2
    grpValue(0) = "sPole,sPed,sHH"
    filterType = grpCode
    filterValue = grpValue
    
    Err = 0
    Set objSS = ThisDrawing.SelectionSets.Add("objSS")
    If Not Err = 0 Then
        Set objSS = ThisDrawing.SelectionSets.Item("objSS")
        objSS.Clear
    End If
    
    Select Case cbWindow.Value
        Case "All"
            objSS.Select acSelectionSetAll, , , filterType, filterValue
        Case Else
            Me.Hide
            vPnt1 = ThisDrawing.Utility.GetPoint(, "Get BL Corner: ")
            vPnt2 = ThisDrawing.Utility.GetCorner(vPnt1, vbCr & "Get UR Corner: ")
            
            objSS.Select acSelectionSetWindow, vPnt1, vPnt2, filterType, filterValue
    End Select
    
Get_Feeder:
    Err = 0
    
    For Each objBlock In objSS
        If objBlock.Name = "sPole" Then
            iAtt = 25
        Else
            iAtt = 5
        End If
        
        vAttList = objBlock.GetAttributes
        
        If vAttList(iAtt).TextString = "" Then GoTo Next_objBlock
        If InStr(vAttList(iAtt).TextString, strName) < 1 Then GoTo Next_objBlock
        
        vLine = Split(vAttList(iAtt).TextString, vbCr)
        
        For i = 0 To UBound(vLine)
            If InStr(vLine(i), strName) < 1 Then GoTo Next_I
            
            vCable = Split(vLine(i), " / ")
            vBlock = Split(vCable(1), " + ")
            For j = 0 To UBound(vBlock)
                If InStr(vBlock(j), strName) < 1 Then GoTo Next_J
                
                vItems = Split(vBlock(j), ": ")
                vCounts = Split(vItems(1), "-")
                iLow = CInt(vCounts(0)) - 1
                If UBound(vCounts) > 0 Then
                    iHigh = CInt(vCounts(1)) + 1
                Else
                    iHigh = CInt(vCounts(0)) + 1
                End If
                
                If iCount > iLow And iCount < iHigh Then GoTo Found_Count
            
Next_J:
            Next j
            
Next_I:
        Next i
        
        GoTo Next_objBlock
                
Found_Count:
        If Not Err = 0 Then GoTo Next_objBlock
        
        lbSpans.AddItem objBlock.Name
        lbSpans.List(lbSpans.ListCount - 1, 1) = vAttList(0).TextString
        lbSpans.List(lbSpans.ListCount - 1, 2) = ""
        If UBound(vItems) > 1 Then lbSpans.List(lbSpans.ListCount - 1, 2) = vItems(2)
        lbSpans.List(lbSpans.ListCount - 1, 3) = ""
        lbSpans.List(lbSpans.ListCount - 1, 4) = ""
        lbSpans.List(lbSpans.ListCount - 1, 5) = ""
        lbSpans.List(lbSpans.ListCount - 1, 6) = ""
        lbSpans.List(lbSpans.ListCount - 1, 7) = ""
        lbSpans.List(lbSpans.ListCount - 1, 8) = objBlock.InsertionPoint(0) & "," & objBlock.InsertionPoint(1)
        
        vItems = Split(vCable(0), ": ")
        vCounts = Split(vItems(1), ")")
        strCable = vCounts(0) & ")"
        
        iAtt = iAtt + 1
        If Not vAttList(iAtt).TextString = "" Then
            vTemp = Split(vAttList(iAtt).TextString, "] ")
            vBlock = Split(vTemp(1), " + ")
            For i = 0 To UBound(vBlock)
                vItems = Split(vBlock(i), ": ")
                If vItems(0) = strName Then
                    vCounts = Split(vItems(1), "-")
                    iLow = CInt(vCounts(0)) - 1
                    If UBound(vCounts) > 0 Then
                        iHigh = CInt(vCounts(1)) + 1
                    Else
                        iHigh = CInt(vCounts(0)) + 1
                    End If
                
                    If iCount > iLow And iCount < iHigh Then
                        lbSpans.List(lbSpans.ListCount - 1, 5) = "1"
                        
                        If InStr(vTemp(1), tbName.Value) > 0 And bFeeder = True Then
                            lbSpans.List(lbSpans.ListCount - 1, 5) = "2"
                            lbSpans.List(lbSpans.ListCount - 1, 6) = tbSplitter.Value
                            If InStr(cbSplitter.Value, "Hub") > 0 Then lbSpans.List(lbSpans.ListCount - 1, 7) = "2"
                            
                            GoTo Done_With_Splices
                        End If
                    End If
                End If
Next_Splice:
            Next i
        End If
        
Done_With_Splices:
        
        iAtt = iAtt + 1
        If Not vAttList(iAtt).TextString = "" Then
            vLine = Split(vAttList(iAtt).TextString, ";;")
            For i = 0 To UBound(vLine)
                If InStr(vLine(i), strCable) > 0 Then
                    If InStr(vLine(i), "LOOP") > 0 Then
                        lbSpans.List(lbSpans.ListCount - 1, 4) = "100"
                    Else
                        vItems = Split(vLine(i), "=")
                        If InStr(vItems(0), "HA") > 0 Then GoTo Next_Unit
                        strTemp = Replace(vItems(1), "'", "")
                        If lbSpans.List(lbSpans.ListCount - 1, 3) = "" Then
                            lbSpans.List(lbSpans.ListCount - 1, 3) = strTemp
                        Else
                            lbSpans.List(lbSpans.ListCount - 1, 3) = CLng(lbSpans.List(lbSpans.ListCount - 1, 3)) + CLng(strTemp)
                        End If
                    End If
                End If
Next_Unit:
            Next i
        End If
        
        
        
        
Next_objBlock:
    Err = 0
    Next objBlock
    
    If InStr(strName, "-") > 0 Then
        vLine = Split(strName, "-")
        strName = vLine(0)
        iCount = CInt(vLine(1))
        bFeeder = True
        
        GoTo Get_Feeder
    End If
    
    '<------------------------ Get Customer with Count
    
    Err = 0
    
    grpCode(0) = 2
    grpValue(0) = "Customer"
    filterType = grpCode
    filterValue = grpValue
    
    objSS.Clear
    
    Select Case cbWindow.Value
        Case "All"
            objSS.Select acSelectionSetAll, , , filterType, filterValue
        Case Else
            objSS.Select acSelectionSetWindow, vPnt1, vPnt2, filterType, filterValue
    End Select
    
    For Each objBlock In objSS
        vAttList = objBlock.GetAttributes
        
        If vAttList(4).TextString = "" Then GoTo Next_Customer
        strCustomer = tbName.Value & ": " & tbCount.Value
        
        vLine = Split(vAttList(4).TextString, " - ")
        strTest = Replace(vLine(1), "(", "")
        strTest = Replace(strTest, ")", "")
        
        If strTest = strCustomer Then
            lbSpans.AddItem vAttList(0).TextString
            lbSpans.List(lbSpans.ListCount - 1, 1) = vAttList(1).TextString & " " & vAttList(2).TextString
            lbSpans.List(lbSpans.ListCount - 1, 2) = vLine(0)
            lbSpans.List(lbSpans.ListCount - 1, 3) = ""
            lbSpans.List(lbSpans.ListCount - 1, 4) = ""
            lbSpans.List(lbSpans.ListCount - 1, 5) = ""
            lbSpans.List(lbSpans.ListCount - 1, 6) = ""
            lbSpans.List(lbSpans.ListCount - 1, 7) = "1"
        End If
        
Next_Customer:
    Next objBlock
    
Exit_Sub:
    Call GetTotals
    Call OrderList
    
    objSS.Clear
    objSS.Delete
    
    If Not cbWindow.Value = "All" Then Me.show
End Sub

Private Sub cbQuit_Click()
    Me.Hide
End Sub

Private Sub cbSplitter_Change()
    Select Case cbSplitter.Value
        Case "16"
            tbSplitter.Value = "14.5"
            tbConnector.Value = "1"
        Case "32"
            tbSplitter.Value = "18.0"
            tbConnector.Value = "1"
        Case "64"
            tbSplitter.Value = "21.5"
            tbConnector.Value = "1"
        Case "16 Hub"
            tbSplitter.Value = "14.5"
            tbConnector.Value = "3"
        Case "32 Hub"
            tbSplitter.Value = "18.0"
            tbConnector.Value = "3"
        Case Else
            tbSplitter.Value = "0.0"
            tbConnector.Value = "1"
    End Select
End Sub

Private Sub Label11_Click()
    Dim objEntity As AcadEntity
    Dim objBlock As AcadBlockReference
    Dim vAttList, vReturnPnt As Variant
    Dim vLine, vTemp As Variant
    Dim strTest As String
    
    On Error Resume Next
    
    Me.Hide
    
    ThisDrawing.Utility.GetEntity objEntity, vReturnPnt, vbCr & "Select Customer:"
    If Not Err = 0 Then GoTo Exit_Sub
    
    If Not TypeOf objEntity Is AcadBlockReference Then GoTo Exit_Sub
    Set objBlock = objEntity
    
    If Not objBlock.Name = "Customer" Then GoTo Exit_Sub
    
    vAttList = objBlock.GetAttributes
    If vAttList(4).TextString = "" Then GoTo Exit_Sub
    
    vLine = Split(vAttList(4).TextString, " - ")
        
    strTest = Replace(vLine(1), "(", "")
    strTest = Replace(strTest, ")", "")
    vTemp = Split(strTest, ": ")
    tbName.Value = vTemp(0)
    tbCount.Value = vTemp(1)
    
    GoTo Exit_Sub
    
    lbSpans.Clear
    
    lbSpans.AddItem vAttList(0).TextString
    lbSpans.List(lbSpans.ListCount - 1, 1) = vAttList(1).TextString & " " & vAttList(2).TextString
    lbSpans.List(lbSpans.ListCount - 1, 2) = vLine(0)
    lbSpans.List(lbSpans.ListCount - 1, 3) = ""
    lbSpans.List(lbSpans.ListCount - 1, 4) = ""
    lbSpans.List(lbSpans.ListCount - 1, 5) = ""
    lbSpans.List(lbSpans.ListCount - 1, 6) = ""
    lbSpans.List(lbSpans.ListCount - 1, 7) = "1"
    
    'bResidence = True
    
Exit_Sub:
    Me.show
End Sub

Private Sub Label6_Click()
    If lbSpans.ListIndex < 0 Then Exit Sub
    
    If lbSpans.List(lbSpans.ListIndex, 5) = "" Then
        lbSpans.List(lbSpans.ListIndex, 5) = "1"
    Else
        lbSpans.List(lbSpans.ListIndex, 5) = CInt(lbSpans.List(lbSpans.ListIndex, 5)) + 1
    End If
End Sub

Private Sub Label7_Click()
    If lbSpans.ListIndex < 0 Then Exit Sub
    
    If lbSpans.List(lbSpans.ListIndex, 5) = "" Then
        lbSpans.List(lbSpans.ListIndex, 5) = "2"
    lbSpans.List(lbSpans.ListIndex, 6) = tbSplitter.Value
            
    If InStr(cbSplitter.Value, "Hub") > 0 Then lbSpans.List(lbSpans.ListIndex, 7) = "2"
End Sub

Private Sub lbSpans_DblClick(ByVal Cancel As MSForms.ReturnBoolean)
    Dim vCoords, vAttList As Variant
    Dim viewCoordsB(0 To 2) As Double
    Dim viewCoordsE(0 To 2) As Double
    Dim iIndex As Integer
    
    Me.Hide
    
    vCoords = Split(lbSpans.List(lbSpans.ListIndex, 8), ",")
    
    viewCoordsB(0) = vCoords(0) - 150
    viewCoordsB(1) = vCoords(1) - 150
    viewCoordsB(2) = 0#
    viewCoordsE(0) = vCoords(0) + 150
    viewCoordsE(1) = vCoords(1) + 150
    viewCoordsE(2) = 0#
    
    ThisDrawing.Application.ZoomWindow viewCoordsB, viewCoordsE
    
    Me.show
End Sub

Private Sub lbSpans_KeyDown(ByVal KeyCode As MSForms.ReturnInteger, ByVal Shift As Integer)
    Select Case KeyCode
        Case vbKeyS
            lbSpans.List(lbSpans.ListIndex, 5) = "2"
            lbSpans.List(lbSpans.ListIndex, 6) = tbSplitter.Value
            
            If InStr(cbSplitter.Value, "Hub") > 0 Then lbSpans.List(lbSpans.ListIndex, 7) = "2"
        Case vbKeyX
            If lbSpans.List(lbSpans.ListIndex, 5) = "" Then
                lbSpans.List(lbSpans.ListIndex, 5) = "1"
            Else
                lbSpans.List(lbSpans.ListIndex, 5) = CInt(lbSpans.List(lbSpans.ListIndex, 5)) + 1
            End If
        Case vbKeyD
            lbSpans.List(lbSpans.ListIndex, 5) = ""
            lbSpans.List(lbSpans.ListIndex, 6) = ""
            lbSpans.List(lbSpans.ListIndex, 7) = ""
        Case vbKeyC
            If lbSpans.List(lbSpans.ListIndex, 7) = "" Then
                lbSpans.List(lbSpans.ListIndex, 7) = "1"
            Else
                lbSpans.List(lbSpans.ListIndex, 7) = CInt(lbSpans.List(lbSpans.ListIndex, 7)) + 1
            End If
    End Select
    
    Call GetTotals
End Sub

Private Sub tbDB1310_Change()
    If CDbl(tbDB1310.Value) > CDbl(tbMax.Value) Then
        Label19.ForeColor = &HFF&
    Else
        Label19.ForeColor = &H80000012
    End If
End Sub

Private Sub tbDB1550_Change()
    If CDbl(tbDB1550.Value) > CDbl(tbMax.Value) Then
        Label20.ForeColor = &HFF&
    Else
        Label20.ForeColor = &H80000012
    End If
End Sub

Private Sub UserForm_Initialize()
    lbSpans.ColumnCount = 9
    lbSpans.ColumnWidths = "72;120;120;36;36;36;36;36;6"
    
    cbSplitter.AddItem ""
    cbSplitter.AddItem "16"
    cbSplitter.AddItem "32"
    cbSplitter.AddItem "64"
    cbSplitter.AddItem "16 Hub"
    cbSplitter.AddItem "32 Hub"
    
    cbSplitter.Value = "32"
    tbSplitter.Value = "18.0"
    
    cbWindow.AddItem "All"
    cbWindow.AddItem "Window"
    cbWindow.Value = "All"
    
    bResidence = False
End Sub

Private Sub GetTotals()
    If lbSpans.ListCount < 1 Then Exit Sub
    
    Dim lSpans, lCoil As Long
    Dim iSplice, iConnect As Integer
    Dim dSplit As Double
    Dim d1310, d1550, dBoth, dTemp As Double
    
    lSpans = 0
    lCoil = 0
    
    iSplice = 0
    iSplit = 0
    iConnect = 0
    
    For i = 0 To lbSpans.ListCount - 1
        If Not lbSpans.List(i, 3) = "" Then lSpans = lSpans + CLng(lbSpans.List(i, 3))
        If Not lbSpans.List(i, 4) = "" Then lCoil = lCoil + CLng(lbSpans.List(i, 4))
        
        If Not lbSpans.List(i, 5) = "" Then iSplice = iSplice + CInt(lbSpans.List(i, 5))
        If Not lbSpans.List(i, 6) = "" Then dSplit = dSplit + CDbl(lbSpans.List(i, 6))
        If Not lbSpans.List(i, 7) = "" Then iConnect = iConnect + CInt(lbSpans.List(i, 7))
    Next i
    
    tbSpan.Value = lSpans
    tbCoiled.Value = lCoil
    
    tbSpliced.Value = iSplice
    tbSplit.Value = dSplit
    tbConnector.Value = iConnect
    
    dBoth = iSplice * CDbl(tbPerSplice.Value)
    dBoth = dBoth + dSplit
    dBoth = dBoth + iConnect * CDbl(tbPerConnector.Value)
    
    d1310 = dBoth + (lSpans + lCoil) / 1000 * CDbl(tbPer1310.Value)
    d1550 = dBoth + (lSpans + lCoil) / 1000 * CDbl(tbPer1550.Value)
    
    tbDB1310.Value = CLng(d1310 * 1000) / 1000
    tbDB1550.Value = CLng(d1550 * 1000) / 1000
    
    dTemp = CDbl(tbMax.Value) - dBoth
    tbMax1310.Value = CLng(dTemp / CDbl(tbPer1310.Value) * 1000) / 1000
    tbMax1550.Value = CLng(dTemp / CDbl(tbPer1550.Value) * 1000) / 1000
    
    tbListCount.Value = lbSpans.ListCount
End Sub

Private Sub OrderList()
    If lbSpans.ListCount < 2 Then Exit Sub
    
    Dim strPrevious, strLine As String
    Dim strList() As String
    Dim iCount As Integer
    Dim vLine As Variant
    
    iCount = lbSpans.ListCount - 1
    ReDim strList(iCount) As String
    
    Select Case lbSpans.List(iCount, 0)
        Case "sPole", "sHH", "sPed"
            'strPrevious = lbSpans.List(lbSpans.ListIndex, 2)
            Exit Sub
        Case Else
            strPrevious = lbSpans.List(iCount, 2)
            strLine = lbSpans.List(iCount, 0) & vbTab & lbSpans.List(iCount, 1) & vbTab & lbSpans.List(iCount, 2)
            strLine = strLine & vbTab & lbSpans.List(iCount, 3) & vbTab & lbSpans.List(iCount, 4) & vbTab & lbSpans.List(iCount, 5)
            strLine = strLine & vbTab & lbSpans.List(iCount, 6) & vbTab & lbSpans.List(iCount, 7) & vbTab & lbSpans.List(iCount, 8)
            strList(iCount) = strLine
            
            iCount = iCount - 1
    End Select
    
    While iCount > -1
        For i = 0 To lbSpans.ListCount - 1
            If lbSpans.List(i, 1) = strPrevious Then
                strPrevious = lbSpans.List(i, 2)
                strLine = lbSpans.List(i, 0) & vbTab & lbSpans.List(i, 1) & vbTab & lbSpans.List(i, 2)
                strLine = strLine & vbTab & lbSpans.List(i, 3) & vbTab & lbSpans.List(i, 4) & vbTab & lbSpans.List(i, 5)
                strLine = strLine & vbTab & lbSpans.List(i, 6) & vbTab & lbSpans.List(i, 7) & vbTab & lbSpans.List(i, 8)
                strList(iCount) = strLine
            
                iCount = iCount - 1
                GoTo Find_Next
            End If
        Next i
        
        MsgBox "Unable to find previous pole  " & strPrevious
        Exit Sub
Find_Next:
    Wend
    
    lbSpans.Clear
    
    For i = UBound(strList) To 0 Step -1
        vLine = Split(strList(i), vbTab)
        
        lbSpans.AddItem vLine(0), 0
        lbSpans.List(0, 1) = vLine(1)
        lbSpans.List(0, 2) = vLine(2)
        lbSpans.List(0, 3) = vLine(3)
        lbSpans.List(0, 4) = vLine(4)
        lbSpans.List(0, 5) = vLine(5)
        lbSpans.List(0, 6) = vLine(6)
        lbSpans.List(0, 7) = vLine(7)
        lbSpans.List(0, 8) = vLine(8)
    Next i
End Sub

Private Sub CustomerTrace()
    Dim filterType, filterValue As Variant
    Dim grpCode(0) As Integer
    Dim grpValue(0) As Variant
    Dim objSS As AcadSelectionSet
    Dim objBlock As AcadBlockReference
    Dim vAttList As Variant
    Dim strPrevious As String
    Dim iAtt As Integer
    'Dim vLine, vCable, vBlock, vItems, vCounts As Variant
    'Dim strName, strCount, strCable, strCustomer, strTest, strTemp As String
    'Dim iCount, iLow, iHigh, iAtt As Integer
    
    On Error Resume Next
    
    'iCount = CInt(tbCount.Value)
    'strName = tbName.Value
    
    grpCode(0) = 2
    grpValue(0) = "sPole,sPed,sHH"
    filterType = grpCode
    filterValue = grpValue
    
    Err = 0
    Set objSS = ThisDrawing.SelectionSets.Add("objSS")
    If Not Err = 0 Then
        Set objSS = ThisDrawing.SelectionSets.Item("objSS")
        objSS.Clear
    End If
    
    objSS.Select acSelectionSetAll, , , filterType, filterValue
    
Start_Over:
    Err = 0
    
    For Each objBlock In objSS
        vAttList = objBlock.GetAttributes
        
        If Not vAttList(0).TextString = strPrevious Then GoTo Next_objBlock
        
        
        
        
        
        
        
        
        
Next_objBlock:
    Next objBlock
    
Exit_Sub:
    Call GetTotals
    
    objSS.Clear
    objSS.Delete
End Sub

Attribute VB_Name = "TransferBlockData"
Attribute VB_Base = "0{4DE4FF0D-1FFD-4D40-96EA-7FB8D584DB84}{FD642768-AA88-4A75-83A0-E8E80FE511E3}"
Attribute VB_GlobalNameSpace = False
Attribute VB_Creatable = False
Attribute VB_PredeclaredId = True
Attribute VB_Exposed = False
Attribute VB_TemplateDerived = False
Attribute VB_Customizable = False
Dim objFrom As AcadBlockReference
Dim objTo As AcadBlockReference

Private Sub cbGetFrom_Click()
    Dim objEntity As AcadEntity
    Dim vAttList, vReturnPnt As Variant
    
    Me.Hide
    On Error Resume Next
    
    ThisDrawing.Utility.GetEntity objEntity, vReturnPnt, vbCr & "Select Block to transfer FROM:"
    If Not Err = 0 Then GoTo Exit_Sub
    If Not TypeOf objEntity Is AcadBlockReference Then GoTo Exit_Sub
    
    Set objFrom = objEntity
    vAttList = objFrom.GetAttributes
    If Not Err = 0 Then GoTo Exit_Sub
    
    For i = 0 To UBound(vAttList)
        lbFrom.AddItem vAttList(i).TagString
        lbFrom.List(i, 1) = vAttList(i).TextString
    Next i
    
    LabelFrom.Caption = LabelFrom.Caption & ": " & objFrom.Name
    
    ThisDrawing.Utility.GetEntity objEntity, vReturnPnt, vbCr & "Select Block to transfer TO:"
    If Not Err = 0 Then GoTo Exit_Sub
    If Not TypeOf objEntity Is AcadBlockReference Then GoTo Exit_Sub
    
    Set objTo = objEntity
    vAttList = objTo.GetAttributes
    If Not Err = 0 Then GoTo Exit_Sub
    
    For i = 0 To UBound(vAttList)
        lbTo.AddItem vAttList(i).TagString
        lbTo.List(i, 1) = vAttList(i).TextString
    Next i
    
    LabelTo.Caption = LabelTo.Caption & ": " & objTo.Name
    
Exit_Sub:
    Me.show
End Sub

Private Sub cbQuit_Click()
    Me.Hide
End Sub

Private Sub cbUpdate_Click()
    If lbFrom.ListCount < 1 Then Exit Sub
    If lbTo.ListCount < 1 Then Exit Sub
    
    Dim strLine As String
    
    strLine = ""
    For i = 0 To lbTo.ListCount - 1
        If lbTo.Selected(i) = True Then
            If InStr(lbTo.List(i, 1), "{{") > 0 Then
                If strLine = "" Then
                    strLine = lbTo.List(i, 1) & ">" & i
                Else
                    strLine = strLine & ":" & lbTo.List(i, 1) & ">" & i
                End If
            End If
        End If
    Next i
    
    If strLine = "" Then Exit Sub
    strLine = Replace(strLine, "{{", "")
    strLine = Replace(strLine, "}}", "")
    
    Dim objEntity As AcadEntity
    Dim vAttFrom, vAttTo As Variant
    Dim vReturnPnt, vLine, vItem As Variant
    
    Me.Hide
    On Error Resume Next
    
Next_Set:
    
    ThisDrawing.Utility.GetEntity objEntity, vReturnPnt, vbCr & "Select Block to transfer FROM:"
    If Not Err = 0 Then GoTo Exit_Sub
    If Not TypeOf objEntity Is AcadBlockReference Then GoTo Exit_Sub
    
    Set objFrom = objEntity
    vAttFrom = objFrom.GetAttributes
    If Not Err = 0 Then GoTo Exit_Sub
    
    ThisDrawing.Utility.GetEntity objEntity, vReturnPnt, vbCr & "Select Block to transfer TO:"
    If Not Err = 0 Then GoTo Exit_Sub
    If Not TypeOf objEntity Is AcadBlockReference Then GoTo Exit_Sub
    
    Set objTo = objEntity
    vAttTo = objTo.GetAttributes
    If Not Err = 0 Then GoTo Exit_Sub
    
    vLine = Split(strLine, ":")
    For i = 0 To UBound(vLine)
        vItem = Split(vLine(i), ">")
        vAttTo(CInt(vItem(1))).TextString = vAttFrom(CInt(vItem(0))).TextString
    Next i
    
    GoTo Next_Set
    
Exit_Sub:
    Me.show
End Sub

Private Sub lbTo_DblClick(ByVal Cancel As MSForms.ReturnBoolean)
    If lbFrom.ListCount < 1 Then Exit Sub
    If lbTo.ListCount < 1 Then Exit Sub
    
    'Dim strLine As String
    Dim iIndex As Integer
    
    'strLine = ""
    For i = 0 To lbTo.ListCount - 1
        If lbTo.Selected(i) = True Then
            For j = 0 To lbFrom.ListCount - 1
                If lbFrom.Selected(j) = True Then
                    lbTo.List(i, 1) = "{{" & j & "}}"
                    
                    If j < lbFrom.ListCount - 1 Then
                        lbFrom.Selected(j) = False
                        lbFrom.Selected(j + 1) = True
                    End If
                    
                    Exit Sub
                End If
            Next j
        End If
    Next i
    
End Sub

Private Sub UserForm_Initialize()
    lbFrom.ColumnCount = 2
    lbFrom.ColumnWidths = "72;138"
    
    lbTo.ColumnCount = 2
    lbTo.ColumnWidths = "72;138"
End Sub

Attribute VB_Name = "TransferToMap"
Attribute VB_Base = "0{E7AD6316-4CB6-46F4-9296-CBBFF90ACF5A}{85EF4153-CD82-4095-9553-CCAB770C2B65}"
Attribute VB_GlobalNameSpace = False
Attribute VB_Creatable = False
Attribute VB_PredeclaredId = True
Attribute VB_Exposed = False
Attribute VB_TemplateDerived = False
Attribute VB_Customizable = False
Dim vDwgLL, vDwgUR As Variant
Dim vMapLL, vMapUR As Variant

Private Sub cbGetBoundaries_Click()
    Me.Hide
    
    Call GetBoundaries
    
    Me.show
End Sub

Private Sub cbQuit_Click()
    Me.Hide
End Sub

Private Sub cbTransfer_Click()
    Dim iNumber As Integer
    iNumber = 0
    
    If cbPoles.Value = True Then Call TransferPoles
    Me.Repaint
    
    If cbPEDs.Value = True Then
        iNumber = TransferBuried(CStr("sPed"))
        LPed.Caption = iNumber
        Me.Repaint
        iNumber = 0
    End If
    
    If cbHH.Value = True Then
        iNumber = TransferBuried(CStr("sHH"))
        LHH.Caption = iNumber
        Me.Repaint
        iNumber = 0
    End If
    
    If cbMH.Value = True Then
        iNumber = TransferBuried(CStr("sMH"))
        LMH.Caption = iNumber
        Me.Repaint
        iNumber = 0
    End If
    
    If cbPanel.Value = True Then
        iNumber = TransferBuried(CStr("sPanel"))
        LPanel.Caption = iNumber
        Me.Repaint
        iNumber = 0
    End If
    
    If cbFP.Value = True Then
        iNumber = TransferBuried(CStr("sFP"))
        LFP.Caption = iNumber
        Me.Repaint
    End If
    
    If cbCustomer.Value = True Then Call TransferCustomers
End Sub

Private Sub cbTransferLatLong_Click()
    Dim iNumber As Integer
    Dim strLine As String
    strLine = ""
    iNumber = 0
    
    If cbPoles.Value = True Then Call AddLLtoPoles
    Me.Repaint
    
    If cbPEDs.Value = True Then
        strLine = AddLLToBuried(CStr("sPed"))
        LPed.Caption = strLine
        Me.Repaint
        strLine = ""
    End If
    
    If cbHH.Value = True Then
        strLine = AddLLToBuried(CStr("sHH"))
        LHH.Caption = strLine
        Me.Repaint
        strLine = ""
    End If
    
    If cbMH.Value = True Then
        strLine = AddLLToBuried(CStr("sMH"))
        LMH.Caption = strLine
        Me.Repaint
        strLine = ""
    End If
    
    If cbPanel.Value = True Then
        strLine = AddLLToBuried(CStr("sPanel"))
        LPanel.Caption = strLine
        Me.Repaint
        strLine = ""
    End If
    
    If cbFP.Value = True Then
        strLine = AddLLToBuried(CStr("sFP"))
        LFP.Caption = strLine
        Me.Repaint
    End If
    
    If cbCustomer.Value = True Then LCustomer.Caption = "x"
        
End Sub

Private Sub GetBoundaries()
    On Error Resume Next
    
    vDwgLL = ThisDrawing.Utility.GetPoint(, "Get DWG LL Corner: ")
    vDwgUR = ThisDrawing.Utility.GetCorner(vDwgLL, vbCr & "Get DWG UR Corner: ")
    
    vMapLL = ThisDrawing.Utility.GetPoint(, "Get MAP LL Corner: ")
    vMapUR = ThisDrawing.Utility.GetCorner(vMapLL, vbCr & "Get MAP UR Corner: ")
    
    If Not Err = 0 Then Exit Sub
    
    cbGetBoundaries.Enabled = False
    cbTransferLatLong.Enabled = True
    cbTransfer.Enabled = True
    Label2.Enabled = True
End Sub

Private Sub TransferPoles()
    Dim filterType, filterValue As Variant
    Dim grpCode(0) As Integer
    Dim grpValue(0) As Variant
    Dim objSSDwg As AcadSelectionSet
    Dim objSSMap As AcadSelectionSet
    Dim objPoleDwg As AcadBlockReference
    Dim objPoleMap As AcadBlockReference
    Dim vAttDwg, vAttMap As Variant
    Dim strPoleNum As String
    Dim strDwgLatLong, strMapLatLong As String
    Dim iPoles, iData, iAttach As Integer
    Dim iCounts, iUnits As Integer
    Dim strAtt(27) As String
    
    For i = 0 To 27
        strAtt(i) = ""
    Next i
    
    iPoles = 0
    iData = 0
    iAttach = 0
    iCounts = 0
    iUnits = 0
        
    grpCode(0) = 2
    grpValue(0) = "sPole"
    filterType = grpCode
    filterValue = grpValue
    
    Set objSSDwg = ThisDrawing.SelectionSets.Add("objSSDwg")
    objSSDwg.Select acSelectionSetWindow, vDwgLL, vDwgUR, filterType, filterValue
    If objSSDwg.count < 1 Then GoTo Exit_Sub
    
    Set objSSMap = ThisDrawing.SelectionSets.Add("objSSMap")
    objSSMap.Select acSelectionSetWindow, vMapLL, vMapUR, filterType, filterValue
    If objSSMap.count < 1 Then GoTo Sub_Exit_Sub
    
    For Each objPoleDwg In objSSDwg
        vAttDwg = objPoleDwg.GetAttributes
        If vAttDwg(7).TextString = "" Then GoTo Next_objDwgPole
        
        strPoleNum = vAttDwg(0).TextString
        strDwgLatLong = vAttDwg(7).TextString
        
        If strPoleNum = "POLE" Then GoTo Next_objDwgPole
        If strPoleNum = "" Then GoTo Next_objDwgPole
        'iTest = 0
        
        For Each objPoleMap In objSSMap
            vAttMap = objPoleMap.GetAttributes
            strMapLatLong = vAttMap(7).TextString
            
            If strMapLatLong = strDwgLatLong Then
                For i = 0 To 6
                    strAtt(i) = vAttDwg(i).TextString
                Next i
                
                For i = 8 To 27
                    strAtt(i) = vAttDwg(i).TextString
                Next i
                
                For i = 0 To 6
                    vAttMap(i).TextString = strAtt(i)
                Next i
                
                For i = 8 To 27
                    vAttMap(i).TextString = strAtt(i)
                Next i
                
                objPoleMap.Update
                iPoles = iPoles + 1
                GoTo Next_objDwgPole
            End If
        Next objPoleMap
Next_objDwgPole:
    Next objPoleDwg
    
Sub_Exit_Sub:
    objSSMap.Clear
    objSSMap.Delete
    
Exit_Sub:
    objSSDwg.Clear
    objSSDwg.Delete
    
    LPole.Caption = iPoles
End Sub

Private Function TransferBuried(strName As String)
    Dim filterType, filterValue As Variant
    Dim grpCode(0) As Integer
    Dim grpValue(0) As Variant
    Dim objSSDwg As AcadSelectionSet
    Dim objSSMap As AcadSelectionSet
    Dim objBlockDwg As AcadBlockReference
    Dim objBlockMap As AcadBlockReference
    Dim vAttDwg, vAttMap As Variant
    Dim strNumber, strOmit As String
    Dim strDwgLatLong, strMapLatLong As String
    Dim iItems As Integer
    Dim strAtt(7) As String
    
    For i = 0 To 7
        strAtt(i) = ""
    Next i
    
    iItems = 0
    strOmit = Replace(UCase(strName), "S", "")
        
    grpCode(0) = 2
    grpValue(0) = strName
    filterType = grpCode
    filterValue = grpValue
    
    Set objSSDwg = ThisDrawing.SelectionSets.Add("objSSDwg")
    objSSDwg.Select acSelectionSetWindow, vDwgLL, vDwgUR, filterType, filterValue
    
    Set objSSMap = ThisDrawing.SelectionSets.Add("objSSMap")
    objSSMap.Select acSelectionSetWindow, vMapLL, vMapUR, filterType, filterValue
    
    If objSSDwg.count < 1 Then GoTo Exit_Sub
    If objSSMap.count < 1 Then GoTo Exit_Sub
    
    For Each objBlockDwg In objSSDwg
        vAttDwg = objBlockDwg.GetAttributes
        
        strNumber = vAttDwg(0).TextString
        If strNumber = "" Then GoTo Next_objBlockDwg
        
        If strOmit = vAttDwg(0).TextString Then GoTo Next_objBlockDwg
        
        If vAttDwg(3).TextString = "" Then GoTo Next_objBlockDwg
        strDwgLatLong = vAttDwg(3).TextString
        
        For Each objBlockMap In objSSMap
            vAttMap = objBlockMap.GetAttributes
            strMapLatLong = vAttMap(3).TextString
            
            If strMapLatLong = strDwgLatLong Then
                For i = 0 To 7
                    strAtt(i) = vAttDwg(i).TextString
                Next i
                
                For i = 0 To 7
                    vAttMap(i).TextString = strAtt(i)
                Next i
                
                objBlockMap.Update
                iItems = iItems + 1
                GoTo Next_objBlockDwg
            End If
        Next objBlockMap
Next_objBlockDwg:
    Next objBlockDwg
    
Exit_Sub:
    objSSDwg.Clear
    objSSDwg.Delete
    
    objSSMap.Clear
    objSSMap.Delete
    
    TransferBuried = iItems
End Function

Private Sub TransferCustomers()
    Dim filterType, filterValue As Variant
    Dim grpCode(0) As Integer
    Dim grpValue(0) As Variant
    Dim objSSDwg As AcadSelectionSet
    Dim objSSMap As AcadSelectionSet
    Dim objBlockDwg As AcadBlockReference
    Dim objBlockMap As AcadBlockReference
    Dim vAttDwg, vAttMap As Variant
    Dim strNumber, strOmit As String
    Dim strDwgLatLong, strMapLatLong As String
    Dim iItems As Integer
    Dim strAtt(5) As String
    
    For i = 0 To 5
        strAtt(i) = ""
    Next i
    
    iItems = 0
        
    grpCode(0) = 2
    grpValue(0) = "Customer"
    filterType = grpCode
    filterValue = grpValue
    
    Set objSSDwg = ThisDrawing.SelectionSets.Add("objSSDwg")
    objSSDwg.Select acSelectionSetWindow, vDwgLL, vDwgUR, filterType, filterValue
    
    Set objSSMap = ThisDrawing.SelectionSets.Add("objSSMap")
    objSSMap.Select acSelectionSetWindow, vMapLL, vMapUR, filterType, filterValue
    If objSSDwg.count < 1 Then GoTo Exit_Sub
    If objSSMap.count < 1 Then GoTo Exit_Sub
    
    For Each objBlockDwg In objSSDwg
        vAttDwg = objBlockDwg.GetAttributes
        
        strNumber = vAttDwg(0).TextString
        If strNumber = "" Then GoTo Next_objBlockDwg
        
        For Each objBlockMap In objSSMap
            vAttMap = objBlockMap.GetAttributes
            
            If vAttMap(1).TextString = vAttDwg(1).TextString Then
                If vAttMap(2).TextString = vAttDwg(2).TextString Then
                    For i = 0 To 5
                        strAtt(i) = vAttDwg(i).TextString
                    Next i
                    
                    For i = 0 To 5
                        vAttMap(i).TextString = strAtt(i)
                    Next i
                
                    objBlockMap.Update
                    iItems = iItems + 1
                    GoTo Next_objBlockDwg
                End If
            End If
        Next objBlockMap
Next_objBlockDwg:
    Next objBlockDwg
    
Exit_Sub:
    objSSDwg.Clear
    objSSDwg.Delete
    
    objSSMap.Clear
    objSSMap.Delete
    
    LCustomer.Caption = iItems
End Sub

Private Sub AddLLtoPoles()
    Dim filterType, filterValue As Variant
    Dim grpCode(0) As Integer
    Dim grpValue(0) As Variant
    Dim objSSDwg As AcadSelectionSet
    Dim objSSMap As AcadSelectionSet
    Dim objPoleDwg As AcadBlockReference
    Dim objPoleMap As AcadBlockReference
    Dim vAttDwg, vAttMap As Variant
    Dim iPoles, iXfer As Integer
    
    Dim dN, dE As Double
    Dim vLL As Variant
    
    iPoles = 0
    iXfer = 0
        
    grpCode(0) = 2
    grpValue(0) = "sPole"
    filterType = grpCode
    filterValue = grpValue
    
    Set objSSDwg = ThisDrawing.SelectionSets.Add("objSSDwg")
    objSSDwg.Select acSelectionSetWindow, vDwgLL, vDwgUR, filterType, filterValue
    
    Set objSSMap = ThisDrawing.SelectionSets.Add("objSSMap")
    objSSMap.Select acSelectionSetWindow, vMapLL, vMapUR, filterType, filterValue
    
    If objSSMap.count < 1 Then GoTo Exit_Sub
    
    For Each objPoleMap In objSSMap
        vAttMap = objPoleMap.GetAttributes
        If vAttMap(0).TextString = "POLE" Then GoTo Next_objDwgPole
        If vAttMap(0).TextString = "" Then GoTo Next_objDwgPole
        
        If Not vAttMap(7).TextString = "" Then
            If cbOverwrite.Value = False Then GoTo Next_objDwgPole
        End If
        
        dE = objPoleMap.InsertionPoint(0)
        dN = objPoleMap.InsertionPoint(1)
        vLL = TN83FtoLL(CDbl(dN), CDbl(dE))
        
        vAttMap(7).TextString = vLL(0) & "," & vLL(1)
        objPoleMap.Update
        iPoles = iPoles + 1
        
        If cbIncludeDWG.Value = False Then GoTo Next_objDwgPole
        If objSSDwg.count < 1 Then GoTo Next_objDwgPole
        
        For Each objPoleDwg In objSSDwg
            vAttDwg = objPoleDwg.GetAttributes
            If vAttDwg(0).TextString = vAttMap(0).TextString Then
                vAttDwg(7).TextString = vAttMap(7).TextString
                objPoleDwg.Update
                iXfer = iXfer + 1
                GoTo Next_objDwgPole
            End If
            
        Next objPoleDwg
Next_objDwgPole:
    Next objPoleMap
    
Exit_Sub:
    objSSDwg.Clear
    objSSDwg.Delete
    
    objSSMap.Clear
    objSSMap.Delete
    
    LPole.Caption = iPoles & " / " & iXfer
End Sub

Private Function AddLLToBuried(strName As String)
    Dim filterType, filterValue As Variant
    Dim grpCode(0) As Integer
    Dim grpValue(0) As Variant
    Dim objSSDwg As AcadSelectionSet
    Dim objSSMap As AcadSelectionSet
    Dim objBlockDwg As AcadBlockReference
    Dim objBlockMap As AcadBlockReference
    Dim vAttDwg, vAttMap As Variant
    Dim strNumber, strOmit As String
    Dim strDwgLatLong, strMapLatLong As String
    Dim iItems, iXfer As Integer
    
    iItems = 0
    iXfer = 0
    strOmit = Replace(UCase(strName), "S", "")
        
    grpCode(0) = 2
    grpValue(0) = strName
    filterType = grpCode
    filterValue = grpValue
    
    Set objSSDwg = ThisDrawing.SelectionSets.Add("objSSDwg")
    objSSDwg.Select acSelectionSetWindow, vDwgLL, vDwgUR, filterType, filterValue
    
    Set objSSMap = ThisDrawing.SelectionSets.Add("objSSMap")
    objSSMap.Select acSelectionSetWindow, vMapLL, vMapUR, filterType, filterValue
    
    If objSSMap.count < 1 Then GoTo Exit_Sub
    
    For Each objBlockMap In objSSMap
        vAttMap = objBlockMap.GetAttributes
        If vAttMap(0).TextString = strOmit Then GoTo Next_objDwgPole
        If vAttMap(0).TextString = "" Then GoTo Next_objDwgPole
        
        If Not vAttMap(3).TextString = "" Then
            If cbOverwrite.Value = False Then GoTo Next_objDwgPole
        End If
        
        dE = objBlockMap.InsertionPoint(0)
        dN = objBlockMap.InsertionPoint(1)
        vLL = TN83FtoLL(CDbl(dN), CDbl(dE))
        
        vAttMap(3).TextString = vLL(0) & "," & vLL(1)
        objBlockMap.Update
        iItems = iItems + 1
        
        If cbIncludeDWG.Value = False Then GoTo Next_objDwgPole
        If objSSDwg.count < 1 Then GoTo Next_objDwgPole
        
        For Each objBlockDwg In objSSDwg
            vAttDwg = objBlockDwg.GetAttributes
            If vAttDwg(0).TextString = vAttMap(0).TextString Then
                vAttDwg(3).TextString = vAttMap(3).TextString
                objBlockDwg.Update
                iXfer = iXfer + 1
                GoTo Next_objDwgPole
            End If
            
        Next objBlockDwg
Next_objDwgPole:
    Next objBlockMap
    
Exit_Sub:
    objSSDwg.Clear
    objSSDwg.Delete
    
    objSSMap.Clear
    objSSMap.Delete
    
    AddLLToBuried = iItems & " / " & iXfer
End Function

Private Function TN83FtoLL(dNorth As Double, dEast As Double)
    Dim dLat, dLong, dDLat As Double
    Dim dDiffE, dEast0 As Double
    Dim dDiffN, dNorth0 As Double
    Dim dR, dCAR, dCA, dU, dK As Double
    Dim LL(2) As Double
    
    dEast = dEast * 0.3048006096
    dNorth = dNorth * 0.3048006096
    
    dDiffE = dEast - 600000
    dDiffN = dNorth - 166504.1691
    
    dR = 8842127.1422 - dDiffN
    dCAR = Atn(dDiffE / dR)
    dCA = dCAR * 180 / 3.14159265359
    dLong = -86 + dCA / 0.585439726459
    
    dU = dDiffN - dDiffE * Tan(dCAR / 2)
    dDLat = dU * (0.00000901305249 + dU * (-6.77268E-15 + dU * (-3.72351E-20 + dU * -9.2828E-28)))
    dLat = 35.8340607459 + dDLat
    
    dK = 0.999948401424 + (1.23188E-14 * dU * dU) + (4.54E-22 * dU * dU * dU)
    
    LL(0) = dLat
    LL(1) = dLong
    LL(2) = dK
    
    TN83FtoLL = LL
End Function

Attribute VB_Name = "TroubleTicket"
Attribute VB_Base = "0{F7497F69-0FCB-468B-B808-82219C7B5D56}{716AACDE-14E7-43E5-AA6E-5362F83C1089}"
Attribute VB_GlobalNameSpace = False
Attribute VB_Creatable = False
Attribute VB_PredeclaredId = True
Attribute VB_Exposed = False
Attribute VB_TemplateDerived = False
Attribute VB_Customizable = False

Dim strSubject As String

Private Sub cbApp_Change()
    tbSubject.Value = strSubject & cbApp.Value
End Sub

Private Sub cbQuit_Click()
    Me.Hide
End Sub

Private Sub cbSend_Click()
    If cbType.Value = "Complaints" Then
        
    End If
    
    Dim objOutlook As Outlook.Application
    Dim objMail As Outlook.MailItem
    Dim strBody As String

    Set objOutlook = New Outlook.Application
    Set objMail = objOutlook.CreateItem(olMailItem)
    
    Call ResetSubject
    strSubject = strSubject & cbApp.Value & " --> " & cbType.Value
    
    strBody = tbNote.Value '& vbCr & vbCr & "Example:" & vbCr & tbExample.Value
    If Not tbExample.Value = "" Then strBody = strBody & vbCr & vbCr & "Examples:" & vbCr & tbExample.Value
    strBody = Replace(strBody, vbCr, "<br>")
    strBody = Replace(strBody, vbLf, "")
    
    objMail.To = "rich.taylor@integrity-us.com"
    'objMail.To = objOutlook.Session.CurrentUser.Address
    objMail.CC = objOutlook.Session.CurrentUser.Address
    objMail.Subject = strSubject
    objMail.HTMLBody = strBody
    
    If InStr(cbType.Value, "High Priority") > 0 Then objMail.FlagRequest = "Follow up"
    
    If cbAttachment.Value = True Then
        objMail.Display
    Else
        objMail.Send
    End If
    
    Me.Hide
End Sub

Private Sub cbType_Change()
    tbSubject.Value = strSubject & cbApp.Value & " --> " & cbType.Value
    'If cbType.Value = "Complaints" Then tbNote.Value = "Hey Asshole," & vbCr & vbCr
End Sub

Private Sub UserForm_Initialize()
    cbApp.AddItem "Integrity Tools"
    cbApp.AddItem "HLE"
    cbApp.AddItem "AutoCAD"
    
    cbType.AddItem "Bug - High Priority"
    cbType.AddItem "Bug"
    'cbType.AddItem "Bug - Low Priority"
    cbType.AddItem "Request - High Priority"
    cbType.AddItem "Request / Suggestion"
    cbType.AddItem "Assistance - High Priority"
    cbType.AddItem "Assistance / Training"
    'cbType.AddItem "Complaints"
    
    'tbSubject.Value = "<Ticket #"
    Call ResetSubject
    tbSubject.Value = strSubject
End Sub

Private Sub ResetSubject()
    Dim strNumber As String
    Dim iTemp As Integer
    
    iTemp = Year(Date) - 2000
    strNumber = CStr(iTemp)
    
    iTemp = Month(Date)
    If iTemp < 10 Then
        strNumber = strNumber & "0" & CStr(iTemp)
    Else
        strNumber = strNumber & CStr(iTemp)
    End If
    
    iTemp = Day(Date)
    If iTemp < 10 Then
        strNumber = strNumber & "0" & CStr(iTemp) & "-"
    Else
        strNumber = strNumber & CStr(iTemp) & "-"
    End If
    
    iTemp = Hour(Time)
    If iTemp < 10 Then
        strNumber = strNumber & "0" & CStr(iTemp)
    Else
        strNumber = strNumber & CStr(iTemp)
    End If
    
    iTemp = Minute(Time)
    If iTemp < 10 Then
        strNumber = strNumber & "0" & CStr(iTemp) & "."
    Else
        strNumber = strNumber & CStr(iTemp) & "."
    End If
    
    iTemp = Second(Time)
    If iTemp < 10 Then
        strNumber = strNumber & "0" & CStr(iTemp)
    Else
        strNumber = strNumber & CStr(iTemp)
    End If
    
    strSubject = "<Ticket #" & strNumber & "> "
    
End Sub

Attribute VB_Name = "UnitForm"
Attribute VB_Base = "0{1E414AC7-A560-4179-A269-1F4E168868FA}{920A4155-A299-47B8-B2F9-4F3C7343FE2D}"
Attribute VB_GlobalNameSpace = False
Attribute VB_Creatable = False
Attribute VB_PredeclaredId = True
Attribute VB_Exposed = False
Attribute VB_TemplateDerived = False
Attribute VB_Customizable = False
Dim objBlock As AcadBlockReference
Dim iListIndex As Integer
Dim dScale As Double
Dim strLastUnit As String

Private Sub cbAddCommon_Click()
    If lbUnits.ListIndex < 0 Then Exit Sub
    
    Dim iIndex, i As Integer
    
    iIndex = lbUnits.ListIndex
    
    lbCommon.AddItem lbUnits.List(iIndex, 0)
    i = lbCommon.ListCount - 1
    
    lbCommon.List(i, 1) = lbUnits.List(iIndex, 1)
    If lbUnits.List(iIndex, 2) = Null Then
        lbCommon.List(i, 2) = lbUnits.List(iIndex, 2)
    Else
        lbCommon.List(i, 2) = lbUnits.List(iIndex, 2)
    End If
End Sub

Private Sub cbAddCommonUnits_Click()
    If lbCommon.ListCount < 1 Then Exit Sub
    
    Dim iIndex, i As Integer
    
    'iIndex = lbCommon.ListIndex
    For i = 0 To lbCommon.ListCount - 1
        lbUnits.AddItem lbCommon.List(i, 0)
        iIndex = lbUnits.ListCount - 1
    
        lbUnits.List(iIndex, 1) = lbCommon.List(i, 1)
        lbUnits.List(iIndex, 2) = lbCommon.List(i, 2)
    Next i
End Sub

Private Sub cbAddtoDWG_Click()
    Dim vAttList As Variant
    Dim strLine As String
    Dim i, iAtt As Integer
    
    strLine = ""
    
    If lbUnits.ListCount < 1 Then GoTo Add_Info
    
    strLine = lbUnits.List(0, 0) & "=" & lbUnits.List(0, 1)
    If Not lbUnits.List(0, 2) = "" Then strLine = strLine & "  " & lbUnits.List(0, 2)
    
    If lbUnits.ListCount > 1 Then
        For i = 1 To lbUnits.ListCount - 1
            strLine = strLine & ";;" & lbUnits.List(i, 0) & "=" & lbUnits.List(i, 1)
            If Not lbUnits.List(i, 2) = "" Then strLine = strLine & "  " & lbUnits.List(i, 2)
        Next i
    End If
Add_Info:
    Select Case objBlock.Name
        Case "sPole"
            iAtt = 27
        Case Else   '   "sPed", "sHH", "sFP"
            iAtt = 7
    End Select
    
    vAttItem = objBlock.GetAttributes
    
    vAttItem(iAtt).TextString = strLine
    objBlock.Update
End Sub

Private Sub cbAddUnit_Click()
    Dim str, strMsg, str2, str3 As String
    Dim varStr As Variant
    Dim vLine, vItem As Variant
    Dim result, iSize As Integer
    Dim iIndex As Integer
    
    If cbAddUnit.Caption = "Update Unit" Then
        lbUnits.Enabled = True
        cbPrefix.Enabled = True
        'cbAddUnit.Enabled = True
        'cbGetUnit.Enabled = True
        cbAddtoDWG.Enabled = True
        cbAddUnit.Caption = "Add Unit"
    
        lbUnits.RemoveItem iListIndex
        
        vLine = Split(tbUnit.Value, "=")
        lbUnits.AddItem vLine(0), iListIndex
        If InStr(vLine(1), "  ") > 0 Then
            vItem = Split(vLine(1), "  ")
            lbUnits.List(iListIndex, 1) = vItem(0)
            lbUnits.List(iListIndex, 2) = vItem(1)
        Else
            lbUnits.List(iListIndex, 1) = vLine(1)
            lbUnits.List(iListIndex, 2) = ""
        End If
    
        'cbUpdateUnit.Enabled = False
        Exit Sub
    End If
    
    str = tbUnit.Value
    If Right(str, 1) = "=" Then str = str & "1"
    
    Select Case Left(str, 4)
        Case "+HAC", "+HBF"
            If InStr(UCase(ThisDrawing.Path), "UNITED") > 0 Then
                'str = "+" & cbPrefix.Value & cbUnits.Value
                
                strMsg = "Will this serve customers?"
                result = MsgBox(strMsg, vbYesNo, "Closure Type")

                If result = vbYes Then
                    If cbUnits.Value = "(288)" Then
                        str = str & "  YJ"
                    Else
                        str = str & "  #1413 "
                    End If
                Else
                    str = str & "  " & cbSuffix.Value
                End If
            Else
                str = str & "  " & cbSuffix.Value
                
                If cbSuffix.Value = "G6S" Then
                    lbUnits.AddItem str
                    str = "+1X32 SPLITTER=1"
                'Else
                    'str = str & "  " & cbSuffix.Value
                End If
            End If
        Case "+CO(", "+BFO", "+UO("
            'str = str + "'"
            If cbSuffix.Value = "LOOP" Then str = str & "  LOOP"
        Case "+FDH"
            If cbUnits.Value = "432" Then
                str = "+OCFH432CADNABA2AL=1"
            Else
                str = "+OCFH" & cbUnits.Value & "CABNABA2AL=1"
            End If
            
            lbUnits.AddItem str
            str = "+1X32 SPLITTER=" & cbSuffix.Value
        Case "+WCA", "BM70", "BM72", "BM73"
            'str = str + "'"
        Case "+BM6"
            If Left(str, 5) = "+BM60" Then Call RemoveIfromBFO
            'str = str + "'"
        'Case "+UD(", "+RRC", "+PE2", "+R3-"
            'str = str + "'"
    End Select
    
    vLine = Split(str, "=")
    lbUnits.AddItem vLine(0)
    iIndex = lbUnits.ListCount - 1
    
    If InStr(vLine(1), "  ") > 0 Then
        vItem = Split(vLine(1), "  ")
        lbUnits.List(iIndex, 1) = vItem(0)
        lbUnits.List(iIndex, 2) = vItem(1)
    Else
        lbUnits.List(iIndex, 1) = vLine(1)
        lbUnits.List(iIndex, 2) = ""
    End If
    
    If Left(str, 4) = "+UD(" Then
        lbUnits.AddItem "+BM61D"
        iIndex = lbUnits.ListCount - 1
        lbUnits.List(iIndex, 1) = lbUnits.List(iIndex - 1, 1)
    End If
    
    strLastUnit = ""
cbPrefix.SetFocus
End Sub

Private Sub cbCallouts_Click()
    If lbUnits.ListCount < 1 Then Exit Sub
    
    Dim objSS As AcadSelectionSet
    Dim objBlock As AcadBlockReference
    Dim vAttList As Variant
    Dim strLayer As String
    Dim dInsertPnt(2) As Double
    Dim dScale As Double
    Dim dPosition As Double
    
    On Error Resume Next
    Me.Hide
    
    Set objSS = ThisDrawing.SelectionSets.Add("objSS")
    If Not Err = 0 Then
        Set objSS = ThisDrawing.SelectionSets.Item("objSS")
        Err = 0
    End If
    objSS.SelectOnScreen
    
    If objSS.count < 1 Then GoTo Exit_Sub
    
    dInsertPnt(0) = 0#
    dInsertPnt(1) = 0#
    dInsertPnt(2) = 0#
    
    For Each objBlock In objSS
        If objBlock.Name = "pole_unit" Then
            If objBlock.InsertionPoint(1) > dInsertPnt(1) Then
                dInsertPnt(0) = objBlock.InsertionPoint(0)
                dInsertPnt(1) = objBlock.InsertionPoint(1)
                dScale = objBlock.XScaleFactor
            End If
            strLayer = objBlock.Layer
            vAttList = objBlock.GetAttributes
            strAtt0 = vAttList(0).TextString
            objBlock.Delete
        End If
    Next objBlock
    
    dPosition = 2#
    
    For v = 0 To lbUnits.ListCount - 1
        strAtt1 = dPosition
        strAtt2 = "N/A"
        strAtt3 = lbUnits.List(v, 0) & "=" & lbUnits.List(v, 1)
        If Not lbUnits.List(v, 2) = "" Then strAtt3 = strAtt3 & "  " & lbUnits.List(v, 2)
    
        Set objBlock = ThisDrawing.ModelSpace.InsertBlock(dInsertPnt, "pole_unit", dScale, dScale, dScale, 0#)
        objBlock.Layer = strLayer
        
        vAttList = objBlock.GetAttributes
        vAttList(0).TextString = strAtt0
        vAttList(1).TextString = strAtt1
        vAttList(2).TextString = strAtt2
        vAttList(3).TextString = strAtt3
        objBlock.Update
    
        dInsertPnt(1) = dInsertPnt(1) - (9 * dScale)
    Next v
    
Exit_Sub:
    objSS.Clear
    objSS.Delete
    
    Me.show
End Sub

Private Sub cbCLR_Click()
    lbUnits.Clear
End Sub

Private Sub cbCombine_Click()
    If lbUnits.ListCount < 2 Then Exit Sub
    
    Dim vCurrent, vOther, vItem As Variant
    Dim strCurrent As String
    
    For i = lbUnits.ListCount - 1 To 0 Step -1
        strCurrent = lbUnits.List(i, 0)
        
        For j = 0 To i - 1
            If lbUnits.List(j, 0) = strCurrent Then
                lbUnits.List(j, 1) = CInt(lbUnits.List(j, 1)) + CInt(lbUnits.List(i, 1))
                lbUnits.RemoveItem i
                GoTo Next_I
            End If
        Next j
Next_I:
    Next i
End Sub

Private Sub cbDelete_Click()
    lbUnits.RemoveItem (lbUnits.ListIndex)
End Sub

Private Sub cbDOWN_Click()
    Dim str1 As String
    Dim i, i2 As Integer
    
    If lbUnits.ListIndex = (lbUnits.ListCount - 1) Then Exit Sub
    i = lbUnits.ListIndex
    i2 = i + 1
    str1 = lbUnits.List(i)
    lbUnits.List(i) = lbUnits.List(i2)
    lbUnits.List(i2) = str1
    
    lbUnits.ListIndex = i2
End Sub

Private Sub cbGetCallouts_Click()
    Dim objSS As AcadSelectionSet
    Dim objEntity As AcadEntity
    Dim objUnit As AcadBlockReference
    Dim objMText As AcadMText
    Dim vAtt As Variant
    Dim vLine, vItem, vTemp As Variant
    Dim strLine As String
    
    Me.Hide
    On Error Resume Next
    
    Set objSS = ThisDrawing.SelectionSets.Add("objSS")
    If Not Err = 0 Then
        Set objSS = ThisDrawing.SelectionSets.Item("objSS")
        objSS.Clear
        Err = 0
    End If
    
    objSS.SelectOnScreen
    
    If objSS.count = 0 Then GoTo Exit_Sub
    
    'lbUnits.Clear
    
    For Each objEntity In objSS
        If TypeOf objEntity Is AcadBlockReference Then
            Set objUnit = objEntity
            
            If Not objUnit.Name = "pole_unit" Then GoTo Next_objEntity
            
            vAtt = objUnit.GetAttributes
            vLine = Split(vAtt(3).TextString, "=")
            
            lbUnits.AddItem vLine(0), 0
            vItem = Split(vLine(1), "  ")
            lbUnits.List(0, 1) = Replace(vItem(0), "'", "")
            If UBound(vItem) > 0 Then lbUnits.List(0, 2) = vItem(1)
        End If
        
        If TypeOf objEntity Is AcadMText Then
            Set objMText = objEntity
            
            vLine = Split(objMText.TextString, "\P")
            
            For i = 0 To UBound(vLine)
                strLine = ""
                vItem = Split(vLine(i), "=")
                
                If vItem(0) = "+UNITS" Then GoTo Next_Unit
                If InStr(vItem(0), "(LOOP)") > 0 Then
                    vItem(0) = Replace(vItem(0), "(LOOP)", "")
                    strLine = "LOOP"
                End If
                
                If InStr(vItem(0), "FOSC") > 0 Then
                    vTemp = Split(vItem(0), "FOSC")
                    vItem(0) = vTemp(0)
                    strLine = "FOSC" & vTemp(1)
                End If
                
                lbUnits.AddItem vItem(0)
                lbUnits.List(lbUnits.ListCount - 1, 1) = Replace(vItem(1), "'", "")
                lbUnits.List(lbUnits.ListCount - 1, 2) = strLine
Next_Unit:
            Next i
        End If
Next_objEntity:
    Next objEntity
    
    If lbUnits.ListCount > 0 Then
        For i = lbUnits.ListCount - 1 To 0 Step -1
            If lbUnits.List(i, 0) = "+UNITS" Then lbUnits.RemoveItem i
        Next i
    End If
    
    If lbMissing.ListCount > 0 And lbUnits.ListCount > 0 Then
        For i = lbMissing.ListCount - 1 To 0 Step -1
            strTemp = lbMissing.List(i, 0)
            
            For j = 0 To lbUnits.ListCount - 1
                If InStr(lbUnits.List(j, 0), strTemp) > 0 Then
                    If lbMissing.List(i, 1) = "" Then
                        lbMissing.RemoveItem i
                        GoTo Next_Missing
                    End If
                    
                    If lbMissing.List(i, 1) = lbUnits.List(j, 1) Then
                        lbMissing.RemoveItem i
                        GoTo Next_Missing
                    Else
                        lbMissing.List(i, 1) = CInt(lbMissing.List(i, 1)) - CInt(lbUnits.List(j, 1))
                        GoTo Next_Missing
                    End If
                End If
            Next j
            
Next_Missing:
        Next i
    End If
    
Exit_Sub:
    objSS.Clear
    objSS.Delete
    
    Me.show
End Sub

Private Sub cbGetExisting_Click()
    Dim objObject As AcadObject
    Dim vBasePnt, vAttList As Variant
    Dim vLine, vItem, vTemp As Variant
    Dim strTemp, strType, strGround As String
    Dim iAtt As Integer
    
    Me.Hide
  On Error Resume Next
    
    ThisDrawing.Utility.GetEntity objObject, vBasePnt, "Select Pole/Buried Plant: "
    If TypeOf objObject Is AcadBlockReference Then
        Set objBlock = objObject
    Else
        MsgBox "Not a valid object."
        Me.show
        Exit Sub
    End If
    
    Select Case objBlock.Name
        Case "sPed", "sHH", "sFP", "sPanel", "sMH"
            iAtt = 7
        Case "sPole"
            iAtt = 27
        Case Else
            MsgBox "Not a valid block."
            Me.show
            Exit Sub
    End Select
    
    vAttList = objBlock.GetAttributes
    
    lbUnits.Clear
    
    If Not vAttList(iAtt).TextString = "" Then
        vAttList(iAtt).TextString = Replace(vAttList(iAtt).TextString, vbLf, "")
        vLine = Split(vAttList(iAtt).TextString, ";;")
        For i = 0 To UBound(vLine)
            If Not Left(vLine(i), 1) = "+" Then vLine(i) = "+" & vLine(i)
            
            vItem = Split(vLine(i), "=")
            lbUnits.AddItem vItem(0)
            
            vItem(1) = Replace(vItem(1), "'", "")
            If InStr(vItem(1), "  ") > 0 Then
                vTemp = Split(vItem(1), "  ")
                lbUnits.List(lbUnits.ListCount - 1, 1) = vTemp(0)
                lbUnits.List(lbUnits.ListCount - 1, 2) = vTemp(1)
            Else
                lbUnits.List(lbUnits.ListCount - 1, 1) = vItem(1)
                lbUnits.List(lbUnits.ListCount - 1, 2) = ""
            End If
        Next i
    End If
    
    cbAddtoDWG.Enabled = True
    cbCallouts.Enabled = True
    cbGetCallouts.Enabled = True
    
    'Dim strLine, strInfo As String
    Dim strCable As String
    Dim strClient As String
    Dim iIndex As Integer
    
    tbStructure.Value = vAttList(0).TextString
    
    lbMissing.Clear
    lbAttach.Clear
    
    lbInfo.Clear
    lbInfo.AddItem "Block:"
    lbInfo.List(0, 1) = objBlock.Name
    
    Select Case objBlock.Name
        Case "sPole"
            lbInfo.AddItem "Owner:"
            lbInfo.List(1, 1) = vAttList(2).TextString
            
            lbInfo.AddItem "H-C:"
            lbInfo.List(2, 1) = vAttList(5).TextString
            
            lbInfo.AddItem "Ground:"
            lbInfo.List(3, 1) = vAttList(8).TextString
            
            For i = 9 To 14
                If Not vAttList(i).TextString = "" Then
                    vLine = Split(vAttList(i).TextString, " ")
                    
                    For j = 0 To UBound(vLine)
                        lbAttach.AddItem vAttList(i).TagString
                        iIndex = lbAttach.ListCount - 1
                        lbAttach.List(iIndex, 1) = vLine(j)
                    Next j
                End If
            Next i
            
            If Not vAttList(15).TextString = "" Then
                vLine = Split(vAttList(15).TextString, " ")
                    
                For j = 0 To UBound(vLine)
                    lbAttach.AddItem "--> NEW"
                    iIndex = lbAttach.ListCount - 1
                    lbAttach.List(iIndex, 1) = vLine(j)
                Next j
            End If
            
            For i = 16 To 23
                If Not vAttList(i).TextString = "" Then
                    vTemp = Split(vAttList(i).TextString, "=")
                    vLine = Split(vTemp(1), " ")
                    
                    For j = 0 To UBound(vLine)
                        lbAttach.AddItem vTemp(0)
                        iIndex = lbAttach.ListCount - 1
                        lbAttach.List(iIndex, 1) = vLine(j)
                    Next j
                End If
            Next i
            
            If Not vAttList(25).TextString = "" Then
                vLine = Split(vAttList(25).TextString, " / ")
                vItem = Split(vLine(0), ": ")
                lbMissing.AddItem "+" & vItem(1)
                lbMissing.List(lbMissing.ListCount - 1, 1) = ""
    
                Select Case Left(UCase(vAttList(8).TextString), 1)
                    Case "M", "T"
                        strGround = "Y"
                    Case Else
                        strGround = ""
                End Select
                
                vTemp = Split(vItem(1), ")")
                If InStr(vTemp(1), "M") > 0 And strGround = "Y" Then
                    iIndex = 0
                    For i = 0 To lbAttach.ListCount - 1
                        If lbAttach.List(i, 0) = "--> NEW" Then iIndex = iIndex + 1
                    Next i
                    If iIndex = 0 Then iIndex = 1
                    
                    lbMissing.AddItem "+PM2A"
                    lbMissing.List(lbMissing.ListCount - 1, 1) = iIndex
                End If
            End If
            
            If Not vAttList(26).TextString = "" Then
                lbMissing.AddItem "+HACO"
                lbMissing.List(lbMissing.ListCount - 1, 1) = ""
                
                lbMissing.AddItem "+PM52"
                lbMissing.List(lbMissing.ListCount - 1, 1) = "1"
            End If
            
            vLine = Split(UCase(ThisDrawing.Path), "DROPBOX\")
            If UBound(vLine) < 0 Then
                Select Case Left(vLine(1), 4)
                    Case "UNIT"
                        strClient = "UTC"
                    Case "TDS "
                        strClient = "TDS"
                    Case "LORE"
                        strClient = "LOR"
                    'Case "MAST"
                        'strClient = "ZAYO"
                    'Case "ECC "
                        'strClient = "ZAYO"
                    Case Else
                        strClient = "***"
                End Select
                
                If lbAttach.ListCount > 0 Then
                    For i = 0 To lbAttach.ListCount - 1
                        If InStr(lbAttach.List(i, 0), strClient) > 0 Then
                            If InStr(lbAttach.List(i, 1), ")") > 0 Or InStr(UCase(lbAttach.List(i, 1)), "X") > 0 Then
                                lbMissing.AddItem "+WC1"
                                lbMissing.List(lbMissing.ListCount - 1, 1) = "1"
                                
                                lbMissing.AddItem "+WC2"
                                lbMissing.List(lbMissing.ListCount - 1, 1) = "1"
                            End If
                        End If
                    Next i
                End If
            End If
            
        Case Else
            lbInfo.AddItem "Type:"
            lbInfo.List(1, 1) = vAttList(2).TextString
            
            lbInfo.AddItem "Ground:"
            lbInfo.List(2, 1) = vAttList(4).TextString
            
            If Not vAttList(5).TextString = "" Then
                vLine = Split(vAttList(5).TextString, " / ")
                vItem = Split(vLine(0), ": ")
                lbMissing.AddItem "+" & vItem(1)
                lbMissing.List(lbMissing.ListCount - 1, 1) = ""
    
                Select Case Left(UCase(vAttList(8).TextString), 1)
                    Case "M", "T"
                        lbMissing.AddItem "+BM2A"
                        lbMissing.List(lbMissing.ListCount - 1, 1) = "1"
                    Case "T"
                        lbMissing.AddItem "+BM2(5/8X8)"
                        lbMissing.List(lbMissing.ListCount - 1, 1) = "1"
                End Select
                
                vTemp = Split(vItem(1), ")")
                If InStr(vTemp(1), "M") > 0 And strGround = "Y" Then
                    lbMissing.AddItem "+PM2A"
                    lbMissing.List(lbMissing.ListCount - 1, 1) = "1"
                End If
            End If
            
            If Not vAttList(26).TextString = "" Then
                lbMissing.AddItem "+HBFO"
                lbMissing.List(lbMissing.ListCount - 1, 1) = ""
            End If
    End Select
    
    If lbMissing.ListCount > 0 And lbUnits.ListCount > 0 Then
        For i = lbMissing.ListCount - 1 To 0 Step -1
            strTemp = lbMissing.List(i, 0)
            
            For j = 0 To lbUnits.ListCount - 1
                If InStr(lbUnits.List(j, 0), strTemp) > 0 Then
                    If lbMissing.List(i, 1) = "" Then
                        lbMissing.RemoveItem i
                        GoTo Next_Missing
                    End If
                    
                    If lbMissing.List(i, 1) = lbUnits.List(j, 1) Then
                        lbMissing.RemoveItem i
                        GoTo Next_Missing
                    Else
                        lbMissing.List(i, 1) = CInt(lbMissing.List(i, 1)) - CInt(lbUnits.List(j, 1))
                        GoTo Next_Missing
                    End If
                End If
            Next j
            
Next_Missing:
        Next i
    End If
    
    Me.show
End Sub

Private Sub cbGetUnits_Click()
    Dim objSS As AcadSelectionSet
    Dim objItem As AcadObject
    Dim obrUnit As AcadBlockReference
    Dim vAttList, vCblList, vTemp As Variant
    Dim vList1, vList2, vList3 As Variant
    Dim str1, str2, str3, strLine As String
    Dim strUnit, strQty, strNote As String
    Dim strCblSize As String
    
    strCblSize = "24"
    Me.Hide
    On Error Resume Next
    
    Set objSS = ThisDrawing.SelectionSets.Add("objSS")
    If Not Err = 0 Then
        Set objSS = ThisDrawing.SelectionSets.Item("objSS")
        objSS.Clear
        Err = 0
    End If
    
    objSS.SelectOnScreen
    
    If objSS.count = 0 Then GoTo Exit_Sub
    
    lbUnits.Clear
    
    For Each objItem In objSS
        If TypeOf objItem Is AcadBlockReference Then
            Set obrUnit = objItem
            'MsgBox obrUnit.Layer
            'GoTo exit_sub
            Select Case obrUnit.Name
                Case "cable_span"
                    vAttList = obrUnit.GetAttributes
                    vCblList = Split(vAttList(1).TextString, " ")
                    vTemp = Split(vAttList(2).TextString, "' ")
                    If UBound(vTemp) > 0 Then
                        str2 = Replace(vTemp(0), "+", "")
                    Else
                        str2 = Replace(vTemp(0), "'", "")
                    End If
                    'str2 = vAttList(2).TextString
                    'str2 = Left(str2, Len(str2) - 1)
                    
                    For i = LBound(vCblList) To UBound(vCblList)
                        str1 = vCblList(i)
                        If str1 = "" Then GoTo Next_Item
                        If UCase(Right(str1, 1)) = "F" Then str1 = Left(str1, Len(str1) - 1)
                        
                        If obrUnit.Layer = "Integrity Cable-Aerial Text" Then
                            strUnit = "+CO(" & str1 & ")"
                            If i = 0 Then
                                strUnit = strUnit & "6M-EHS"
                            Else
                                strUnit = strUnit & "E"
                            End If
                        Else
                            strUnit = "+UO(" & str1 & ")"
                            
                            lbUnits.AddItem "+RRCONDUIT"
                            lbUnits.List(lbUnits.ListCount - 1, 1) = str2
                            lbUnits.List(lbUnits.ListCount - 1, 2) = ""
                            'strline = "+RRCONDUIT=" & str2 '& "'"
                        End If
                        
                        lbUnits.AddItem strUnit
                        lbUnits.List(lbUnits.ListCount - 1, 1) = str2
                        lbUnits.List(lbUnits.ListCount - 1, 2) = ""
Next_Item:
                    Next i
                Case "Map coil"
                    vAttList = obrUnit.GetAttributes
                    str1 = Replace(vAttList(0).TextString, "'", "")
                    'str1 = Left(str1, Len(str1) - 1)
                    str2 = vAttList(1).TextString
                    str2 = Replace(str2, "F", "")
                    str2 = Replace(str2, " ", "")
                    'str2 = Left(str2, Len(str2) - 1)
                    
                    If obrUnit.Layer = "Integrity Map Coils-Aerial" Then
                        strUnit = "+CO(" & str2 & ")E" '& str1 & " (LOOP)"
                    Else
                        strUnit = "+UO(" & str2 & ")" '& str1 & " (LOOP)"
                    End If
                    strQty = str1
                    'strNote = "LOOP"
                    
                    If CInt(str2) > CInt(strCblSize) Then strCblSize = str2
                    
                    lbUnits.AddItem strUnit
                    lbUnits.List(lbUnits.ListCount - 1, 1) = strQty
                    lbUnits.List(lbUnits.ListCount - 1, 2) = "LOOP"
                'Case "iClosure"
                Case "Map splice"
                    vAttList = obrUnit.GetAttributes
                    str1 = vAttList(0).TextString
                    
                    If obrUnit.Layer = "Integrity Map Splices-Aerial" Then
                        strLine = "+HACO(" & strCblSize & ")=1  " & str1
                    Else
                        strLine = "+HBFO(" & strCblSize & ")=1  " & str1
                    End If
                    
                    strCblSize = str2
                    lbUnits.AddItem strLine
                    lbUnits.List(lbUnits.ListCount - 1, 1) = "1"
                    lbUnits.List(lbUnits.ListCount - 1, 2) = str1
                Case "iClosure"
                    vAttList = obrUnit.GetAttributes
                    str1 = vAttList(0).TextString
                    
                    Select Case str1
                        Case "G5"
                            strUnit = "(288)"  '=1  G5"
                        Case "G4"
                            If strCblSize = "24" Then
                                strUnit = "(24)"   '=1  G4"
                            Else
                                strUnit = "(" & strCblSize & ")"   '=1  G4"
                            End If
                    End Select
                    
                    If obrUnit.Layer = "Integrity Map Splices-Aerial" Then
                        strUnit = "+HACO" & strUnit
                    Else
                        strUnit = "+HBFO" & strUnit
                    End If
                    
                    strCblSize = str2
                    lbUnits.AddItem strUnit
                    lbUnits.List(lbUnits.ListCount - 1, 1) = "1"
                    lbUnits.List(lbUnits.ListCount - 1, 2) = str1
                Case "pole_attach"
                    vAttList = obrUnit.GetAttributes
                    If InStr(vAttList(2).TextString, "UTC") > 0 Then
                        If Not vAttList(4).TextString = "" Then
                            'strline = "+WC1=1"
                            lbUnits.AddItem "+WC1"
                            lbUnits.List(lbUnits.ListCount - 1, 1) = "1"
                            lbUnits.List(lbUnits.ListCount - 1, 2) = ""
                        End If
                    End If
                Case "pole_info"
                    vAttList = obrUnit.GetAttributes
                    If vAttList(1).TextString = "0.1" Then
                        If vAttList(2).TextString = "UTC" Then
                            vCblList = Split(vAttList(3).TextString, "-")
                            If CInt(vCblList(1)) > 5 Then
                                lbUnits.AddItem "+A" & vCblList(0) & "-4=1"
                                lbUnits.AddItem "+WC1=1"
                                lbUnits.AddItem "+XXPOLE=1"
                                
                                vAttList(3).TextString = "(" & vAttList(3).TextString & ") " & vCblList(0) & "-4"
                                obrUnit.Update
                            End If
                        End If
                    End If
                Case "grd"
                    If obrUnit.Layer = "Integrity Proposed" Then
                        strLine = "+PM2A=1"
                    End If
                    
                    lbUnits.AddItem strLine
                Case "IS_Pwr_Pole"
                    vAttList = obrUnit.GetAttributes
                    vList1 = Split(vAttList(0).TextString, "/")
                    vList2 = Split(vList1(UBound(vList1)), "L")
                    vList3 = Split(vList2(UBound(vList2)), "R")
                    str1 = vList3(UBound(vList3))
                    If Right(str1, 1) = "5" Or Right(str1, 1) = "0" Then
                        lbUnits.AddItem "+PM52=1"
                    End If
                Case "ExGuyOR", "ExGuyOL"
                    vAttList = obrUnit.GetAttributes
                    str1 = vAttList(2).TextString
                    If obrUnit.Layer = "Integrity Proposed" Then
                        strLine = "+" & str1 & "=1"
                        lbUnits.AddItem strLine
                        lbUnits.AddItem "+PM11=1"
                    End If
                    If obrUnit.Layer = "Integrity Guys" Then
                        strLine = "+" & str1 & "=1"
                        lbUnits.AddItem strLine
                        lbUnits.AddItem "+PM11=2"
                    End If
                Case "ohgL", "ohgR"
                    vAttList = obrUnit.GetAttributes
                    str1 = vAttList(1).TextString
                    str2 = vAttList(0).TextString
                    
                    If obrUnit.Layer = "Integrity Proposed" Then
                        strLine = "+" & str1 & "=" & str2
                        lbUnits.AddItem strLine
                    End If
                Case "ExAncOR", "ExAncOL"
                    vAttList = obrUnit.GetAttributes
                    str1 = vAttList(0).TextString
                    
                    If obrUnit.Layer = "Integrity Proposed" Then
                        strLine = "+" & str1 & "=1"
                        lbUnits.AddItem strLine
                    End If
                    If obrUnit.Layer = "Integrity Guys" Then
                        strLine = "+" & str1 & "=1"
                        lbUnits.AddItem strLine
                    End If
                Case "notes"
                    vAttList = obrUnit.GetAttributes
                    vList1 = vAttList(0).TextString
                    vList2 = Split(vList1, "=")
                    
                    If vList2(0) = "T.T" Then
                        strLine = "+R3-5=" & vList2(1)
                        lbUnits.AddItem strLine
                    End If
                Case "__Trim"
                    vAttList = obrUnit.GetAttributes
                    vList1 = vAttList(0).TextString
                    vList2 = Split(vList1, "=")
                    
                    'If vList2(0) = "T.T" Then
                        strLine = "+R3-5=" & vList2(1)
                        If Not Right(vList2(1), 1) = "'" Then
                            strLine = strLine & "'"
                        End If
                        lbUnits.AddItem strLine
                    'End If
                Case "iLHH", "iLPED"
                    vAttList = obrUnit.GetAttributes
                    str1 = "+" & vAttList(1).TextString & "=1"
                    lbUnits.AddItem str1
                Case "iPorts"
                    vAttList = obrUnit.GetAttributes
                    str1 = "+" & vAttList(0).TextString & " PORT TERM=1"
                    lbUnits.AddItem str1
            End Select
        End If
    Next objItem
    
Exit_Sub:
    ssUnits8.Clear
    ssUnits8.Delete
    Me.show
End Sub

Private Sub cbQuit_Click()
    Dim layerObj As AcadLayer
  On Error Resume Next
    Set layerObj = ThisDrawing.Layers.Add("0")
    
    ThisDrawing.ActiveLayer = layerObj
    Me.Hide
End Sub

Private Sub cbPrefix_Change()
    cbUnits.Clear
    cbSuffix.Clear
    
    tbUnit.Value = "+" & cbPrefix.Value
    
    Select Case cbPrefix.Value
        Case "A"
            cbUnits.AddItem "30-4"
            cbUnits.AddItem "30-5"
            cbUnits.AddItem "30-6"
            cbUnits.AddItem "30-7"
            cbUnits.AddItem "35-4"
            cbUnits.AddItem "40-4"
            cbUnits.AddItem "40-5"
            cbUnits.AddItem "45-4"
            cbUnits.AddItem "45-5"
            cbUnits.AddItem "50-3"
        Case "BA"
            cbUnits.AddItem "2"
            cbUnits.AddItem "3"
            cbUnits.AddItem "4"
            cbUnits.AddItem "5"
        Case "BDO"
            cbUnits.AddItem "3"
            cbUnits.AddItem "4"
            cbUnits.AddItem "5"
            cbUnits.AddItem "7"
        Case "BFO"
            cbUnits.AddItem "(12)"
            cbUnits.AddItem "(24)"
            cbUnits.AddItem "(36)"
            cbUnits.AddItem "(48)"
            cbUnits.AddItem "(72)"
            cbUnits.AddItem "(144)"
            cbUnits.AddItem "(216)"
            cbUnits.AddItem "(288)"
            cbUnits.AddItem "(432)"
                cbSuffix.AddItem ""
                cbSuffix.AddItem "I"
                cbSuffix.AddItem "T"
                cbSuffix.AddItem "LOOP"
        Case "BHF"
            cbUnits.AddItem "(30X48X36)"
                cbSuffix.AddItem ""
                cbSuffix.AddItem "T"
        Case "BM"
            cbUnits.AddItem "2(5/8)(8)"
            cbUnits.AddItem "2A"
            cbUnits.AddItem "6M"
            cbUnits.AddItem "10M"
            cbUnits.AddItem "21"
            cbUnits.AddItem "52"
            cbUnits.AddItem "53"
            cbUnits.AddItem "60"
            cbUnits.AddItem "61"
            cbUnits.AddItem "61D"
            cbUnits.AddItem "71"
            cbUnits.AddItem "72"
            cbUnits.AddItem "73"
            cbUnits.AddItem "80"
            cbUnits.AddItem "81"
            cbUnits.AddItem "82"
            cbUnits.AddItem "83"
        Case "CO"
            cbUnits.AddItem "(12)"
            cbUnits.AddItem "(24)"
            cbUnits.AddItem "(36)"
            cbUnits.AddItem "(48)"
            cbUnits.AddItem "(72)"
            cbUnits.AddItem "(96)"
            cbUnits.AddItem "(144)"
            cbUnits.AddItem "(216)"
            cbUnits.AddItem "(288)"
            cbUnits.AddItem "(432)"
                cbSuffix.AddItem ""
                cbSuffix.AddItem "E"
                cbSuffix.AddItem "6M-EHS"
                cbSuffix.AddItem "6M"
                cbSuffix.AddItem "10M"
                cbSuffix.AddItem "LOOP"
        Case "FDH"
            cbUnits.AddItem "96"
            cbUnits.AddItem "144"
            cbUnits.AddItem "288"
            cbUnits.AddItem "432"
                cbSuffix.AddItem "1"
                cbSuffix.AddItem "2"
                cbSuffix.AddItem "3"
                cbSuffix.AddItem "4"
                cbSuffix.AddItem "5"
                cbSuffix.AddItem "6"
                cbSuffix.AddItem "7"
                cbSuffix.AddItem "8"
                cbSuffix.AddItem "9"
                cbSuffix.AddItem "10"
                cbSuffix.AddItem "11"
                cbSuffix.AddItem "12"
                cbSuffix.AddItem "13"
                cbSuffix.AddItem "14"
        Case "HACO"
            cbUnits.AddItem "(12)"
            cbUnits.AddItem "(24)"
            cbUnits.AddItem "(36)"
            cbUnits.AddItem "(48)"
            cbUnits.AddItem "(72)"
            cbUnits.AddItem "(96)"
            cbUnits.AddItem "(144)"
            cbUnits.AddItem "(216)"
            cbUnits.AddItem "(288)"
            cbUnits.AddItem "(432)"
                cbSuffix.AddItem "#1413"
                cbSuffix.AddItem "FOSC A"
                cbSuffix.AddItem "FOSC B"
                cbSuffix.AddItem "FOSC D"
                cbSuffix.AddItem "G4"
                cbSuffix.AddItem "G5"
                cbSuffix.AddItem "G6"
                cbSuffix.AddItem "G6S"
        Case "HBFO"
            cbUnits.AddItem "(12)"
            cbUnits.AddItem "(24)"
            cbUnits.AddItem "(36)"
            cbUnits.AddItem "(48)"
            cbUnits.AddItem "(72)"
            cbUnits.AddItem "(96)"
            cbUnits.AddItem "(144)"
            cbUnits.AddItem "(216)"
            cbUnits.AddItem "(288)"
            cbUnits.AddItem "(432)"
        Case "PE"
            cbUnits.AddItem "1-2"
            cbUnits.AddItem "1-3"
            cbUnits.AddItem "1-4"
            cbUnits.AddItem "2-2"
            cbUnits.AddItem "2-3"
            cbUnits.AddItem "2-4"
                cbSuffix.AddItem ""
                cbSuffix.AddItem "G"
        Case "PF"
            cbUnits.AddItem "1-5"
            cbUnits.AddItem "1-7"
            cbUnits.AddItem "3-5"
            cbUnits.AddItem "5-3"
            cbUnits.AddItem "5-4"
                cbSuffix.AddItem ""
                cbSuffix.AddItem "A"
        Case "PM"
            cbUnits.AddItem "2"
            cbUnits.AddItem "2A"
            cbUnits.AddItem "11"
            cbUnits.AddItem "21"
            cbUnits.AddItem "52"
        Case "R"
            cbUnits.AddItem "1-5"
            cbUnits.AddItem "2-5"
            cbUnits.AddItem "1-10"
            cbUnits.AddItem "2-10"
            cbUnits.AddItem "3-5"
        Case "SE"
            cbUnits.AddItem "AO2"
            cbUnits.AddItem "BO2"
            cbUnits.AddItem "AO12"
            cbUnits.AddItem "BO12"
        Case "UD"
            cbUnits.AddItem "(1X1-2)"
            cbUnits.AddItem "(1X2-2)"
            cbUnits.AddItem "(1X1-4)"
        Case "UHF"
            cbUnits.AddItem "(17X30X18)"
            cbUnits.AddItem "(24X36X24)"
            cbUnits.AddItem "(30X48X36)"
            cbUnits.AddItem "(36X60X36)"
        Case "UO"
            cbUnits.AddItem "(12)"
            cbUnits.AddItem "(24)"
            cbUnits.AddItem "(36)"
            cbUnits.AddItem "(48)"
            cbUnits.AddItem "(72)"
            cbUnits.AddItem "(96)"
            cbUnits.AddItem "(144)"
            cbUnits.AddItem "(216)"
            cbUnits.AddItem "(288)"
            cbUnits.AddItem "(432)"
                cbSuffix.AddItem ""
                cbSuffix.AddItem "LOOP"
        Case "UHF"
            cbUnits.AddItem "(24X36X24)"
        Case "W"
            cbUnits.AddItem "CA"
            cbUnits.AddItem "C1"
            cbUnits.AddItem "C2"
            cbUnits.AddItem "PE"
            cbUnits.AddItem "PE2"
            cbUnits.AddItem "HACO"
            cbUnits.AddItem "HBFO"
            cbUnits.AddItem "POLE"
            cbUnits.AddItem "SEA"
            cbUnits.AddItem "SEB"
            cbUnits.AddItem "SUD"
            cbUnits.AddItem "UD"
        Case "XX"
            cbUnits.AddItem "PE"
            cbUnits.AddItem "PE2"
            cbUnits.AddItem "PF"
            cbUnits.AddItem "PM11"
            cbUnits.AddItem "PM52"
            cbUnits.AddItem "POLE"
            cbUnits.AddItem "PED"
            cbUnits.AddItem "HH"
            cbUnits.AddItem "SEA"
            cbUnits.AddItem "CABLE"
            cbUnits.AddItem "CABLE & STRAND"
            cbUnits.AddItem "STRAND"
    End Select
End Sub

Private Sub cbSort_Click()
    Dim strCO, strUO, strBDO, strHACO As String
    Dim strBM, strPM, strPE, strPF As String
    Dim strMisc, strTemp As String
    Dim vTemp As Variant
    
    strCO = ""
    strUO = ""
    strBDO = ""
    strHACO = ""
    strBM = ""
    strPM = ""
    strPE = ""
    strPF = ""
    strMisc = ""
    
    For i = 0 To lbUnits.ListCount - 1
        strTemp = lbUnits.List(i)
        Select Case Left(strTemp, 3)
            Case "+CO"
                strCO = strCO & strTemp & "**"
            Case "+UO"
                strUO = strUO & strTemp & "**"
            Case "+BD", "+UH"
                strBDO = strBDO & strTemp & "**"
            Case "+HA", "+HB"
                strHACO = strHACO & strTemp & "**"
            Case "+BM"
                strBM = strBM & strTemp & "**"
            Case "+PM"
                strPM = strPM & strTemp & "**"
            Case "+PE"
                strPE = strPE & strTemp & "**"
            Case "+PF"
                strPF = strPF & strTemp & "**"
            Case Else
                strMisc = strMisc & strTemp & "**"
        End Select
    Next i
    
    lbUnits.Clear
    
    vTemp = Split(strCO, "**")
    For i = 0 To UBound(vTemp) - 1
        lbUnits.AddItem vTemp(i)
    Next i
    
    vTemp = Split(strUO, "**")
    For i = 0 To UBound(vTemp) - 1
        lbUnits.AddItem vTemp(i)
    Next i
    
    vTemp = Split(strBDO, "**")
    For i = 0 To UBound(vTemp) - 1
        lbUnits.AddItem vTemp(i)
    Next i
    
    vTemp = Split(strHACO, "**")
    For i = 0 To UBound(vTemp) - 1
        lbUnits.AddItem vTemp(i)
    Next i
    
    vTemp = Split(strBM, "**")
    For i = 0 To UBound(vTemp) - 1
        lbUnits.AddItem vTemp(i)
    Next i
    
    vTemp = Split(strPE, "**")
    For i = 0 To UBound(vTemp) - 1
        lbUnits.AddItem vTemp(i)
    Next i
    
    vTemp = Split(strPF, "**")
    For i = 0 To UBound(vTemp) - 1
        lbUnits.AddItem vTemp(i)
    Next i
    
    vTemp = Split(strPM, "**")
    For i = 0 To UBound(vTemp) - 1
        lbUnits.AddItem vTemp(i)
    Next i
    
    vTemp = Split(strMisc, "**")
    For i = 0 To UBound(vTemp) - 1
        lbUnits.AddItem vTemp(i)
    Next i
End Sub

Private Sub cbSuffix_Change()
    If cbSuffix.Value = "LOOP" Then
        If cbPrefix.Value = "CO" Then
            tbUnit.Value = "+" & cbPrefix.Value & cbUnits.Value & "E="
        Else
            tbUnit.Value = "+" & cbPrefix.Value & cbUnits.Value & "="
        End If
    Else
        If cbPrefix.Value = "HACO" Or cbPrefix.Value = "HBFO" Then
            tbUnit.Value = "+" & cbPrefix.Value & cbUnits.Value & "="
        Else
            tbUnit.Value = "+" & cbPrefix.Value & cbUnits.Value & cbSuffix.Value & "="
        End If
    End If
    
    tbUnit.SetFocus
End Sub

Private Sub cbUnits_Change()
    tbUnit.Value = "+" & cbPrefix.Value & cbUnits.Value
    
    If cbPrefix.Value = "CO" Then cbSuffix.Value = ""
    If cbPrefix.Value = "HACO" Then cbSuffix.Value = ""
    If cbPrefix.Value = "HBFO" Then cbSuffix.Value = ""
    
    Select Case tbUnit.Value
        Case "+BM60"
            cbSuffix.Clear
            cbSuffix.AddItem "(1.25)D"
            cbSuffix.AddItem "(1.5)D"
            cbSuffix.AddItem "(2)"
            cbSuffix.AddItem "(2)D"
            cbSuffix.AddItem "(4)"
            cbSuffix.AddItem "(4)D"
            cbSuffix.AddItem "(4)DS"
            cbSuffix.AddItem "(4)DSR"
            cbSuffix.AddItem "(4)DSRR"
            cbSuffix.AddItem "(4)S"
            cbSuffix.AddItem "(4)SR"
            cbSuffix.AddItem "(4)SRR"
            cbSuffix.AddItem "(4)R"
            cbSuffix.AddItem "(4)RR"
        Case "+BM61"
            cbSuffix.Clear
            cbSuffix.AddItem ""
            cbSuffix.AddItem "D"
        Case Else
            If Left(tbUnit.Value, 5) = "+HACO" Or Left(tbUnit.Value, 5) = "+HBFO" Then
                Dim str As String
                
                str = Replace(cbUnits.Value, "(", "")
                str = Replace(str, ")", "")
                Select Case str
                    Case "12", "24"
                        If InStr(UCase(ThisDrawing.Path), "LORETTO") > 0 Then
                            cbSuffix.Value = "G4"
                        Else
                            cbSuffix.Value = "FOSC A"
                        End If
                    Case "36", "48"
                        If InStr(UCase(ThisDrawing.Path), "LORETTO") > 0 Then
                            cbSuffix.Value = "G5"
                        Else
                            cbSuffix.Value = "FOSC A"
                        End If
                    Case "72", "96"
                        If InStr(UCase(ThisDrawing.Path), "LORETTO") > 0 Then
                            cbSuffix.Value = "G5"
                        Else
                            cbSuffix.Value = "FOSC B"
                        End If
                    Case "144"
                        If InStr(UCase(ThisDrawing.Path), "LORETTO") > 0 Then
                            cbSuffix.Value = "G5"
                        Else
                            cbSuffix.Value = "FOSC D"
                        End If
                    Case Else
                        If InStr(UCase(ThisDrawing.Path), "LORETTO") > 0 Then
                            cbSuffix.Value = "G6"
                        Else
                            cbSuffix.Value = "FOSC D"
                        End If
                End Select
                'tbUnit.Value = tbUnit.Value & "="
                'tbUnit.SetFocus
            Else
                tbUnit.Value = tbUnit.Value & "="
                tbUnit.SetFocus
            End If
    End Select
End Sub

Private Sub l1x32_Click()
    If lbUnits.ListCount < 1 Then
        lbUnits.AddItem "+1X32 SPLITTER"
        lbUnits.List(0, 1) = "1"
        Exit Sub
    End If
    
    For i = 0 To lbUnits.ListCount - 1
        If lbUnits.List(i, 0) = "+1X32 SPLITTER" Then
            lbUnits.List(i, 1) = CInt(lbUnits.List(i, 1)) + 1
            Exit Sub
        End If
    Next i
    
    lbUnits.AddItem "+1X32 SPLITTER"
    lbUnits.List(lbUnits.ListCount - 1, 1) = "1"
End Sub

Private Sub Label10_Click()
    Dim str1, str2 As String
    
    On Error Resume Next
    
    If lbUnits.ListCount < 1 Then
        lbUnits.AddItem "+PE1-2G=1"
        Exit Sub
    End If
    
    If strLastUnit = "PE1-2G" Then
        str1 = lbUnits.List(lbUnits.ListCount - 1)
        str2 = Right(str1, Len(str1) - 8)
        str1 = Left(str1, 8)
        str2 = str2 + 1
        lbUnits.RemoveItem (lbUnits.ListCount - 1)
        lbUnits.AddItem str1 & str2
    Else
        lbUnits.AddItem "+PE1-2G=1"
    End If
    strLastUnit = "PE1-2G"
End Sub

Private Sub Label11_Click()
    Dim count As Integer
    Dim strItem As String
    Dim vItem As Variant
    
    count = 0
    
    For i = (lbUnits.ListCount - 1) To 0 Step -1
        If Left(lbUnits.List(i, 0), 4) = "+PE1" Then
            count = count + CInt(lbUnits.List(i, 1))
        End If
    Next i
    
    If count = 0 Then Exit Sub
    
    For i = 0 To lbUnits.ListCount - 1
        If lbUnits.List(i, 0) = "+PM11" Then
            lbUnits.List(i, 1) = count
            Exit Sub
        End If
    Next i
    
    lbUnits.AddItem "+PM11"
    lbUnits.List(lbUnits.ListCount - 1, 1) = count
End Sub

Private Sub Label12_Click()
    'On Error Resume Next
    
    If lbUnits.ListCount < 1 Then
        lbUnits.AddItem "+PE1-3G"
        lbUnits.List(0, 1) = "1"
        Exit Sub
    End If
    
    For i = 0 To lbUnits.ListCount - 1
        If lbUnits.List(i, 0) = "+PE1-3G" Then
            lbUnits.List(i, 1) = CInt(lbUnits.List(i, 1)) + 1
            Exit Sub
        End If
    Next i
    
    lbUnits.AddItem "+PE1-3G"
    lbUnits.List(lbUnits.ListCount - 1, 1) = "1"
End Sub

Private Sub Label13_Click()
    'On Error Resume Next
    
    If lbUnits.ListCount < 1 Then
        lbUnits.AddItem "+PF1-7A"
        lbUnits.List(0, 1) = "1"
        Exit Sub
    End If
    
    For i = 0 To lbUnits.ListCount - 1
        If lbUnits.List(i, 0) = "+PF1-7A" Then
            lbUnits.List(i, 1) = CInt(lbUnits.List(i, 1)) + 1
            Exit Sub
        End If
    Next i
    
    lbUnits.AddItem "+PF1-7A"
    lbUnits.List(lbUnits.ListCount - 1, 1) = "1"
End Sub

Private Sub Label14_Click()
    Dim str1, str2 As String
    
    On Error Resume Next
    
    If lbUnits.ListCount < 1 Then
        lbUnits.AddItem "+PE1-4G=1"
        Exit Sub
    End If
    
    If strLastUnit = "PE1-4G" Then
        str1 = lbUnits.List(lbUnits.ListCount - 1)
        str2 = Right(str1, Len(str1) - 8)
        str1 = Left(str1, 8)
        str2 = str2 + 1
        lbUnits.RemoveItem (lbUnits.ListCount - 1)
        lbUnits.AddItem str1 & str2
    Else
        lbUnits.AddItem "+PE1-4G=1"
    End If
    strLastUnit = "PE1-4G"
End Sub

Private Sub Label19_Click()
    'On Error Resume Next
    
    If lbUnits.ListCount < 1 Then
        lbUnits.AddItem "+FP"
        lbUnits.List(0, 1) = "1"
        Exit Sub
    End If
    
    For i = 0 To lbUnits.ListCount - 1
        If lbUnits.List(i, 0) = "+FP" Then
            lbUnits.List(i, 1) = CInt(lbUnits.List(i, 1)) + 1
            Exit Sub
        End If
    Next i
    
    lbUnits.AddItem "+FP"
    lbUnits.List(lbUnits.ListCount - 1, 1) = "1"
    lbUnits.List(lbUnits.ListCount - 1, 2) = ""
End Sub

Private Sub Label20_Click()
    tbUnit.Value = "+RRCONDUIT="
    tbUnit.SetFocus
    strLastUnit = "RRUD"
End Sub

Private Sub Label21_Click()
    tbUnit.Value = "+PE2-3G="
    tbUnit.SetFocus
    'strLastUnit = "PE2-3G"
End Sub

Private Sub Label22_Click()
    tbUnit.Value = "+R3-5="
    tbUnit.SetFocus
    'strLastUnit = "R3-5"
End Sub

Private Sub Label23_Click()
    Dim entPole As AcadObject
    Dim obrGP As AcadBlockReference
    Dim attItem, basePnt As Variant
    Dim dScale As Double
    
    Me.Hide
    On Error Resume Next
    
    ThisDrawing.Utility.GetEntity entPole, basePnt, "Select Block: "
    If TypeOf entPole Is AcadBlockReference Then
        Set obrGP = entPole
    Else
        MsgBox "Not a valid block."
        Exit Sub
    End If
    
    dScale = obrGP.XScaleFactor
    cbScale.Value = (dScale * 100)
    
    Me.show
End Sub

Private Sub Label24_Click()
    'On Error Resume Next
    
    If lbUnits.ListCount < 1 Then
        lbUnits.AddItem "+BHF(30X48X36)"
        lbUnits.List(0, 1) = "1"
        Exit Sub
    End If
    
    For i = 0 To lbUnits.ListCount - 1
        If lbUnits.List(i, 0) = "+BHF(30X48X36)" Then Exit Sub
    Next i
    
    lbUnits.AddItem "+BHF(30X48X36)"
    lbUnits.List(lbUnits.ListCount - 1, 1) = "1"
End Sub

Private Sub Label25_Click()
    'On Error Resume Next
    
    If lbUnits.ListCount < 1 Then
        lbUnits.AddItem "+BDO3"
        lbUnits.List(0, 1) = "1"
        Exit Sub
    End If
    
    For i = 0 To lbUnits.ListCount - 1
        If lbUnits.List(i, 0) = "+BDO3" Then Exit Sub
    Next i
    
    lbUnits.AddItem "+BDO3"
    lbUnits.List(lbUnits.ListCount - 1, 1) = "1"
End Sub

Private Sub Label26_Click()
    'On Error Resume Next
    
    If lbUnits.ListCount < 1 Then
        lbUnits.AddItem "+BDO5"
        lbUnits.List(0, 1) = "1"
        Exit Sub
    End If
    
    For i = 0 To lbUnits.ListCount - 1
        If lbUnits.List(i, 0) = "+BDO5" Then Exit Sub
    Next i
    
    lbUnits.AddItem "+BDO5"
    lbUnits.List(lbUnits.ListCount - 1, 1) = "1"
End Sub

Private Sub Label27_Click()
    'On Error Resume Next
    
    If lbUnits.ListCount < 1 Then
        lbUnits.AddItem "+BDO(12126)"
        lbUnits.List(0, 1) = "1"
        Exit Sub
    End If
    
    For i = 0 To lbUnits.ListCount - 1
        If lbUnits.List(i, 0) = "+BDO(12126)" Then Exit Sub
    Next i
    
    lbUnits.AddItem "+BDO(12126)"
    lbUnits.List(lbUnits.ListCount - 1, 1) = "1"
End Sub

Private Sub Label35_Click()
    If lbUnits.ListCount < 1 Then
        lbUnits.AddItem "+XXPE"
        lbUnits.List(0, 1) = "1"
        Exit Sub
    End If
    
    For i = 0 To lbUnits.ListCount - 1
        If lbUnits.List(i, 0) = "+XXPE" Then Exit Sub
    Next i
    
    lbUnits.AddItem "+XXPE"
    lbUnits.List(lbUnits.ListCount - 1, 1) = "1"
End Sub

Private Sub Label36_Click()
    If lbUnits.ListCount < 1 Then
        lbUnits.AddItem "+XXPF"
        lbUnits.List(0, 1) = "1"
        Exit Sub
    End If
    
    For i = 0 To lbUnits.ListCount - 1
        If lbUnits.List(i, 0) = "+XXPF" Then Exit Sub
    Next i
    
    lbUnits.AddItem "+XXPF"
    lbUnits.List(lbUnits.ListCount - 1, 1) = "1"
End Sub

Private Sub Label37_Click()
    If lbUnits.ListCount < 1 Then
        lbUnits.AddItem "+XXPOLE"
        lbUnits.List(0, 1) = "1"
        Exit Sub
    End If
    
    For i = 0 To lbUnits.ListCount - 1
        If lbUnits.List(i, 0) = "+XXPOLE" Then Exit Sub
    Next i
    
    lbUnits.AddItem "+XXPOLE"
    lbUnits.List(lbUnits.ListCount - 1, 1) = "1"
End Sub

Private Sub Label38_Click()
    If lbUnits.ListCount < 1 Then
        lbUnits.AddItem "+XXPED"
        lbUnits.List(0, 1) = "1"
        Exit Sub
    End If
    
    For i = 0 To lbUnits.ListCount - 1
        If lbUnits.List(i, 0) = "+XXPED" Then Exit Sub
    Next i
    
    lbUnits.AddItem "+XXPED"
    lbUnits.List(lbUnits.ListCount - 1, 1) = "1"
End Sub

Private Sub Label39_Click()
    If lbUnits.ListCount < 1 Then
        lbUnits.AddItem "+XXHH"
        lbUnits.List(0, 1) = "1"
        Exit Sub
    End If
    
    For i = 0 To lbUnits.ListCount - 1
        If lbUnits.List(i, 0) = "+XXHH" Then Exit Sub
    Next i
    
    lbUnits.AddItem "+XXHH"
    lbUnits.List(lbUnits.ListCount - 1, 1) = "1"
End Sub

Private Sub Label5_Click() '<---------------------------- Get DWG Number
    Dim entPole As AcadObject
    Dim obrGP2 As AcadBlockReference
    Dim attItem, basePnt As Variant
    
    Me.Hide
  On Error Resume Next
    
    ThisDrawing.Utility.GetEntity entPole, basePnt, "Select Staking Sheet: "
    If TypeOf entPole Is AcadBlockReference Then
        Set obrGP2 = entPole
    Else
        MsgBox "Not a valid pole."
        Exit Sub
    End If
    
    attItem = obrGP2.GetAttributes
    tbDWG.Value = Right(attItem(0).TextString, 3)
    
    Me.show
End Sub

Private Sub Label6_Click()
    'On Error Resume Next
    
    If lbUnits.ListCount < 1 Then
        lbUnits.AddItem "+PM2A"
        lbUnits.List(0, 1) = "1"
        Exit Sub
    End If
    
    For i = 0 To lbUnits.ListCount - 1
        If lbUnits.List(i, 0) = "+PM2A" Then
            lbUnits.List(i, 1) = CInt(lbUnits.List(i, 1)) + 1
            Exit Sub
        End If
    Next i
    
    lbUnits.AddItem "+PM2A"
    lbUnits.List(lbUnits.ListCount - 1, 1) = "1"
End Sub

Private Sub Label7_Click()
    'On Error Resume Next
    
    If lbUnits.ListCount < 1 Then
        lbUnits.AddItem "+PM52"
        lbUnits.List(0, 1) = "1"
        Exit Sub
    End If
    
    For i = 0 To lbUnits.ListCount - 1
        If lbUnits.List(i, 0) = "+PM52" Then Exit Sub
    Next i
    
    lbUnits.AddItem "+PM52"
    lbUnits.List(lbUnits.ListCount - 1, 1) = "1"
End Sub

Private Sub Label9_Click()
    'On Error Resume Next
    
    If lbUnits.ListCount < 1 Then
        lbUnits.AddItem "+PF1-5A"
        lbUnits.List(0, 1) = "1"
        Exit Sub
    End If
    
    For i = 0 To lbUnits.ListCount - 1
        If lbUnits.List(i, 0) = "+PF1-5A" Then
            lbUnits.List(i, 1) = CInt(lbUnits.List(i, 1)) + 1
            Exit Sub
        End If
    Next i
    
    lbUnits.AddItem "+PF1-5A"
    lbUnits.List(lbUnits.ListCount - 1, 1) = "1"
End Sub

Private Sub LabelBM2_Click()
    'On Error Resume Next
    
    If lbUnits.ListCount < 1 Then
        lbUnits.AddItem "+BM2A"
        lbUnits.List(0, 1) = "1"
        Exit Sub
    End If
    
    For i = 0 To lbUnits.ListCount - 1
        If lbUnits.List(i, 0) = "+BM2A" Then Exit Sub
    Next i
    
    lbUnits.AddItem "+BM2A"
    lbUnits.List(lbUnits.ListCount - 1, 1) = "1"
End Sub

Private Sub LabelBM602D_Click()
    Dim str1, str2 As String
    
    On Error Resume Next
    
    If strLastUnit = "UD(2)" Then
        Select Case tbUnit.Value
            Case "+UD(1X1-2"")="
                tbUnit.Value = "+UD(1X2-2)="
            Case "+UD(1X2-2"")="
                tbUnit.Value = "+UD(1X3-2)="
            Case Else
                tbUnit.Value = "+UD(1X1-2)="
        End Select
    End If
        
    tbUnit.SetFocus
    strLastUnit = "UD(2)"
End Sub

Private Sub LabelBM604D_Click()
    Dim str1, str2 As String
    
    On Error Resume Next
    
    If strLastUnit = "UD(4)" Then
        Select Case tbUnit.Value
            Case "+UD(1X1-4"")="
                tbUnit.Value = "+UD(1X2-4)="
            Case "+UD(1X2-4"")="
                tbUnit.Value = "+UD(1X3-4)="
            Case Else
                tbUnit.Value = "+UD(1X1-4)="
        End Select
    End If
        
    tbUnit.SetFocus
    strLastUnit = "UD(4)"
End Sub

Private Sub LabelBM81_Click()
    'On Error Resume Next
    
    If lbUnits.ListCount < 1 Then
        lbUnits.AddItem "+BM81"
        lbUnits.List(0, 1) = "1"
        Exit Sub
    End If
    
    For i = 0 To lbUnits.ListCount - 1
        If lbUnits.List(i, 0) = "+BM81" Then
            lbUnits.List(i, 1) = CInt(lbUnits.List(i, 1)) + 1
            Exit Sub
        End If
    Next i
    
    lbUnits.AddItem "+BM81"
    lbUnits.List(lbUnits.ListCount - 1, 1) = "1"
End Sub

Private Sub LabelBM82_Click()
    'On Error Resume Next
    
    If lbUnits.ListCount < 1 Then
        lbUnits.AddItem "+BM82"
        lbUnits.List(0, 1) = "1"
        Exit Sub
    End If
    
    For i = 0 To lbUnits.ListCount - 1
        If lbUnits.List(i, 0) = "+BM82" Then
            lbUnits.List(i, 1) = CInt(lbUnits.List(i, 1)) + 1
            Exit Sub
        End If
    Next i
    
    lbUnits.AddItem "+BM82"
    lbUnits.List(lbUnits.ListCount - 1, 1) = "1"
End Sub

Private Sub LabelHH_Click()
    'On Error Resume Next
    
    If lbUnits.ListCount < 1 Then
        lbUnits.AddItem "+UHF(24X36X24)"
        lbUnits.List(0, 1) = "1"
        Exit Sub
    End If
    
    For i = 0 To lbUnits.ListCount - 1
        If lbUnits.List(i, 0) = "+UHF(24X36X24)" Then Exit Sub
    Next i
    
    lbUnits.AddItem "+UHF(24X36X24)"
    lbUnits.List(lbUnits.ListCount - 1, 1) = "1"
End Sub

Private Sub LabelPan_Click()
    Dim entPole As AcadObject
    Dim basePnt As Variant
    
    Me.Hide
  On Error Resume Next
    
    ThisDrawing.Utility.GetEntity entPole, basePnt, "Left Click to Exit: "
    
    Me.show
End Sub

Private Sub LabelUD1_Click()
    tbUnit.Value = "+UD(1X1-1.25)="
    tbUnit.SetFocus
    strLastUnit = "UD(1.25)"
End Sub

Private Sub lbCommon_KeyDown(ByVal KeyCode As MSForms.ReturnInteger, ByVal Shift As Integer)
    If lbCommon.ListCount < 1 Then Exit Sub
    
    Dim str1, str2, str3 As String
    Dim i, i2 As Integer
    
    Select Case KeyCode
        Case vbKeyDown
            If lbCommon.ListIndex = (lbCommon.ListCount - 1) Then Exit Sub
            i = lbCommon.ListIndex
            i2 = i + 1
            
            str1 = lbCommon.List(i, 0)
            str2 = lbCommon.List(i, 1)
            If lbCommon.List(i, 2) > 0 Then
                str3 = lbCommon.List(i, 2)
            Else
                str3 = ""
            End If
            
            
            lbCommon.List(i, 0) = lbCommon.List(i2, 0)
            lbCommon.List(i, 1) = lbCommon.List(i2, 1)
            If lbCommon.List(i2, 2) > 0 Then
                lbCommon.List(i, 2) = lbCommon.List(i2, 2)
            Else
                lbCommon.List(i, 2) = ""
            End If
            
            lbCommon.List(i2, 0) = str1
            lbCommon.List(i2, 1) = str2
            lbCommon.List(i2, 2) = str3
            'lbCommon.ListIndex = i2
        Case vbKeyUp
            If lbCommon.ListIndex = 0 Then Exit Sub
            i = lbCommon.ListIndex
            i2 = i - 1
            
            str1 = lbCommon.List(i, 0)
            str2 = lbCommon.List(i, 1)
            If lbCommon.List(i, 2) > 0 Then
                str3 = lbCommon.List(i, 2)
            Else
                str3 = ""
            End If
            
            lbCommon.List(i, 0) = lbCommon.List(i2, 0)
            lbCommon.List(i, 1) = lbCommon.List(i2, 1)
            If lbCommon.List(i2, 2) > 0 Then
                lbCommon.List(i, 2) = lbCommon.List(i2, 2)
            Else
                lbCommon.List(i, 2) = ""
            End If
            
            lbCommon.List(i2, 0) = str1
            lbCommon.List(i2, 1) = str2
            lbCommon.List(i2, 2) = str3
            'lbCommon.ListIndex = i2
        Case vbKeyDelete
            lbCommon.RemoveItem (lbCommon.ListIndex)
    End Select
End Sub

Private Sub lbMissing_DblClick(ByVal Cancel As MSForms.ReturnBoolean)
    If lbMissing.ListIndex < 0 Then Exit Sub
    
    Dim iIndex As Integer
    
    iIndex = lbMissing.ListIndex
    
    If lbMissing.List(iIndex, 1) = "" Then
        tbUnit.Value = lbMissing.List(iIndex, 0) & "="
        lbMissing.RemoveItem iIndex
        
        tbUnit.SetFocus
        Exit Sub
    End If
    
    If lbUnits.ListCount < 1 Then
        lbUnits.AddItem lbMissing.List(iIndex, 0)
        lbUnits.List(0, 1) = lbMissing.List(iIndex, 1)
        
        lbMissing.RemoveItem iIndex
        Exit Sub
    End If
    
    For i = 0 To lbUnits.ListCount - 1
        If InStr(lbUnits.List(i, 0), lbMissing.List(iIndex, 0)) > 0 Then
            lbUnits.List(i, 1) = CInt(lbMissing.List(iIndex, 1)) + CInt(lbUnits.List(i, 1))
            lbMissing.RemoveItem iIndex
            Exit Sub
        End If
    Next i
    
    lbUnits.AddItem lbMissing.List(iIndex, 0)
    lbUnits.List(lbUnits.ListCount - 1, 1) = lbMissing.List(iIndex, 1)
    lbMissing.RemoveItem iIndex
End Sub

Private Sub lbUnits_DblClick(ByVal Cancel As MSForms.ReturnBoolean)
    iListIndex = lbUnits.ListIndex
    lbUnits.Enabled = False
    cbPrefix.Enabled = False
    'cbAddUnit.Enabled = False
    'cbGetUnit.Enabled = False
    cbAddtoDWG.Enabled = False
    'cbUpdateUnit.Enabled = True
    cbAddUnit.Caption = "Update Unit"
    
    tbUnit.Value = lbUnits.List(iListIndex, 0) & "=" & lbUnits.List(iListIndex, 1)
    If Not lbUnits.List(iListIndex, 2) = "" Then tbUnit.Value = tbUnit.Value & "  " & lbUnits.List(iListIndex, 2)
    tbUnit.SetFocus
    
    Dim iStart, iLength As Integer
    Dim strTemp1 As String
    Dim vItems As Variant
    
    strTemp1 = tbUnit.Value
    iLength = Len(strTemp1)
    vItems = Split(strTemp1, "=")
    iStart = iLength - Len(vItems(1))
    
    If Right(vItems(1), 1) = "'" Then
        iLength = Len(vItems(1)) - 1
    Else
        iLength = Len(vItems(1))
    End If
    
    tbUnit.SelStart = iStart
    tbUnit.SelLength = iLength
    
End Sub

Private Sub lbUnits_KeyDown(ByVal KeyCode As MSForms.ReturnInteger, ByVal Shift As Integer)
    If lbUnits.ListCount < 1 Then Exit Sub
    
    Dim str1, str2, str3 As String
    Dim i, i2 As Integer
    
    Select Case KeyCode
        Case vbKeyDown
            If lbUnits.ListIndex = (lbUnits.ListCount - 1) Then Exit Sub
            i = lbUnits.ListIndex
            i2 = i + 1
            
            str1 = lbUnits.List(i, 0)
            str2 = lbUnits.List(i, 1)
            If lbUnits.List(i, 2) > 0 Then
                str3 = lbUnits.List(i, 2)
            Else
                str3 = ""
            End If
            
            
            lbUnits.List(i, 0) = lbUnits.List(i2, 0)
            lbUnits.List(i, 1) = lbUnits.List(i2, 1)
            If lbUnits.List(i2, 2) > 0 Then
                lbUnits.List(i, 2) = lbUnits.List(i2, 2)
            Else
                lbUnits.List(i, 2) = ""
            End If
            
            lbUnits.List(i2, 0) = str1
            lbUnits.List(i2, 1) = str2
            lbUnits.List(i2, 2) = str3
            'lbUnits.ListIndex = i2
        Case vbKeyUp
            If lbUnits.ListIndex = 0 Then Exit Sub
            i = lbUnits.ListIndex
            i2 = i - 1
            
            str1 = lbUnits.List(i, 0)
            str2 = lbUnits.List(i, 1)
            If lbUnits.List(i, 2) > 0 Then
                str3 = lbUnits.List(i, 2)
            Else
                str3 = ""
            End If
            
            lbUnits.List(i, 0) = lbUnits.List(i2, 0)
            lbUnits.List(i, 1) = lbUnits.List(i2, 1)
            If lbUnits.List(i2, 2) > 0 Then
                lbUnits.List(i, 2) = lbUnits.List(i2, 2)
            Else
                lbUnits.List(i, 2) = ""
            End If
            
            lbUnits.List(i2, 0) = str1
            lbUnits.List(i2, 1) = str2
            lbUnits.List(i2, 2) = str3
            'lbUnits.ListIndex = i2
        Case vbKeyDelete
            lbUnits.RemoveItem (lbUnits.ListIndex)
    End Select
End Sub

Private Sub UserForm_Initialize()
    cbPrefix.AddItem "A"
    cbPrefix.AddItem "BA"
    cbPrefix.AddItem "BDO"
    cbPrefix.AddItem "BFO"
    cbPrefix.AddItem "BHF"
    cbPrefix.AddItem "BM"
    cbPrefix.AddItem "CO"
    cbPrefix.AddItem "FDH"
    cbPrefix.AddItem "HACO"
    cbPrefix.AddItem "HBFO"
    cbPrefix.AddItem "PE"
    cbPrefix.AddItem "PF"
    cbPrefix.AddItem "PM"
    cbPrefix.AddItem "R"
    cbPrefix.AddItem "SE"
    cbPrefix.AddItem "UD"
    cbPrefix.AddItem "UHF"
    cbPrefix.AddItem "UO"
    cbPrefix.AddItem "W"
    cbPrefix.AddItem "XX"
    cbPrefix.AddItem "FP"

    cbUP.Caption = Chr(225)
    cbDOWN.Caption = Chr(226)
    
    strLastUnit = ""
    
    lbUnits.ColumnCount = 3
    lbUnits.ColumnWidths = "96;36;48"
    
    lbCommon.ColumnCount = 3
    lbCommon.ColumnWidths = "96;36;60"
    
    lbInfo.ColumnCount = 2
    lbInfo.ColumnWidths = "60;80"
    
    lbAttach.ColumnCount = 2
    lbAttach.ColumnWidths = "60;80"
    
    lbMissing.ColumnCount = 2
    lbMissing.ColumnWidths = "84;56"
End Sub

Private Sub ValidateUnits()
    Dim iNeeded, iThere As Integer
    
    iNeeded = 0
    iThere = 0
    
    On Error Resume Next
    
    For i = 0 To (lbUnits.ListCount - 1)
        If Right(lbUnits.List(i), 2) = "P)" And Left(lbUnits.List(i), 2) = "+C" Then iNeeded = 1
        If Left(lbUnits.List(i), 5) = "+PM52" Then iThere = 1
    Next i
    
    If iThere > 0 Then Exit Sub
    If Not (iNeeded - iThere) = 0 Then lbUnits.AddItem "+PM52=1"
    'MsgBox "Needed: " & iNeeded & vbCr & "There: " & iThere
End Sub

Private Sub RemoveIfromBFO()
    Dim strItem, strDuct, strTemp As String
    Dim vItem, vTemp As Variant
    Dim iExisting, iNew, iDuct As Integer
    
    For i = 0 To lbUnits.ListCount - 1
        If InStr(lbUnits.List(i, 0), ")I") > 0 Then Exit Sub
    Next i
    
    For i = 0 To lbUnits.ListCount - 1
        strItem = lbUnits.List(i, 0)
        
        If InStr(strItem, "+BFO") > 0 Then
            If lbUnits.List(i, 2) = "LOOP" Then GoTo Next_Item
            
            iExisting = CInt(lbUnits.List(i, 1))
            strDuct = Replace(lbUnits.List(i, 0), ")", ")I")
            
            vTemp = Split(tbUnit.Value, "=")
            strTemp = Replace(vTemp(1), "'", "")
            iDuct = CInt(strTemp)
            iNew = iExisting - iDuct
            
            lbUnits.List(i, 1) = iNew
            i = i + 1
            lbUnits.AddItem strDuct, i
            lbUnits.List(i, 1) = iDuct
            Exit Sub
        End If
        
Next_Item:
    Next i
End Sub

Attribute VB_Name = "UnnamedForm"
Attribute VB_Base = "0{BA629936-DF40-4FA8-AA97-CB5CD9BAE242}{DA2F706A-AF9E-4BF5-8937-9B0FEC6C33AC}"
Attribute VB_GlobalNameSpace = False
Attribute VB_Creatable = False
Attribute VB_PredeclaredId = True
Attribute VB_Exposed = False
Attribute VB_TemplateDerived = False
Attribute VB_Customizable = False
Private Sub cbGetPoint_Click()
    Dim vCoords As Variant
    
    On Error Resume Next
    Me.Hide
    
    vCoords = ThisDrawing.Utility.GetPoint(, vbCr & "Pick Point:")
    If Not Err = 0 Then GoTo Exit_Sub
    
    tbTN83F.Value = vCoords(1) & "," & vCoords(0)
    
    Call GetLL
Exit_Sub:
    Me.show
End Sub

Private Sub cbGoogleMaps_Click()
    If tbLL.Value = "" Then Exit Sub
    If tbLL.Value = "error" Then Exit Sub
    If InStr(tbLL.Value, ",") < 1 Then Exit Sub
    
    Dim strURL As String
    
    strURL = "http://www.google.com/maps/place/" & tbLL.Value
    Shell ("C:\Program Files (x86)\Google\Chrome\Application\chrome.exe -url " & strURL)
End Sub

Private Sub cbPlaceNote_Click()
    Dim objMText As AcadMText
    Dim vBasePnt, vLL As Variant
    Dim strLine As String
    Dim dInsert(2) As Double
    Dim dScale As Double
    
    On Error Resume Next
    Me.Hide
    
    vBasePnt = ThisDrawing.Utility.GetPoint(, "Select Note Placement: ")
    If Not Err = 0 Then GoTo Exit_Sub
    
    dInsert(0) = vBasePnt(0)
    dInsert(1) = vBasePnt(1)
    dInsert(2) = 0#
    
    dScale = CDbl(tbTextHeight.Value)
    
    strLine = Replace(tbNote.Value, vbLf, "")
    strLine = Replace(strLine, vbCr, "\P")
    
    If InStr(strLine, "{Lat}") > 0 Then
        vLL = Split(tbLL.Value, ",")
        
        strLine = Replace(strLine, "{Lat}", vLL(0))
        strLine = Replace(strLine, "{Long}", vLL(1))
    End If
    
    If InStr(strLine, "{N}") > 0 Then
        vLL = Split(tbTN83F.Value, ",")
        
        strLine = Replace(strLine, "{N}", vLL(0))
        strLine = Replace(strLine, "{E}", vLL(1))
    End If
    
    If InStr(strLine, "{D}") > 0 Then
        strLine = Replace(strLine, "{D}", Date)
    End If

    Set objMText = ThisDrawing.ModelSpace.AddMText(dInsert, 0, strLine)
    objMText.Layer = cbNoteLayer.Value
    objMText.Height = dScale
    objMText.InsertionPoint = dInsert
    Select Case cbJust.Value
        Case "TL"
            objMText.AttachmentPoint = acAttachmentPointTopLeft
        Case "TC"
            objMText.AttachmentPoint = acAttachmentPointTopCenter
        Case "TR"
            objMText.AttachmentPoint = acAttachmentPointTopRight
        Case "ML"
            objMText.AttachmentPoint = acAttachmentPointMiddleLeft
        Case "MC"
            objMText.AttachmentPoint = acAttachmentPointMiddleCenter
        Case "MR"
            objMText.AttachmentPoint = acAttachmentPointMiddleRight
        Case "BL"
            objMText.AttachmentPoint = acAttachmentPointBottomLeft
        Case "BC"
            objMText.AttachmentPoint = acAttachmentPointBottomCenter
        Case "BR"
            objMText.AttachmentPoint = acAttachmentPointBottomRight
    End Select
    If cbMask.Value = True Then objMText.BackgroundFill = True
    
    objMText.Update
    
Exit_Sub:
    Me.show
End Sub

Private Sub cbQuit_Click()
    Me.Hide
End Sub

Private Sub cbZoomCoordinates_Click()
    If tbTN83F.Value = "" Then Exit Sub
    If InStr(tbTN83F.Value, ",") < 1 Then Exit Sub
    
    Dim vCoords As Variant
    'Dim dLL(2), dUR(2) As Double
    Dim viewCoordsB(0 To 2) As Double
    Dim viewCoordsE(0 To 2) As Double
    Dim strLine As String
    
    vCoords = Split(tbTN83F.Value, ",")
    
    Me.Hide
    
    viewCoordsB(0) = CDbl(vCoords(1)) - 300
    viewCoordsB(1) = CDbl(vCoords(0)) - 300
    viewCoordsB(2) = 0#
    viewCoordsE(0) = viewCoordsB(0) + 600
    viewCoordsE(1) = viewCoordsB(1) + 600
    viewCoordsE(2) = 0#
    
    ThisDrawing.Application.ZoomWindow viewCoordsB, viewCoordsE
    
    Me.show
End Sub

Private Sub tbTN83F_Exit(ByVal Cancel As MSForms.ReturnBoolean)
    If InStr(tbTN83F.Value, ",") < 1 Then Exit Sub
    
    Dim vCoords As Variant
    Dim dN, dE As Double
    
    On Error Resume Next
    
    vCoords = Split(tbTN83F.Value, ",")
    dN = CDbl(vCoords(0))
    dE = CDbl(vCoords(1))
    
    If Not Err = 0 Then
        tbLL.Value = "error"
        Exit Sub
    End If
    
    Call GetLL
End Sub

Private Sub UserForm_Initialize()
    cbJust.AddItem "TL"
    cbJust.AddItem "TC"
    cbJust.AddItem "TR"
    cbJust.AddItem "ML"
    cbJust.AddItem "MC"
    cbJust.AddItem "MR"
    cbJust.AddItem "BL"
    cbJust.AddItem "BC"
    cbJust.AddItem "BR"
    cbJust.Value = "TL"
    
    Dim objLayers As AcadLayers
    Dim objLayer As AcadLayer
    
    Set objLayers = ThisDrawing.Layers
    For Each objLayer In objLayers
        cbNoteLayer.AddItem objLayer.Name
    Next objLayer
    cbNoteLayer.Value = "Integrity Planning"
    
    Dim strNote As String
    
    strNote = "{Lat}itude  {Long}itude  {N}orth  {E}ast  {D}ate"
    tbNote.ControlTipText = strNote
    
    tbTN83F.SetFocus
End Sub

Private Sub GetLL()
    Dim vCoords As Variant
    Dim vLL As Variant
    Dim dN, dE As Double
    
    vCoords = Split(tbTN83F.Value, ",")
    dN = CDbl(vCoords(0))
    dE = CDbl(vCoords(1))
    
    vLL = TN83FtoLL(CDbl(dN), CDbl(dE))
    tbLL.Value = vLL(0) & "," & vLL(1)
End Sub

Private Function TN83FtoLL(dNorth As Double, dEast As Double)
    Dim dLat, dLong, dDLat As Double
    Dim dDiffE, dEast0 As Double
    Dim dDiffN, dNorth0 As Double
    Dim dR, dCAR, dCA, dU, dK As Double
    Dim LL(2) As Double
    
    dEast = dEast * 0.3048006096
    dNorth = dNorth * 0.3048006096
    
    dDiffE = dEast - 600000
    dDiffN = dNorth - 166504.1691
    
    dR = 8842127.1422 - dDiffN
    dCAR = Atn(dDiffE / dR)
    dCA = dCAR * 180 / 3.14159265359
    dLong = -86 + dCA / 0.585439726459
    
    dU = dDiffN - dDiffE * Tan(dCAR / 2)
    dDLat = dU * (0.00000901305249 + dU * (-6.77268E-15 + dU * (-3.72351E-20 + dU * -9.2828E-28)))
    dLat = 35.8340607459 + dDLat
    
    dK = 0.999948401424 + (1.23188E-14 * dU * dU) + (4.54E-22 * dU * dU * dU)
    
    LL(0) = dLat
    LL(1) = dLong
    LL(2) = dK
    
    TN83FtoLL = LL
End Function

Private Function LLtoTN83F(dLat As Double, dLong As Double)
    Dim dDLat As Double
    Dim dEast, dDiffE, dEast0 As Double
    Dim dNorth, dDiffN, dNorth0 As Double
    Dim dU, dR, dCA, dK As Double
    Dim NE(2) As Double
    
    dDLat = dLat - 35.8340607459
    dU = dDLat * (110950.2019 + dDLat * (9.25072 + dDLat * (5.64572 + dDLat * 0.017374)))
    dR = 8842127.1422 - dU
    dCA = ((86 + dLong) * 0.585439726459) * 3.14159265359 / 180
    
    dDiffE = dR * Sin(dCA)
    dDiffN = dU + dDiffE * Tan(dCA / 2)
    
    dEast = (dDiffE + 600000) / 0.3048006096
    dNorth = (dDiffN + 166504.1691) / 0.3048006096
    
    dK = 0.999948401424 + (1.23188E-14 * dU * dU) + (4.54E-22 * dU * dU * dU)
    
    NE(0) = dNorth
    NE(1) = dEast
    NE(2) = dK
    
    LLtoTN83F = NE
End Function

Attribute VB_Name = "UserForm2"
Attribute VB_Base = "0{DC15A17E-FF46-48A6-8B26-1AB95DEDC521}{171B575F-FD0A-4ADC-B84E-DDE169BA62A9}"
Attribute VB_GlobalNameSpace = False
Attribute VB_Creatable = False
Attribute VB_PredeclaredId = True
Attribute VB_Exposed = False
Attribute VB_TemplateDerived = False
Attribute VB_Customizable = False
Dim objStructure As AcadBlockReference

Private Sub cbGetStructure_Click()
    Dim objEntity As AcadEntity
    Dim vAttList, vReturnPnt As Variant
    Dim vLine, vItem, vCounts As Variant
    Dim vCable, vSplice As Variant
    Dim strText, strBack As String
    Dim strCables, strSplices, strTemp As String
    Dim result, iAtt As Integer
    Dim bTest As Boolean
    
    'bTest = False
    
    'If Not tbCableCounts.Value = strMainCC Then bTest = True
    'If Not tbClosure.Value = strMainSC Then bTest = True
    'If strMainCC = "empty" Then
        'If strMainSC = "empty" Then bTest = False
    'End If
    'If bTest = True Then
        'result = MsgBox("Save count changes to Block?", vbYesNo, "Save Changes")
        'If result = vbYes Then Call UpdateBlock(CStr(tbPosition.Value))
    'End If
    
    Me.Hide
    
    On Error Resume Next
    
    Err = 0
    ThisDrawing.Utility.GetEntity objEntity, vReturnPnt, vbCr & "Select Structure:"
    If Not Err = 0 Then
        MsgBox Err.Description
        GoTo Exit_Sub
    End If
    
    If Not TypeOf objEntity Is AcadBlockReference Then
        MsgBox objEntity.ObjectName
        GoTo Exit_Sub
    End If
    
    lbCounts.Clear
    tbClosure.Value = ""
    tbCableCounts.Value = ""
    tbFutureCableCounts.Value = ""
    tbType.Value = ""
    tbNumber.Value = ""
    tbPosition.Value = ""
    
    Set objStructure = objEntity
    
    Select Case objStructure.Name
        Case "sPole"
            iAtt = 25
            tbType.Value = "POLE"
        Case "sPed"
            iAtt = 5
            tbType.Value = "PED"
        Case "sHH"
            iAtt = 5
            tbType.Value = "HH"
        Case "sMH"
            iAtt = 5
            tbType.Value = "MH"
        Case "sPanel"
            iAtt = 5
            tbType.Value = "PANEL"
        Case Else
            GoTo Exit_Sub
    End Select
    
    'cbScale.Value = GetScale(objStructure.InsertionPoint) * 100
    
    vAttList = objStructure.GetAttributes
    
    'MsgBox vAttList(iAtt).TextString
    strCables = Replace(vAttList(iAtt).TextString, vbLf, "")
    strCables = Replace(strCables, "\P", vbCr)
    vCable = Split(strCables, vbCr)
    
    cbPosition.Clear
    For i = 0 To UBound(vCable)
        vCounts = Split(vCable(i), ": ")
        cbPosition.AddItem vCounts(0)
    Next i
    cbPosition.Value = cbPosition.List(0)
    
    Call GetPositionData(cbPosition.Value)
    
    If tbNumber.Value = "" Then tbNumber.Value = vAttList(0).TextString
    
    
    strText = Replace(tbCableCounts.Value, vbLf, "")
    strText = Replace(strText, vbTab, " ")
    vCable = Split(strText, vbCr)
    
    For i = 0 To UBound(vCable)
        vLine = Split(vCable(i), ": ")
        vCable(i) = vLine(0) & ": " & vLine(1) & ": " & tbNumber.Value
    Next i
    
    strText = vCable(0)
    If UBound(vCable) > 0 Then
        For i = 1 To UBound(vCable)
            strText = strText & vbCr & vCable(i)
        Next i
    End If
    
    strText = Replace(strText, " ", vbTab)
    tbFutureCableCounts.Value = strText
    
    Call CreateList
    
    
    strText = Replace(tbClosure.Value, vbLf, "")
    strText = Replace(strText, vbTab, " ")
    vSplice = Split(strText, vbCr)
    
    For i = 0 To UBound(vSplice)
        vLine = Split(vSplice(i), ": ")
        strText = vLine(0)
    Next i
    
    tbF2.Value = strText
    
    vLine = Split(ThisDrawing.Name, " ")
    tbFileName.Value = vLine(0) & " Counts -" & strText & ".mcl"
    
    Call OpenMCL
    
Exit_Sub:
    
    Me.show
End Sub

Private Sub GetPositionData(strPosition As String)
    Dim vAttList As Variant
    Dim vLine, vItem, vCounts As Variant
    Dim vCable, vSplice As Variant
    Dim strText, strBack As String
    Dim strCables, strSplices, strTemp As String
    Dim iAtt As Integer
    
    On Error Resume Next
    
    tbCableCounts.Value = ""
    tbClosure.Value = ""
    'tbWL.Value = ""
    
    Select Case objStructure.Name
        Case "sPole"
            iAtt = 25
            tbType.Value = "POLE"
        Case "sPed"
            iAtt = 5
            tbType.Value = "PED"
        Case "sHH"
            iAtt = 5
            tbType.Value = "HH"
        Case "sPanel"
            iAtt = 5
            tbType.Value = "PANEL"
        Case "sMH"
            iAtt = 5
            tbType.Value = "MH"
        Case Else
            MsgBox objStructure.Name & vbCr & "Why?"
            GoTo Exit_Sub
    End Select
    
    vAttList = objStructure.GetAttributes
    
    strCables = Replace(vAttList(iAtt).TextString, vbLf, "")
    strCables = Replace(strCables, "\P", vbCr)
    vCable = Split(strCables, vbCr)
    
    For i = 0 To UBound(vCable)
        vItem = Split(vCable(i), ": ")
        If vItem(0) = strPosition Then GoTo Found_Cable
    Next i
    
    'MsgBox "No Cable found at that Position."
    GoTo Find_Splice
    
Found_Cable:
    vLine = Split(vCable(i), " / ")
    vItem = Split(vLine(0), ": ")
    tbNumber.Value = vAttList(0).TextString
    tbPosition.Value = vItem(0)
    tbCableType.Value = vItem(1)
            
    strText = Replace(vLine(1), " + ", vbCr)
    strText = Replace(strText, " ", vbTab)
    tbCableCounts.Value = strText
    
Find_Splice:
            
    strSplices = Replace(vAttList(iAtt + 1).TextString, vbLf, "")
    
    If Left(strSplices, 1) = vbCrLf Then strSplices = Right(strSplices, Len(strSplices) - 1)
    If Left(strSplices, 1) = vbCr Then strSplices = Right(strSplices, Len(strSplices) - 1)
    If Left(strSplices, 1) = vbLf Then strSplices = Right(strSplices, Len(strSplices) - 1)
    
    If Right(strSplices, 1) = vbCrLf Then strSplices = Left(strSplices, Len(strSplices) - 1)
    If Right(strSplices, 1) = vbCr Then strSplices = Left(strSplices, Len(strSplices) - 1)
    If Right(strSplices, 1) = vbLf Then strSplices = Left(strSplices, Len(strSplices) - 1)
    
    strSplices = Replace(strSplices, "\P", vbCr)
    
    vAttList(iAtt + 1).TextString = strSplices
    objStructure.Update
    
    vSplice = Split(strSplices, vbCr)
    
    For i = 0 To UBound(vSplice)
        If vSplice(i) = "" Then GoTo Next_I
        
        vItem = Split(vSplice(i), "] ")
        strTemp = Replace(vItem(0), "[", "")
        If tbPosition.Value = "" Then tbPosition.Value = strTemp
        If strTemp = strPosition Then GoTo Found_Splice
Next_I:
    Next i
    
    'MsgBox "No Splice found at that Position."
    GoTo Get_Wiring_Limits
    
Found_Splice:
    
    If Not vSplice(0) = "" Then
        For i = 0 To UBound(vSplice)
            vCounts = Split(vSplice(i), "] ")
            strTemp = Replace(vCounts(0), "[", "")
            If strTemp = strPosition Then
                strText = Replace(vCounts(1), " + ", vbCr)
                strText = Replace(strText, " ", vbTab)
                tbClosure.Value = strText
                
                GoTo Get_Wiring_Limits
            End If
        Next i
    End If
    
Get_Wiring_Limits:
    GoTo Clear_objSS

    tbWL.Value = ""
    
    Dim filterType, filterValue As Variant
    Dim grpCode(0) As Integer
    Dim grpValue(0) As Variant
    Dim objSS As AcadSelectionSet
    Dim objBlock As AcadBlockReference
    
    grpCode(0) = 2
    grpValue(0) = "Customer,SG"
    filterType = grpCode
    filterValue = grpValue
    
    Err = 0
    Set objSS = ThisDrawing.SelectionSets.Add("objSS")
    If Not Err = 0 Then
        Set objSS = ThisDrawing.SelectionSets.Item("objSS")
        objSS.Clear
    End If
    
    objSS.Select acSelectionSetAll, , , filterType, filterValue
    
    For Each objBlock In objSS
        vAttList = objBlock.GetAttributes
        
        Select Case objBlock.Name
            Case "SG"
                If vAttList(2).TextString = "" Then GoTo Next_objBlock
                vLine = Split(vAttList(2).TextString, " - ")
                strText = vLine(1) & vbTab & "SG - " & vAttList(1).TextString
            Case Else
                If vAttList(4).TextString = "" Then GoTo Next_objBlock
                vLine = Split(vAttList(4).TextString, " - ")
                strText = vLine(1) & vbTab & vAttList(1).TextString & " " & vAttList(2).TextString
        End Select
        
        If vLine(0) = tbNumber.Value Then
            'vItem = Split(vLine(1), ": ")
            'strText = Replace(vItem(1), ")", "")
            
            If tbWL.Value = "" Then
                'tbWL.Value = strText & vbTab & vAttList(1).TextString & " " & vAttList(2).TextString
                tbWL.Value = strText
            Else
                'tbWL.Value = tbWL.Value & vbCr & strText & vbTab & vAttList(1).TextString & " " & vAttList(2).TextString
                tbWL.Value = tbWL.Value & vbCr & strText
            End If
            
        End If
Next_objBlock:
    Next objBlock
    
    'Call SortWL
    
Clear_objSS:
    objSS.Clear
    objSS.Delete
        
Exit_Sub:
    cbUpdate.Enabled = True
    
    strMainCC = tbCableCounts.Value
    strMainSC = tbClosure.Value
End Sub

Private Sub UserForm_Initialize()
    lbCounts.Clear
    lbCounts.ColumnCount = 9
    lbCounts.ColumnWidths = "24;72;26;72;72;36;140;48;102"
End Sub

Private Sub CreateList()
    If tbCableCounts.Value = "" Then Exit Sub
    
    Dim vLine, vItem, vCounts As Variant
    Dim strText As String
    Dim iStart, iEnd As Integer
    Dim iFiber As Integer
    
    lbCounts.AddItem ""
    iFiber = 1
    
    strText = Replace(tbCableCounts.Value, vbLf, "")
    strText = Replace(strText, vbTab, " ")
    vLine = Split(strText, vbCr)
    
    For i = 0 To UBound(vLine)
        vItem = Split(vLine(i), ": ")
        vCounts = Split(vItem(1), "-")
        
        iStart = CInt(vCounts(0))
        
        If UBound(vCounts) = 0 Then
            iEnd = iStart
        Else
            iEnd = CInt(vCounts(1))
        End If
        
        For j = iStart To iEnd
            lbCounts.AddItem iFiber
            lbCounts.List(iFiber, 1) = vItem(0)
            lbCounts.List(iFiber, 2) = j
            lbCounts.List(iFiber, 3) = vItem(2)
            lbCounts.List(iFiber, 4) = "<>"
            lbCounts.List(iFiber, 5) = "<>"
            lbCounts.List(iFiber, 6) = "<>"
            lbCounts.List(iFiber, 7) = "<>"
            lbCounts.List(iFiber, 8) = "<>"
            
            iFiber = iFiber + 1
        Next j
    Next i
End Sub

Private Sub OpenMCL()
    Dim vLine, vItem As Variant
    Dim strFile, strAllText As String
    Dim fName As String
    Dim iIndex As Integer
    
    strFile = ThisDrawing.Path & "\" & tbFileName.Value
    
    fName = Dir(strFile)
    If fName = "" Then
        tbFileStatus.Value = "missing"
        Exit Sub
    Else
        tbFileStatus.Value = "found"
    End If
    
    Open strFile For Input As #2
    
    strAllText = Input(LOF(2), 2)
    strAllText = Replace(strAllText, vbLf, "")
    vLine = Split(strAllText, vbCr)
    
    Close #2
    
    For i = 1 To lbCounts.ListCount - 1
        If lbCounts.List(i, 1) = tbF2.Value Then
            iIndex = CInt(lbCounts.List(i, 2))
            
            If iIndex > UBound(vLine) + 1 Then GoTo Next_line
            
            vItem = Split(vLine(iIndex), vbTab)
            
            lbCounts.List(i, 4) = vItem(1)
            lbCounts.List(i, 5) = vItem(2)
            lbCounts.List(i, 6) = vItem(3)
            lbCounts.List(i, 7) = vItem(4)
            lbCounts.List(i, 8) = vItem(5)
        End If
        
        If lbCounts.List(i, 4) = tbNumber.Value Then lbCounts.List(i, 4) = "current pole"
Next_line:
    Next i
    
    
    'MsgBox UBound(vLine) & vbCr & vLine(0) & vbCr & vLine(1) & vbCr & vLine(UBound(vLine) - 1)
    
    'While Not EOF(2)
        'Input #2, strLine
        
    'Wend
    
        
End Sub

Attribute VB_Name = "UserForm4"
Attribute VB_Base = "0{E05A68F3-2E62-489D-837A-BB2FD7477A57}{2CA80234-1D2A-42BC-81F6-F5D57E87C693}"
Attribute VB_GlobalNameSpace = False
Attribute VB_Creatable = False
Attribute VB_PredeclaredId = True
Attribute VB_Exposed = False
Attribute VB_TemplateDerived = False
Attribute VB_Customizable = False
Dim iListIndex As Integer

Private Sub cbAddToList_Click()
    If tbEndFibers.Value = "" Then Exit Sub
    If tbSource.Value = "" Then Exit Sub
    
    lbList.AddItem tbEndFibers.Value
    lbList.List(lbList.ListCount - 1, 1) = tbSource.Value
End Sub

Private Sub cbGet_Click()
    Dim objEntity As AcadEntity
    Dim vReturnPnt As Variant
    Dim vAttList As Variant
    Dim strLine As String
    Dim iStart, iEnd, iSize As Integer
    
    Me.Hide
    
    On Error Resume Next
    ThisDrawing.Utility.GetEntity objEntity, vReturnPnt, vbCr & "Select Block:"
    If Not Err = 0 Then GoTo Exit_Sub
    
    If Not TypeOf objEntity Is AcadBlockReference Then GoTo Exit_Sub
    Set objBlock = objEntity
    vAttList = objBlock.GetAttributes
    
    Dim vLine, vItem, vCounts, vTemp As Variant
    
    Select Case objBlock.Name
        Case "sPole"
            strLine = vAttList(25).TextString
        Case "sPed", "sHH", "sFP", "sMH", "sPanel"
            strLine = vAttList(5).TextString
        Case "Callout"
            vLine = Split(vAttList(1).TextString, ")")
            vItem = Split(vLine(0), "(")
            iSize = CInt(vItem(1))
            'If Not vItem(1) = cbCableSize.Value Then
                'If cbCableSize.Value = "" Then
                    'cbCableSize.Value = vItem(1)
                'Else
                    'GoTo Exit_Sub
                'End If
            'End If
            
            strLine = Replace(vAttList(2).TextString, "\P", " + ")
            'MsgBox strLine
            GoTo Fixed_Line
        Case Else
            GoTo Exit_Sub
    End Select
    
    vLine = Split(strLine, " / ")
    vItem = Split(vLine(0), ")")
    vTemp = Split(vItem(0), "(")
    iSize = CInt(vTemp(1))
    'If Not vTemp(1) = cbCableSize.Value Then
        'If cbCableSize.Value = "" Then
            'cbCableSize.Value = vTemp(1)
        'Else
            'GoTo Exit_Sub
        'End If
    'End If
    
    strLine = vLine(1)
    
Fixed_Line:
    
    'If cbCableSize.Value = "" Then GoTo Exit_Sub
    If strLine = "" Then GoTo Exit_Sub
    
    Dim strName, strSource As String
    Dim iFiber As Integer
    
    iFiber = 1
    lbCounts.Clear
    lbCounts.AddItem ""
    
    vLine = Split(strLine, " + ")
    For i = 0 To UBound(vLine)
        vItem = Split(vLine(i), ": ")
        strName = vItem(0)
        If UBound(vItem) < 2 Then
            strSource = ""
        Else
            strSource = vItem(2)
        End If
        
        vCounts = Split(vItem(1), "-")
        iStart = CInt(vCounts(0))
        If UBound(vCounts) < 1 Then
            iEnd = iStart
        Else
            iEnd = CInt(vCounts(1))
        End If
        
        'strLine = iFiber & "-"
        'iFiber = iFiber + iEnd - iStart
        'strLine = strLine & iFiber
        
        'lbCounts.AddItem strLine
        'lbCounts.List(lbCounts.ListCount - 1, 1) = strName
        'lbCounts.List(lbCounts.ListCount - 1, 2) = vItem(1)
        'lbCounts.List(lbCounts.ListCount - 1, 3) = strSource
        
        'iFiber = iFiber + 1
        
        For j = iStart To iEnd
            lbCounts.AddItem iFiber
            lbCounts.List(lbCounts.ListCount - 1, 1) = strName
            lbCounts.List(lbCounts.ListCount - 1, 2) = j
            lbCounts.List(lbCounts.ListCount - 1, 3) = strSource
            
            iFiber = iFiber + 1
        Next j
    Next i
    
Exit_Sub:
    Me.show
End Sub

Private Sub cbGetBlock_Click()
    Dim objEntity As AcadEntity
    Dim vReturnPnt As Variant
    Dim vAttList As Variant
    Dim strLine As String
    Dim iStart, iEnd, iSize As Integer
    
    Me.Hide
    
    On Error Resume Next
    ThisDrawing.Utility.GetEntity objEntity, vReturnPnt, vbCr & "Select Block:"
    If Not Err = 0 Then GoTo Exit_Sub
    
    If Not TypeOf objEntity Is AcadBlockReference Then GoTo Exit_Sub
    Set objBlock = objEntity
    vAttList = objBlock.GetAttributes
    
    Dim vLine, vItem, vCounts, vTemp As Variant
    
    Select Case objBlock.Name
        Case "sPole"
            strLine = vAttList(25).TextString
        Case "sPed", "sHH", "sFP", "sMH", "sPanel"
            strLine = vAttList(5).TextString
        Case "Callout"
            vLine = Split(vAttList(1).TextString, ")")
            vItem = Split(vLine(0), "(")
            iSize = CInt(vItem(1))
            'If Not vItem(1) = cbCableSize.Value Then
                'If cbCableSize.Value = "" Then
                    'cbCableSize.Value = vItem(1)
                'Else
                    'GoTo Exit_Sub
                'End If
            'End If
            
            strLine = Replace(vAttList(2).TextString, "\P", " + ")
            'MsgBox strLine
            GoTo Fixed_Line
        Case Else
            GoTo Exit_Sub
    End Select
    
    vLine = Split(strLine, " / ")
    vItem = Split(vLine(0), ")")
    vTemp = Split(vItem(0), "(")
    iSize = CInt(vTemp(1))
    'If Not vTemp(1) = cbCableSize.Value Then
        'If cbCableSize.Value = "" Then
            'cbCableSize.Value = vTemp(1)
        'Else
            'GoTo Exit_Sub
        'End If
    'End If
    
    strLine = vLine(1)
    
Fixed_Line:
    
    'If cbCableSize.Value = "" Then GoTo Exit_Sub
    If strLine = "" Then GoTo Exit_Sub
    
    strLine = Replace(strLine, " + ", vbCr)
    
    tbBefore.Value = strLine
    lbBefore.Clear
    
    vLine = Split(strLine, vbCr)
    For i = 0 To UBound(vLine)
        vItem = Split(vLine(i), ": ")
        
        lbBefore.AddItem vItem(0)
        lbBefore.List(lbBefore.ListCount - 1, 1) = vItem(1)
        If UBound(vItem) > 1 Then lbBefore.List(lbBefore.ListCount - 1, 2) = vItem(2)
    Next i
    
    'Dim strName, strSource As String
    'Dim iFiber As Integer
    
    'iFiber = 1
    'lbCounts.Clear
    'lbCounts.AddItem ""
    
    'vLine = Split(strLine, " + ")
    'For i = 0 To UBound(vLine)
        'vItem = Split(vLine(i), ": ")
        'strName = vItem(0)
        'If UBound(vItem) < 2 Then
            'strSource = ""
        'Else
            'strSource = vItem(2)
        'End If
        
        'vCounts = Split(vItem(1), "-")
        'iStart = CInt(vCounts(0))
        'If UBound(vCounts) < 1 Then
            'iEnd = iStart
        'Else
            'iEnd = CInt(vCounts(1))
        'End If
        
        'strLine = iFiber & "-"
        'iFiber = iFiber + iEnd - iStart
        'strLine = strLine & iFiber
        
        'lbCounts.AddItem strLine
        'lbCounts.List(lbCounts.ListCount - 1, 1) = strName
        'lbCounts.List(lbCounts.ListCount - 1, 2) = vItem(1)
        'lbCounts.List(lbCounts.ListCount - 1, 3) = strSource
        
        'iFiber = iFiber + 1
        
        'For j = iStart To iEnd
            'lbCounts.AddItem iFiber
            'lbCounts.List(lbCounts.ListCount - 1, 1) = strName
            'lbCounts.List(lbCounts.ListCount - 1, 2) = j
            'lbCounts.List(lbCounts.ListCount - 1, 3) = strSource
            
            'iFiber = iFiber + 1
        'Next j
    'Next i
    
Exit_Sub:
    Me.show
End Sub

Private Sub lbList_KeyDown(ByVal KeyCode As MSForms.ReturnInteger, ByVal Shift As Integer)
    Dim strAtt(1) As String
    Dim iIndex As Integer
    
    Select Case KeyCode
        Case vbKeyReturn
            iListIndex = lbList.ListIndex
    
            tbEndFibers.Value = lbList.List(iListIndex, 0)
            tbSource.Value = lbList.List(iListIndex, 1)
    
            cbAddToList.Caption = "Update"
        Case vbKeyUp
            iIndex = lbList.ListIndex
            If iIndex < 1 Then Exit Sub
            
            strAtt(0) = lbList.List(iIndex, 0)
            strAtt(1) = lbList.List(iIndex, 1)
            
            lbList.List(iIndex, 0) = lbList.List(iIndex - 1, 0)
            lbList.List(iIndex, 1) = lbList.List(iIndex - 1, 1)
            
            lbList.List(iIndex - 1, 0) = strAtt(0)
            lbList.List(iIndex - 1, 1) = strAtt(1)
        Case vbKeyDown
            iIndex = lbList.ListIndex
            If iIndex > lbList.ListCount - 2 Then Exit Sub
            
            strAtt(0) = lbList.List(iIndex, 0)
            strAtt(1) = lbList.List(iIndex, 1)
            
            lbList.List(iIndex, 0) = lbList.List(iIndex + 1, 0)
            lbList.List(iIndex, 1) = lbList.List(iIndex + 1, 1)
            
            lbList.List(iIndex + 1, 0) = strAtt(0)
            lbList.List(iIndex + 1, 1) = strAtt(1)
        Case vbKeyDelete
            lbList.RemoveItem lbList.ListIndex
    End Select
End Sub

Private Sub UserForm_Initialize()
    lbCounts.ColumnCount = 4
    lbCounts.ColumnWidths = "48;96;48;90"

    lbList.ColumnCount = 2
    lbList.ColumnWidths = "72;72"

    lbBefore.ColumnCount = 3
    lbBefore.ColumnWidths = "60;24;60"
    
    cbEndFiber.AddItem "12"
    cbEndFiber.AddItem "24"
    cbEndFiber.AddItem "48"
    cbEndFiber.AddItem "72"
    cbEndFiber.AddItem "96"
    cbEndFiber.AddItem "144"
    cbEndFiber.AddItem "216"
    cbEndFiber.AddItem "288"
    cbEndFiber.AddItem "360"
    cbEndFiber.AddItem "432"
    cbEndFiber.AddItem "576"
    cbEndFiber.AddItem "876"
    
    cbCableSize.AddItem "12"
    cbCableSize.AddItem "24"
    cbCableSize.AddItem "48"
    cbCableSize.AddItem "72"
    cbCableSize.AddItem "96"
    cbCableSize.AddItem "144"
    cbCableSize.AddItem "216"
    cbCableSize.AddItem "288"
    cbCableSize.AddItem "360"
    cbCableSize.AddItem "432"
    cbCableSize.AddItem "576"
    cbCableSize.AddItem "876"
End Sub

Private Sub UpdateCallout()
    Dim vLine, vItem, vCounts As Variant
    Dim iStart, iEnd As Integer
    
    For i = 0 To lbList.ListCount - 1
        vItem = Split(lbList.List(i, 0), "-")
        iStart = CInt(vItem(0))
        iEnd = CInt(vItem(1))
        
        For j = iStart To iEnd
            
        Next j
    Next i
End Sub

Attribute VB_Name = "ValidateAttachPole"
Attribute VB_Base = "0{698C41F1-56DE-466C-BFA9-4C7B6A71D4CF}{76A72890-828A-4FDF-8FB6-FDE20F4765BE}"
Attribute VB_GlobalNameSpace = False
Attribute VB_Creatable = False
Attribute VB_PredeclaredId = True
Attribute VB_Exposed = False
Attribute VB_TemplateDerived = False
Attribute VB_Customizable = False
Private Sub cbMark_Click()
    Dim objCircle As AcadCircle
    Dim dInsert(2) As Double
    Dim vTemp As Variant

    vTemp = Split(tbCoords.Value, ",")
    dInsert(0) = CDbl(vTemp(0))
    dInsert(1) = CDbl(vTemp(1))
    dInsert(2) = 0#
                    
    Set objCircle = ThisDrawing.ModelSpace.AddCircle(dInsert, 80)
    objCircle.Layer = "Integrity Notes"
    objCircle.Update
End Sub

Private Sub cbQuit_Click()
    Me.Hide
End Sub

Private Sub LabelPan_Click()
    Dim entPole As AcadObject
    Dim basePnt As Variant
    
    Me.Hide
  On Error Resume Next
    Err = 0
    
    ThisDrawing.Utility.GetEntity entPole, basePnt, "Left Click to Exit: "
    
    Me.show
End Sub

Attribute VB_Name = "ValidateAttachments"
Attribute VB_Base = "0{3DA8596D-A4B3-43E7-A57B-77CAB350E35E}{B3315D44-A753-4F0B-B101-3ECDE4A8E752}"
Attribute VB_GlobalNameSpace = False
Attribute VB_Creatable = False
Attribute VB_PredeclaredId = True
Attribute VB_Exposed = False
Attribute VB_TemplateDerived = False
Attribute VB_Customizable = False

Private Sub cbClearSame_Click()
    If lbPoles.ListCount < 1 Then Exit Sub
    
    For i = lbPoles.ListCount - 1 To 0 Step -1
        If lbPoles.List(i, 1) = lbPoles.List(i, 3) Then
            If lbPoles.List(i, 2) = lbPoles.List(i, 4) Then lbPoles.RemoveItem i
        End If
    Next i
    
    tbDifferent.Value = lbPoles.ListCount
End Sub

'Dim vMapLL, vMapUR As Variant

Private Sub cbGetPoles_Click()
    Dim vDwgLL, vDwgUR As Variant
    Dim filterType, filterValue As Variant
    Dim grpCode(0) As Integer
    Dim grpValue(0) As Variant
    Dim objSSDwg As AcadSelectionSet
    Dim objPoleDwg As AcadBlockReference
    Dim vAttDwg, vAttMap As Variant
    Dim vLine, vTemp As Variant
    Dim strPoleNum As String
    Dim strDwgLatLong, strMapLatLong As String
    Dim iPwr, iCOMM As Integer
    
    iPwr = 0
    iCOMM = 0
    
    On Error Resume Next
    
    Me.Hide
    Err = 0
    
    vDwgLL = ThisDrawing.Utility.GetPoint(, "Get DWG LL Corner: ")
    vDwgUR = ThisDrawing.Utility.GetCorner(vDwgLL, vbCr & "Get DWG UR Corner: ")
    
    grpCode(0) = 2
    grpValue(0) = "sPole"
    filterType = grpCode
    filterValue = grpValue
    
    Set objSSDwg = ThisDrawing.SelectionSets.Add("objSSDwg")
    objSSDwg.Select acSelectionSetWindow, vDwgLL, vDwgUR, filterType, filterValue
    If objSSDwg.count < 1 Then GoTo Exit_Sub
    
    For Each objPoleDwg In objSSDwg
        vAttDwg = objPoleDwg.GetAttributes
        If vAttDwg(7).TextString = "" Then GoTo Next_objDwgPole
        
        strPoleNum = vAttDwg(0).TextString
        strDwgLatLong = vAttDwg(7).TextString
        'strDwgLatLong = objPoleDwg.InsertionPoint(0) & "," & objPoleDwg.InsertionPoint(1)
        
        If strPoleNum = "POLE" Then GoTo Next_objDwgPole
        If strPoleNum = "" Then GoTo Next_objDwgPole
        
        
        If Not vAttDwg(9).TextString = "" Then
            vLine = Split(vAttDwg(9).TextString, " ")
            iPwr = iPwr + UBound(vLine) + 1
        End If
        
        If Not vAttDwg(10).TextString = "" Then
            vLine = Split(vAttDwg(10).TextString, " ")
            iPwr = iPwr + UBound(vLine) + 1
        End If
        
        If Not vAttDwg(11).TextString = "" Then
            vLine = Split(vAttDwg(11).TextString, " ")
            iPwr = iPwr + UBound(vLine) + 1
        End If
        
        If Not vAttDwg(12).TextString = "" Then
            vLine = Split(vAttDwg(12).TextString, " ")
            iPwr = iPwr + UBound(vLine) + 1
        End If
        
        If Not vAttDwg(13).TextString = "" Then
            vLine = Split(vAttDwg(13).TextString, " ")
            iPwr = iPwr + UBound(vLine) + 1
        End If
        
        If Not vAttDwg(14).TextString = "" Then
            vLine = Split(vAttDwg(14).TextString, " ")
            iPwr = iPwr + UBound(vLine) + 1
        End If
        
        If Not vAttDwg(16).TextString = "" Then
            vTemp = Split(vAttDwg(16).TextString, "=")
            vLine = Split(vTemp(UBound(vTemp)), " ")
            iCOMM = iCOMM + UBound(vLine) + 1
        End If
        
        If Not vAttDwg(17).TextString = "" Then
            vTemp = Split(vAttDwg(17).TextString, "=")
            vLine = Split(vTemp(UBound(vTemp)), " ")
            iCOMM = iCOMM + UBound(vLine) + 1
        End If
        
        If Not vAttDwg(18).TextString = "" Then
            vTemp = Split(vAttDwg(18).TextString, "=")
            vLine = Split(vTemp(UBound(vTemp)), " ")
            iCOMM = iCOMM + UBound(vLine) + 1
        End If
        
        If Not vAttDwg(19).TextString = "" Then
            vTemp = Split(vAttDwg(19).TextString, "=")
            vLine = Split(vTemp(UBound(vTemp)), " ")
            iCOMM = iCOMM + UBound(vLine) + 1
        End If
        
        If Not vAttDwg(20).TextString = "" Then
            vTemp = Split(vAttDwg(20).TextString, "=")
            vLine = Split(vTemp(UBound(vTemp)), " ")
            iCOMM = iCOMM + UBound(vLine) + 1
        End If
        
        If Not vAttDwg(21).TextString = "" Then
            vTemp = Split(vAttDwg(21).TextString, "=")
            vLine = Split(vTemp(UBound(vTemp)), " ")
            iCOMM = iCOMM + UBound(vLine) + 1
        End If
        
        If Not vAttDwg(22).TextString = "" Then
            vTemp = Split(vAttDwg(22).TextString, "=")
            vLine = Split(vTemp(UBound(vTemp)), " ")
            iCOMM = iCOMM + UBound(vLine) + 1
        End If
        
        If Not vAttDwg(23).TextString = "" Then
            vTemp = Split(vAttDwg(23).TextString, "=")
            vLine = Split(vTemp(UBound(vTemp)), " ")
            iCOMM = iCOMM + UBound(vLine) + 1
        End If
        
        lbPoles.AddItem strPoleNum
        lbPoles.List(lbPoles.ListCount - 1, 1) = iPwr
        lbPoles.List(lbPoles.ListCount - 1, 2) = iCOMM
        lbPoles.List(lbPoles.ListCount - 1, 3) = ""
        lbPoles.List(lbPoles.ListCount - 1, 4) = ""
        lbPoles.List(lbPoles.ListCount - 1, 5) = strDwgLatLong
        lbPoles.List(lbPoles.ListCount - 1, 6) = objPoleDwg.InsertionPoint(0) & "," & objPoleDwg.InsertionPoint(1)
        lbPoles.List(lbPoles.ListCount - 1, 7) = ""
        
        iPwr = 0
        iCOMM = 0
Next_objDwgPole:
    Next objPoleDwg
    
Exit_Sub:
    objSSDwg.Clear
    objSSDwg.Delete
    
    tbTotal.Value = lbPoles.ListCount
    
    If lbPoles.ListCount > 0 Then Call SortList
    
    Me.show
End Sub

Private Sub cbQuit_Click()
    Me.Hide
End Sub

Private Sub LabelPan_Click()
    Dim entPole As AcadObject
    Dim basePnt As Variant
    
    Me.Hide
  On Error Resume Next
    Err = 0
    
    ThisDrawing.Utility.GetEntity entPole, basePnt, "Left Click to Exit: "
    
    Me.show
End Sub

Private Sub lbDWG_DblClick(ByVal Cancel As MSForms.ReturnBoolean)
    If lbPoles.ListCount < 1 Then Exit Sub
    If Not lbPoles.List(0, 3) = "" Then Exit Sub
    If Not lbPoles.List(0, 4) = "" Then Exit Sub
    
    Dim objMainDwg As AcadDocument
    Dim filterType, filterValue As Variant
    Dim grpCode(0) As Integer
    Dim grpValue(0) As Variant
    Dim objSSMap As AcadSelectionSet
    Dim objPole As AcadBlockReference
    Dim vAttMap, vLine, vTemp As Variant
    Dim strFile As String
    Dim strAttach As String
    Dim iPwr, iCOMM As Integer
    
    Set objMainDwg = ThisDrawing
    
    strFile = ThisDrawing.Path & "\MISC\" & lbDWG.List(lbDWG.ListIndex) & ".dwg"
    'MsgBox strFile
    
    If Dir(strFile) = "" Then
        MsgBox "Error opening file."
        Exit Sub
    End If
    
    ThisDrawing.Application.Documents.Open strFile
    ZoomExtents
    
    grpCode(0) = 2
    grpValue(0) = "sPole"
    filterType = grpCode
    filterValue = grpValue
    
    Set objSSMap = ThisDrawing.SelectionSets.Add("objSSMap")
    objSSMap.Select acSelectionSetAll, , , filterType, filterValue
    If objSSMap.count < 1 Then
        MsgBox "None found"
        GoTo Exit_Sub
    End If
    
    For Each objPole In objSSMap
        iPwr = 0
        iCOMM = 0
        strAttach = ""
        vAttMap = objPole.GetAttributes
        If vAttMap(7).TextString = "" Then GoTo Next_objPole
        
        For i = 0 To lbPoles.ListCount - 1
            If vAttMap(7).TextString = lbPoles.List(i, 5) Then
                If Not vAttMap(9).TextString = "" Then
                    vLine = Split(vAttMap(9).TextString, " ")
                    iPwr = iPwr + UBound(vLine) + 1
                    strAttach = "N = " & vAttMap(9).TextString
                End If
        
                If Not vAttMap(10).TextString = "" Then
                    vLine = Split(vAttMap(10).TextString, " ")
                    iPwr = iPwr + UBound(vLine) + 1
                    strAttach = strAttach & vbCr & "TF = " & vAttMap(10).TextString
                End If
        
                If Not vAttMap(11).TextString = "" Then
                    vLine = Split(vAttMap(11).TextString, " ")
                    iPwr = iPwr + UBound(vLine) + 1
                    strAttach = strAttach & vbCr & "LP = " & vAttMap(11).TextString
                End If
        
                If Not vAttMap(12).TextString = "" Then
                    vLine = Split(vAttMap(12).TextString, " ")
                    iPwr = iPwr + UBound(vLine) + 1
                    strAttach = strAttach & vbCr & "ANT = " & vAttMap(12).TextString
                End If
        
                If Not vAttMap(13).TextString = "" Then
                    vLine = Split(vAttMap(13).TextString, " ")
                    iPwr = iPwr + UBound(vLine) + 1
                    strAttach = strAttach & vbCr & "SLC = " & vAttMap(13).TextString
                End If
        
                If Not vAttMap(14).TextString = "" Then
                    vLine = Split(vAttMap(14).TextString, " ")
                    iPwr = iPwr + UBound(vLine) + 1
                    strAttach = strAttach & vbCr & "SL = " & vAttMap(14).TextString
                End If
        
                If Not vAttMap(15).TextString = "" Then
                    strAttach = strAttach & vbCr & "NEW = " & vAttMap(15).TextString
                End If
        
                If Not vAttMap(16).TextString = "" Then
                    vTemp = Split(vAttMap(16).TextString, "=")
                    vLine = Split(vTemp(UBound(vTemp)), " ")
                    For j = 0 To UBound(vLine)
                        If Not vLine(j) = "" Then
                            iCOMM = iCOMM + 1
                            strAttach = strAttach & vbCr & vTemp(0) & "= " & vLine(j)
                        End If
                    Next j
                End If
        
                If Not vAttMap(17).TextString = "" Then
                    vTemp = Split(vAttMap(17).TextString, "=")
                    vLine = Split(vTemp(UBound(vTemp)), " ")
                    For j = 0 To UBound(vLine)
                        If Not vLine(j) = "" Then
                            iCOMM = iCOMM + 1
                            strAttach = strAttach & vbCr & vTemp(0) & "= " & vLine(j)
                        End If
                    Next j
                End If
        
                If Not vAttMap(18).TextString = "" Then
                    vTemp = Split(vAttMap(18).TextString, "=")
                    vLine = Split(vTemp(UBound(vTemp)), " ")
                    For j = 0 To UBound(vLine)
                        If Not vLine(j) = "" Then
                            iCOMM = iCOMM + 1
                            strAttach = strAttach & vbCr & vTemp(0) & "= " & vLine(j)
                        End If
                    Next j
                End If
        
                If Not vAttMap(19).TextString = "" Then
                    vTemp = Split(vAttMap(19).TextString, "=")
                    vLine = Split(vTemp(UBound(vTemp)), " ")
                    For j = 0 To UBound(vLine)
                        If Not vLine(j) = "" Then
                            iCOMM = iCOMM + 1
                            strAttach = strAttach & vbCr & vTemp(0) & "= " & vLine(j)
                        End If
                    Next j
                End If
        
                If Not vAttMap(20).TextString = "" Then
                    vTemp = Split(vAttMap(20).TextString, "=")
                    vLine = Split(vTemp(UBound(vTemp)), " ")
                    For j = 0 To UBound(vLine)
                        If Not vLine(j) = "" Then
                            iCOMM = iCOMM + 1
                            strAttach = strAttach & vbCr & vTemp(0) & "= " & vLine(j)
                        End If
                    Next j
                End If
        
                If Not vAttMap(21).TextString = "" Then
                    vTemp = Split(vAttMap(21).TextString, "=")
                    vLine = Split(vTemp(UBound(vTemp)), " ")
                    For j = 0 To UBound(vLine)
                        If Not vLine(j) = "" Then
                            iCOMM = iCOMM + 1
                            strAttach = strAttach & vbCr & vTemp(0) & "= " & vLine(j)
                        End If
                    Next j
                End If
        
                If Not vAttMap(22).TextString = "" Then
                    vTemp = Split(vAttMap(22).TextString, "=")
                    vLine = Split(vTemp(UBound(vTemp)), " ")
                    For j = 0 To UBound(vLine)
                        If Not vLine(j) = "" Then
                            iCOMM = iCOMM + 1
                            strAttach = strAttach & vbCr & vTemp(0) & "= " & vLine(j)
                        End If
                    Next j
                End If
        
                If Not vAttMap(23).TextString = "" Then
                    vTemp = Split(vAttMap(23).TextString, "=")
                    vLine = Split(vTemp(UBound(vTemp)), " ")
                    For j = 0 To UBound(vLine)
                        If Not vLine(j) = "" Then
                            iCOMM = iCOMM + 1
                            strAttach = strAttach & vbCr & vTemp(0) & "= " & vLine(j)
                        End If
                    Next j
                End If
        
                If Not vAttMap(24).TextString = "" Then
                    strAttach = strAttach & vbCr & "OHG = " & vAttMap(24).TextString
                End If
                
                lbPoles.List(i, 3) = iPwr
                lbPoles.List(i, 4) = iCOMM
                lbPoles.List(i, 7) = strAttach
            End If
        Next i
        
Next_objPole:
    Next objPole
    
    ThisDrawing.Close False, strFile
Exit_Sub:
    'objSSMap.Clear
    'objSSMap.Delete
    
    objMainDwg.Activate
End Sub

Private Sub lbOpen_DblClick(ByVal Cancel As MSForms.ReturnBoolean)
    If lbPoles.ListCount < 1 Then Exit Sub
    If Not lbPoles.List(0, 3) = "" Then Exit Sub
    If Not lbPoles.List(0, 4) = "" Then Exit Sub
    
    Dim objMainDwg As AcadDocument
    Dim objDoc As AcadDocument
    Dim filterType, filterValue As Variant
    Dim grpCode(0) As Integer
    Dim grpValue(0) As Variant
    Dim objSSMap As AcadSelectionSet
    Dim objPole As AcadBlockReference
    Dim vAttMap, vLine, vTemp As Variant
    Dim strFile As String
    Dim strName, strAttach As String
    Dim iPwr, iCOMM As Integer
    
    strName = ThisDrawing.Name
    
    For Each objDoc In AcadApplication.Documents
        If objDoc.Name = lbOpen.List(lbOpen.ListIndex, 0) Then GoTo Found_Doc
    Next objDoc
    
    MsgBox "Not Found" & vbCr & lbOpen.List(lbOpen.ListIndex, 0)
    
    Exit Sub
    
Found_Doc:
    
    objDoc.Activate
    
    ZoomExtents
    
    grpCode(0) = 2
    grpValue(0) = "sPole"
    filterType = grpCode
    filterValue = grpValue
    
    Set objSSMap = ThisDrawing.SelectionSets.Add("objSSMap")
    objSSMap.Select acSelectionSetAll, , , filterType, filterValue
    If objSSMap.count < 1 Then
        MsgBox "None found"
        GoTo Exit_Sub
    End If
    
    For Each objPole In objSSMap
        iPwr = 0
        iCOMM = 0
        strAttach = ""
        vAttMap = objPole.GetAttributes
        If vAttMap(7).TextString = "" Then GoTo Next_objPole
        
        For i = 0 To lbPoles.ListCount - 1
            If vAttMap(7).TextString = lbPoles.List(i, 5) Then
                If Not vAttMap(9).TextString = "" Then
                    vLine = Split(vAttMap(9).TextString, " ")
                    iPwr = iPwr + UBound(vLine) + 1
                    strAttach = "N = " & vAttMap(9).TextString
                End If
        
                If Not vAttMap(10).TextString = "" Then
                    vLine = Split(vAttMap(10).TextString, " ")
                    iPwr = iPwr + UBound(vLine) + 1
                    strAttach = strAttach & vbCr & "TF = " & vAttMap(10).TextString
                End If
        
                If Not vAttMap(11).TextString = "" Then
                    vLine = Split(vAttMap(11).TextString, " ")
                    iPwr = iPwr + UBound(vLine) + 1
                    strAttach = strAttach & vbCr & "LP = " & vAttMap(11).TextString
                End If
        
                If Not vAttMap(12).TextString = "" Then
                    vLine = Split(vAttMap(12).TextString, " ")
                    iPwr = iPwr + UBound(vLine) + 1
                    strAttach = strAttach & vbCr & "ANT = " & vAttMap(12).TextString
                End If
        
                If Not vAttMap(13).TextString = "" Then
                    vLine = Split(vAttMap(13).TextString, " ")
                    iPwr = iPwr + UBound(vLine) + 1
                    strAttach = strAttach & vbCr & "SLC = " & vAttMap(13).TextString
                End If
        
                If Not vAttMap(14).TextString = "" Then
                    vLine = Split(vAttMap(14).TextString, " ")
                    iPwr = iPwr + UBound(vLine) + 1
                    strAttach = strAttach & vbCr & "SL = " & vAttMap(14).TextString
                End If
        
                If Not vAttMap(15).TextString = "" Then
                    strAttach = strAttach & vbCr & "NEW = " & vAttMap(15).TextString
                End If
        
                If Not vAttMap(16).TextString = "" Then
                    vTemp = Split(vAttMap(16).TextString, "=")
                    vLine = Split(vTemp(UBound(vTemp)), " ")
                    For j = 0 To UBound(vLine)
                        If Not vLine(j) = "" Then
                            iCOMM = iCOMM + 1
                            strAttach = strAttach & vbCr & vTemp(0) & "= " & vLine(j)
                        End If
                    Next j
                End If
        
                If Not vAttMap(17).TextString = "" Then
                    vTemp = Split(vAttMap(17).TextString, "=")
                    vLine = Split(vTemp(UBound(vTemp)), " ")
                    For j = 0 To UBound(vLine)
                        If Not vLine(j) = "" Then
                            iCOMM = iCOMM + 1
                            strAttach = strAttach & vbCr & vTemp(0) & "= " & vLine(j)
                        End If
                    Next j
                End If
        
                If Not vAttMap(18).TextString = "" Then
                    vTemp = Split(vAttMap(18).TextString, "=")
                    vLine = Split(vTemp(UBound(vTemp)), " ")
                    For j = 0 To UBound(vLine)
                        If Not vLine(j) = "" Then
                            iCOMM = iCOMM + 1
                            strAttach = strAttach & vbCr & vTemp(0) & "= " & vLine(j)
                        End If
                    Next j
                End If
        
                If Not vAttMap(19).TextString = "" Then
                    vTemp = Split(vAttMap(19).TextString, "=")
                    vLine = Split(vTemp(UBound(vTemp)), " ")
                    For j = 0 To UBound(vLine)
                        If Not vLine(j) = "" Then
                            iCOMM = iCOMM + 1
                            strAttach = strAttach & vbCr & vTemp(0) & "= " & vLine(j)
                        End If
                    Next j
                End If
        
                If Not vAttMap(20).TextString = "" Then
                    vTemp = Split(vAttMap(20).TextString, "=")
                    vLine = Split(vTemp(UBound(vTemp)), " ")
                    For j = 0 To UBound(vLine)
                        If Not vLine(j) = "" Then
                            iCOMM = iCOMM + 1
                            strAttach = strAttach & vbCr & vTemp(0) & "= " & vLine(j)
                        End If
                    Next j
                End If
        
                If Not vAttMap(21).TextString = "" Then
                    vTemp = Split(vAttMap(21).TextString, "=")
                    vLine = Split(vTemp(UBound(vTemp)), " ")
                    For j = 0 To UBound(vLine)
                        If Not vLine(j) = "" Then
                            iCOMM = iCOMM + 1
                            strAttach = strAttach & vbCr & vTemp(0) & "= " & vLine(j)
                        End If
                    Next j
                End If
        
                If Not vAttMap(22).TextString = "" Then
                    vTemp = Split(vAttMap(22).TextString, "=")
                    vLine = Split(vTemp(UBound(vTemp)), " ")
                    For j = 0 To UBound(vLine)
                        If Not vLine(j) = "" Then
                            iCOMM = iCOMM + 1
                            strAttach = strAttach & vbCr & vTemp(0) & "= " & vLine(j)
                        End If
                    Next j
                End If
        
                If Not vAttMap(23).TextString = "" Then
                    vTemp = Split(vAttMap(23).TextString, "=")
                    vLine = Split(vTemp(UBound(vTemp)), " ")
                    For j = 0 To UBound(vLine)
                        If Not vLine(j) = "" Then
                            iCOMM = iCOMM + 1
                            strAttach = strAttach & vbCr & vTemp(0) & "= " & vLine(j)
                        End If
                    Next j
                End If
        
                If Not vAttMap(24).TextString = "" Then
                    strAttach = strAttach & vbCr & "OHG = " & vAttMap(24).TextString
                End If
                
                lbPoles.List(i, 3) = iPwr
                lbPoles.List(i, 4) = iCOMM
                lbPoles.List(i, 7) = strAttach
            End If
        Next i
        
Next_objPole:
    Next objPole
    
    'ThisDrawing.Close , strFile
Exit_Sub:
    objSSMap.Clear
    objSSMap.Delete
    
    For Each objDoc In AcadApplication.Documents
        If objDoc.Name = strName Then GoTo Found_Doc2
    Next objDoc
    
    Exit Sub
    
Found_Doc2:
    
    objDoc.Activate
End Sub

Private Sub lbPoles_DblClick(ByVal Cancel As MSForms.ReturnBoolean)
    Dim vCoords As Variant
    Dim viewCoordsB(0 To 2) As Double
    Dim viewCoordsE(0 To 2) As Double
    
    Me.Hide
    
    vCoords = Split(lbPoles.List(lbPoles.ListIndex, 6), ",")
    'MsgBox vCoords(0) & vbCr & vCoords(1)
    
    viewCoordsB(0) = CDbl(vCoords(0)) - 300
    viewCoordsB(1) = CDbl(vCoords(1)) - 300
    viewCoordsB(2) = 0#
    viewCoordsE(0) = CDbl(vCoords(0)) + 300
    viewCoordsE(1) = CDbl(vCoords(1)) + 300
    viewCoordsE(2) = 0#
    
    ThisDrawing.Application.ZoomWindow viewCoordsB, viewCoordsE
    
    Load ValidateAttachPole
        ValidateAttachPole.tbAttach.Value = lbPoles.List(lbPoles.ListIndex, 7)
        ValidateAttachPole.tbPole.Value = lbPoles.List(lbPoles.ListIndex, 0)
        ValidateAttachPole.tbCoords.Value = lbPoles.List(lbPoles.ListIndex, 6)
        
        ValidateAttachPole.show
    Unload ValidateAttachPole
    
    'MsgBox lbPoles.List(lbPoles.ListIndex, 7), , lbPoles.List(lbPoles.ListIndex, 0)
    
    Me.show
End Sub

Private Sub lbPoles_KeyDown(ByVal KeyCode As MSForms.ReturnInteger, ByVal Shift As Integer)
    If lbPoles.ListCount < 1 Then Exit Sub
    
    Select Case KeyCode
        Case vbKeyReturn
            Dim result, iIndex As Integer
            Dim objCircle As AcadCircle
            Dim dInsert(2) As Double
            Dim vTemp As Variant
            
            iIndex = lbPoles.ListIndex
            
            Me.Hide
                result = MsgBox(lbPoles.List(iIndex, 7), vbYesNo, "Mark " & lbPoles.List(iIndex, 0))
                If result = vbYes Then
                    vTemp = Split(lbPoles.List(iIndex, 6), ",")
                    dInsert(0) = CDbl(vTemp(0))
                    dInsert(1) = CDbl(vTemp(1))
                    dInsert(2) = 0#
                    
                    Set objCircle = ThisDrawing.ModelSpace.AddCircle(dInsert, 80)
                    objCircle.Layer = "Integrity Notes"
                    objCircle.Update
                End If
            Me.show
        Case vbKeyDelete
            lbPoles.RemoveItem lbPoles.ListIndex
    End Select
End Sub

Private Sub UserForm_Initialize()
    lbPoles.ColumnCount = 8
    lbPoles.ColumnWidths = "120;36;36;36;24;6;6;6"
    
    lbOpen.ColumnCount = 2
    lbOpen.ColumnWidths = "264;6"
    
    Dim strFolder, strFile As String
    Dim vTemp As Variant
    
    strFolder = ""
    
    strFolder = ThisDrawing.Path & "\MISC\*.*"
    
    strFile = Dir$(strFolder)
    
    Do While strFile <> ""
        If InStr(strFile, ".dwg") Then
            lbDWG.AddItem Replace(strFile, ".dwg", "")
        End If
        strFile = Dir$
    Loop
    
    Dim objDoc As AcadDocument
    
    For Each objDoc In AcadApplication.Documents
        lbOpen.AddItem objDoc.Name
        lbOpen.List(lbOpen.ListCount - 1, 1) = objDoc.FullName
    Next objDoc
End Sub

Private Sub SortList()
    Dim strTemp, strTotal As String
    Dim iCount, iOffset As Integer
    Dim iIndex As Integer
    Dim strAtt(0 To 6) As String
    
    iCount = lbPoles.ListCount - 1
    If iCount < 1 Then Exit Sub
    
    On Error Resume Next
    
    For a = iCount To 0 Step -1
        For b = 0 To a - 1
            If lbPoles.List(b, 0) > lbPoles.List(b + 1, 0) Then
                If Not Err = 0 Then
                    MsgBox "Error sorting list"
                    lbPoles.Selected(b) = True
                    lbPoles.ListIndex = b
                    Exit Sub
                End If
                
                strAtt(0) = lbPoles.List(b + 1, 0)
                strAtt(1) = lbPoles.List(b + 1, 1)
                strAtt(2) = lbPoles.List(b + 1, 2)
                strAtt(3) = lbPoles.List(b + 1, 3)
                strAtt(4) = lbPoles.List(b + 1, 4)
                strAtt(5) = lbPoles.List(b + 1, 5)
                strAtt(6) = lbPoles.List(b + 1, 6)
                
                lbPoles.List(b + 1, 0) = lbPoles.List(b, 0)
                lbPoles.List(b + 1, 1) = lbPoles.List(b, 1)
                lbPoles.List(b + 1, 2) = lbPoles.List(b, 2)
                lbPoles.List(b + 1, 3) = lbPoles.List(b, 3)
                lbPoles.List(b + 1, 4) = lbPoles.List(b, 4)
                lbPoles.List(b + 1, 5) = lbPoles.List(b, 5)
                lbPoles.List(b + 1, 6) = lbPoles.List(b, 6)
                
                lbPoles.List(b, 0) = strAtt(0)
                lbPoles.List(b, 1) = strAtt(1)
                lbPoles.List(b, 2) = strAtt(2)
                lbPoles.List(b, 3) = strAtt(3)
                lbPoles.List(b, 4) = strAtt(4)
                lbPoles.List(b, 5) = strAtt(5)
                lbPoles.List(b, 6) = strAtt(6)
            End If
        Next b
    Next a
End Sub

Attribute VB_Name = "ValidateChecklist"
Attribute VB_Base = "0{806B081D-D757-46B6-B7E2-ADC0400B8727}{931BC0FD-B53E-49C9-9092-85FD696209A4}"
Attribute VB_GlobalNameSpace = False
Attribute VB_Creatable = False
Attribute VB_PredeclaredId = True
Attribute VB_Exposed = False
Attribute VB_TemplateDerived = False
Attribute VB_Customizable = False
Private Sub cbCountsCallout_Click()
    Me.Hide
        Load PlaceCountCallouts
        PlaceCountCallouts.show
        Unload PlaceCountCallouts
    Me.show
End Sub

Private Sub cbExtraHeights_Click()
    Me.Hide
        Load ExtraHeightForm
        ExtraHeightForm.show
        Unload ExtraHeightForm
    Me.show
End Sub

Private Sub cbGetSpansReel_Click()
    Me.Hide
        Load GetSpansReel
        GetSpansReel.show
        Unload GetSpansReel
    Me.show
End Sub

Private Sub cbQuit_Click()
    Call SaveData
    Me.Hide
End Sub

Private Sub cbTabGeneric_Click()
    Me.Hide
        Load TabGeneric
            TabGeneric.show
        Unload TabGeneric
    Me.show
End Sub

Private Sub cbTDOT_Click()
    Me.Hide
        Load TDOT
            TDOT.show
        Unload TDOT
    Me.show
End Sub

Private Sub cbTransfer_Click()
    Me.Hide
        Load TransferToMap
        TransferToMap.show
        Unload TransferToMap
    Me.show
End Sub

Private Sub cbValidateCounts_Click()
    Me.Hide
        Load ValidateCounts
        ValidateCounts.show
        Unload ValidateCounts
    Me.show
End Sub

Private Sub cbValidateCustomers_Click()
    Me.Hide
        Load ValidateCustomers
        ValidateCustomers.show
        Unload ValidateCustomers
    Me.show
End Sub

Private Sub cbValidateHO1_Click()
    Me.Hide
        Load ValidateHO1
        ValidateHO1.show
        Unload ValidateHO1
    Me.show
End Sub

Private Sub cbValidateMCL_Click()
    Me.Hide
        Load ValidateMCL
        ValidateMCL.show
        Unload ValidateMCL
    Me.show
End Sub

Private Sub cbValidateML_Click()
    Me.Hide
        Load ValidateML
        ValidateML.show
        Unload ValidateML
    Me.show
End Sub

Private Sub cbVerifyUnits_Click()
    Me.Hide
        Load VerifyUnits
            VerifyUnits.show
        Unload VerifyUnits
    Me.show
End Sub

Private Sub UserForm_Initialize()
    Dim strFileName As String
    Dim vLine As Variant
    Dim fName As String
    
    strFileName = ThisDrawing.Path & "\xxQC Checklist.qcl"
    
    fName = Dir(strFileName)
    If fName = "" Then
        MsgBox "No File found."
        Exit Sub
    End If
    
    Open strFileName For Input As #2
    
    While Not EOF(2)
        Line Input #2, strLine
        vLine = Split(strLine, vbTab)
        
        Select Case vLine(0)
            Case "Validate Matchlines"
                If vLine(1) = "Y" Then chVML.Value = True
            Case "Validate Customers"
                If vLine(1) = "Y" Then chVCustomers.Value = True
            Case "Validate MCL"
                If vLine(1) = "Y" Then chVMCL.Value = True
            Case "Counts Callouts"
                If vLine(1) = "Y" Then chCC.Value = True
            Case "Validate Callouts"
                If vLine(1) = "Y" Then chVCallouts.Value = True
            Case "Validate Splices"
                If vLine(1) = "Y" Then chVHO1.Value = True
            Case "Validate Units"
                If vLine(1) = "Y" Then chVUnits.Value = True
            Case "Tab"
                If vLine(1) = "Y" Then chTab.Value = True
            Case "Extra Heights"
                If vLine(1) = "Y" Then chEH.Value = True
            Case "Spans for Reels"
                If vLine(1) = "Y" Then chS4R.Value = True
            Case "Print DWGs"
                If vLine(1) = "Y" Then chPrint.Value = True
            Case "Transfer Data to Maps"
                If vLine(1) = "Y" Then chTransfer.Value = True
        End Select
    Wend
    
Exit_Sub:
    Close #2
End Sub

Private Sub SaveData()
    Dim strFileName As String
    Dim vLine As Variant
    Dim strLine As String
    
    strFileName = ThisDrawing.Path & "\xxQC Checklist.qcl"
    
    Open strFileName For Output As #2
    
    If chVML.Value = True Then
        strLine = "Validate Matchlines" & vbTab & "Y"
    Else
        strLine = "Validate Matchlines" & vbTab & "N"
    End If
    Print #2, strLine
    
    If chVCustomers.Value = True Then
        strLine = "Validate Customers" & vbTab & "Y"
    Else
        strLine = "Validate Customers" & vbTab & "N"
    End If
    Print #2, strLine
    
    If chVMCL.Value = True Then
        strLine = "Validate MCL" & vbTab & "Y"
    Else
        strLine = "Validate MCL" & vbTab & "N"
    End If
    Print #2, strLine
    
    If chCC.Value = True Then
        strLine = "Counts Callouts" & vbTab & "Y"
    Else
        strLine = "Counts Callouts" & vbTab & "N"
    End If
    Print #2, strLine
    
    If chVCallouts.Value = True Then
        strLine = "Validate Callouts" & vbTab & "Y"
    Else
        strLine = "Validate Callouts" & vbTab & "N"
    End If
    Print #2, strLine
    
    If chVHO1.Value = True Then
        strLine = "Validate Splices" & vbTab & "Y"
    Else
        strLine = "Validate Splices" & vbTab & "N"
    End If
    Print #2, strLine
    
    If chVUnits.Value = True Then
        strLine = "Validate Units" & vbTab & "Y"
    Else
        strLine = "Validate Units" & vbTab & "N"
    End If
    Print #2, strLine
    
    If chTab.Value = True Then
        strLine = "Tab" & vbTab & "Y"
    Else
        strLine = "Tab" & vbTab & "N"
    End If
    Print #2, strLine
    
    If chEH.Value = True Then
        strLine = "Extra Heights" & vbTab & "Y"
    Else
        strLine = "Extra Heights" & vbTab & "N"
    End If
    Print #2, strLine
    
    If chS4R.Value = True Then
        strLine = "Spans for Reels" & vbTab & "Y"
    Else
        strLine = "Spans for Reels" & vbTab & "N"
    End If
    Print #2, strLine
    
    If chPrint.Value = True Then
        strLine = "Print DWGs" & vbTab & "Y"
    Else
        strLine = "Print DWGs" & vbTab & "N"
    End If
    Print #2, strLine
    
    If chTransfer.Value = True Then
        strLine = "Transfer Data to Maps" & vbTab & "Y"
    Else
        strLine = "Transfer Data to Maps" & vbTab & "N"
    End If
    Print #2, strLine
    
    Close #2
End Sub

Attribute VB_Name = "ValidateCounts"
Attribute VB_Base = "0{DAAE3EEF-50F2-4F7E-89E5-D7B9FB3CAFE6}{6B56F293-DC99-4E50-9B80-B18F4D57C6D3}"
Attribute VB_GlobalNameSpace = False
Attribute VB_Creatable = False
Attribute VB_PredeclaredId = True
Attribute VB_Exposed = False
Attribute VB_TemplateDerived = False
Attribute VB_Customizable = False
Dim objSSPole As AcadSelectionSet
Dim objSS As AcadSelectionSet
Dim vPnt1, vPnt2 As Variant
Dim strStatus As String
Dim iIndex, iPole, iCallout As Integer

Private Sub cbChangeCallout_Click()
    Dim vLine, vItem, vTemp As Variant
    Dim strLine As String
    
    strLine = Replace(tbPole.Value, vbLf, "")
    vLine = Split(strLine, vbCr)
    strLine = ""
    For i = 0 To UBound(vLine)
        vItem = Split(vLine(i), ": ")
        If strLine = "" Then
            strLine = vItem(0) & ": " & vItem(1)
        Else
            strLine = strLine & vbCr & vItem(0) & ": " & vItem(1)
        End If
    Next i
    
    tbCallout.Value = strLine
End Sub

Private Sub cbChangePole_Click()
    Dim vPrevious, vLine, vItem, vTemp As Variant
    Dim strLine, strList, strSource As String
    
    strList = Replace(tbPole.Value, vbLf, "")
    vPrevious = Split(strList, vbCr)
    strList = ""
    For i = 0 To UBound(vPrevious)
        
    Next i
    
    strSource = "??"
    
    
    
    
    
    strLine = Replace(tbCallout.Value, vbLf, "")
    vLine = Split(strLine, vbCr)
    strLine = ""
    For i = 0 To UBound(vLine)
        vItem = Split(vLine(i), ": ")
        
        For j = 0 To UBound(vPrevious)
            vTemp = Split(vPrevious(j), ": ")
            If vTemp(0) = vItem(0) Then
                strSource = vTemp(2)
                GoTo Found_Source
            End If
        Next j
        
Found_Source:
        If strLine = "" Then
            strLine = vItem(0) & ": " & vItem(1) & ": " & strSource
        Else
            strLine = strLine & vbCr & vItem(0) & ": " & vItem(1) & ": " & strSource
        End If
    Next i
    
    tbPole.Value = strLine
End Sub

Private Sub cbGetCallouts_Click()
    Dim objBlock As AcadBlockReference
    Dim filterType, filterValue As Variant
    Dim grpCode(0) As Integer
    Dim grpValue(0) As Variant
    Dim vAtt As Variant
    Dim vResult, vLine, vTemp As Variant
    Dim strPole, strCounts As String
    Dim iPos As Integer
    
    On Error Resume Next
    
    Me.Hide
        
    Err = 0
    vPnt1 = ThisDrawing.Utility.GetPoint(, "Get BL Corner: ")
    vPnt2 = ThisDrawing.Utility.GetCorner(vPnt1, vbCr & "Get UR Corner: ")
    If Not Err = 0 Then GoTo Exit_Sub
    
    lbList.Clear
    objSSPole.Clear
    
    grpCode(0) = 2
    grpValue(0) = "sPole,sPed,sHH,sMH"
    filterType = grpCode
    filterValue = grpValue
    objSSPole.Select acSelectionSetWindow, vPnt1, vPnt2, filterType, filterValue
    
    If objSSPole.count < 1 Then GoTo Skip_This:
    
    For i = 0 To objSSPole.count - 1
        Set objBlock = objSSPole.Item(i)
        
        vAtt = objBlock.GetAttributes
        If vAtt(0).TextString = "POLE" Then GoTo Next_Pole
        If vAtt(0).TextString = "" Then GoTo Next_Pole
        
        strPole = vAtt(0).TextString
        
        Select Case objBlock.Name
            Case "sPole"
                iPos = 25
            Case Else
                iPos = 5
        End Select
        If vAtt(iPos).TextString = "" Then GoTo Next_Pole
        
        vLine = Split(vAtt(iPos).TextString, vbCr)
        For j = 0 To UBound(vLine)
            lbList.AddItem strPole
            lbList.List(lbList.ListCount - 1, 1) = UCase(vAtt(iPos).TextString)
            lbList.List(lbList.ListCount - 1, 2) = "none"
            lbList.List(lbList.ListCount - 1, 3) = ""
            lbList.List(lbList.ListCount - 1, 4) = ""
            lbList.List(lbList.ListCount - 1, 5) = ""
            lbList.List(lbList.ListCount - 1, 6) = ""
            lbList.List(lbList.ListCount - 1, 7) = i
            lbList.List(lbList.ListCount - 1, 8) = vAtt(iPos + 2).TextString
        Next j
        
Next_Pole:
    Next i
    
    Call CheckUnits
    
Skip_This:
    objSS.Clear
    
    grpCode(0) = 2
    grpValue(0) = "Callout"
    filterType = grpCode
    filterValue = grpValue
    objSS.Select acSelectionSetWindow, vPnt1, vPnt2, filterType, filterValue
    
    For i = 0 To objSS.count - 1
        Set objBlock = objSS.Item(i)
        
        vAtt = objBlock.GetAttributes
        If InStr(vAtt(1).TextString, "+HO1") > 0 Then GoTo Next_objBlock
        If vAtt(1).TextString = "CALLOUT" Then GoTo Next_objBlock
        
        vLine = Split(vAtt(0).TextString, ": ")
        For j = 0 To lbList.ListCount - 1
            If lbList.List(j, 0) = vLine(0) Then
                vTemp = Split(lbList(j, 1), ": ")
                If vTemp(0) = vLine(1) Then
                    lbList.List(j, 2) = vLine(1) & ": " & UCase(vAtt(1).TextString) & " / " & UCase(vAtt(2).TextString)
                    strCounts = ConvertToCallout(CStr(lbList.List(j, 1)))
                    If strCounts = lbList.List(j, 2) Then lbList.List(j, 3) = "Y"
                    
                    vResult = ValidateCounts(UCase(vAtt(1).TextString), UCase(vAtt(2).TextString))
                    If vResult(0) = "Y" Then
                        lbList.List(j, 4) = "Y"
                    Else
                        lbList.List(j, 4) = ""
                    End If
                    
                    If vResult(1) = "Y" Then
                        lbList.List(j, 5) = "Y"
                    Else
                        lbList.List(j, 5) = ""
                    End If
                    
                    lbList.List(j, 7) = lbList.List(j, 7) & ";;" & i
                    GoTo Next_objBlock
                End If
            End If
        Next j
Next_objBlock:
    Next i
    
Exit_Sub:
    tbListCount.Value = lbList.ListCount
    Me.show
End Sub

Private Sub cbQuit_Click()
    objSS.Clear
    objSS.Delete
    
    Me.Hide
End Sub

Private Sub cbRemove_Click()
    If lbList.ListCount < 1 Then Exit Sub
    
    For i = lbList.ListCount - 1 To 0 Step -1
        If lbList.List(i, 3) = "Y" Then
            If lbList.List(i, 4) = "Y" Then
                If lbList.List(i, 5) = "Y" Then
                    If lbList.List(i, 6) = "Y" Then
                        lbList.RemoveItem i
                        GoTo Next_I
                    End If
                End If
            End If
        End If
        
        If lbList.List(i, 2) = "none" Then
            If lbList.List(i, 6) = "Y" Then lbList.RemoveItem i
        End If
Next_I:
    Next i
    
    tbListCount.Value = lbList.ListCount
End Sub

Private Sub cbUpdate_Click()
    strStatus = ""
    
    Call UpdatePole
    Call UpdateCallout
    tbUnits.Value = ""
    
    For i = 0 To lbList.ListCount - 1
        lbList.List(i, 6) = ""
    Next i
    Call CheckUnits
    
    If strStatus = "" Then strStatus = "No updates have been made."
    
    MsgBox strStatus
End Sub

Private Sub cbUpdateUnits_Click()
    If tbUnits.Value = "" Then Exit Sub
    
    Dim objSSCO As AcadSelectionSet
    Dim objBlock As AcadBlockReference
    Dim vAttList, vUnits As Variant
    Dim strLayer, strUnits As String
    Dim dInsertPnt(2) As Double
    Dim dScale As Double
    Dim dPosition As Double
    
    On Error Resume Next
    Me.Hide
    
    Set objSSCO = ThisDrawing.SelectionSets.Add("objSSCO")
    If Not Err = 0 Then
        Set objSSCO = ThisDrawing.SelectionSets.Item("objSSCO")
        Err = 0
    End If
    objSSCO.SelectOnScreen
    
    If objSSCO.count < 1 Then GoTo Exit_Sub
    
    dInsertPnt(0) = 0#
    dInsertPnt(1) = 0#
    dInsertPnt(2) = 0#
    
    For Each objBlock In objSSCO
        If objBlock.Name = "pole_unit" Then
            If objBlock.InsertionPoint(1) > dInsertPnt(1) Then
                dInsertPnt(0) = objBlock.InsertionPoint(0)
                dInsertPnt(1) = objBlock.InsertionPoint(1)
                dScale = objBlock.XScaleFactor
            End If
            strLayer = objBlock.Layer
            objBlock.Delete
        End If
    Next objBlock
    
    dPosition = 2#
    
    strUnits = Replace(tbUnits.Value, vbLf, "")
    vUnits = Split(strUnits, vbCr)
    
    For v = 0 To UBound(vUnits)
        strAtt1 = dPosition
        strAtt2 = "N/A"
        strAtt3 = vUnits(v)
    
        Set objBlock = ThisDrawing.ModelSpace.InsertBlock(dInsertPnt, "pole_unit", dScale, dScale, dScale, 0#)
        objBlock.Layer = strLayer
        
        vAttList = objBlock.GetAttributes
        vAttList(0).TextString = strAtt0
        vAttList(1).TextString = strAtt1
        vAttList(2).TextString = strAtt2
        vAttList(3).TextString = strAtt3
        objBlock.Update
    
        dInsertPnt(1) = dInsertPnt(1) - (9 * dScale)
    Next v
    
Exit_Sub:
    objSSCO.Clear
    objSSCO.Delete
    
    Me.show
End Sub

Private Sub CommandButton1_Click()
    Dim vLine, vItem, vTemp As Variant
    Dim vPrevious, vCurrent, vCounts As Variant
    Dim strLine, strName As String
    Dim iPF, iPL, iCF, iCL As Integer
    
    strLine = Replace(tbPole.Value, vbLf, "")
    vLine = Split(strLine, vbCr)
    
    If UBound(vLine) > 0 Then
        For i = UBound(vLine) To 1 Step -1
            vCurrent = Split(vLine(i), ": ")
            vPrevious = Split(vLine(i - 1), ": ")
            
            If vCurrent(0) = vPrevious(0) Then
                If vCurrent(2) = vPrevious(2) Then
                    vCounts = Split(vCurrent(1), "-")
                    iCF = CInt(vCounts(0))
                    If UBound(vCounts) > 0 Then
                        iCL = CInt(vCounts(1))
                    Else
                        iCL = iCF
                    End If
                    
                    vCounts = Split(vPrevious(1), "-")
                    iPF = CInt(vCounts(0))
                    If UBound(vCounts) > 0 Then
                        iPL = CInt(vCounts(1))
                    Else
                        iPL = iPF
                    End If
                    
                    If iCF = iPL + 1 Then
                        iPL = iCL
                        strLine = vPrevious(0) & ": " & iPF & "-" & iPL & ": " & vPrevious(2)
                        
                        vLine(i - 1) = strLine
                        vLine(i) = ""
                    End If
                End If
            End If
        Next i
        
        strLine = ""
        For i = 0 To UBound(vLine)
            If Not vLine(i) = "" Then
                If strLine = "" Then
                    strLine = vLine(i)
                Else
                    strLine = strLine & vbCr & vLine(i)
                End If
            End If
        Next i
        
        tbPole.Value = strLine
    End If
End Sub

Private Sub LabelPan_Click()
    Dim entPole As AcadObject
    Dim basePnt As Variant
    
    Me.Hide
  On Error Resume Next
    
    ThisDrawing.Utility.GetEntity entPole, basePnt, "Left Click to Exit: "
    
    Me.show
End Sub

Private Sub lbList_DblClick(ByVal Cancel As MSForms.ReturnBoolean)
    Dim objBlock As AcadBlockReference
    Dim vLine As Variant
    Dim strText As String
    Dim viewCoordsB(0 To 2) As Double
    Dim viewCoordsE(0 To 2) As Double
    
    iIndex = lbList.ListIndex
    
    vLine = Split(lbList.List(iIndex, 7), ";;")
    iPole = CInt(vLine(0))
    If UBound(vLine) > 0 Then
        iCallout = CInt(vLine(1))
    Else
        iCallout = -1
    End If
    cbUpdate.Enabled = True
    'cbUpdatePole.Enabled = True
    
    Me.Hide
    
    Set objBlock = objSSPole.Item(iPole)
    viewCoordsB(0) = objBlock.InsertionPoint(0) - 300
    viewCoordsB(1) = objBlock.InsertionPoint(1) - 300
    viewCoordsB(2) = 0#
    viewCoordsE(0) = viewCoordsB(0) + 600
    viewCoordsE(1) = viewCoordsB(1) + 600
    viewCoordsE(2) = 0#
    ThisDrawing.Application.ZoomWindow viewCoordsB, viewCoordsE
    
    vLine = Split(UCase(lbList.List(lbList.ListIndex, 1)), " / ")
    
    tbPoleCable.Value = vLine(0)
    strText = Replace(vLine(1), " + ", vbCr)
    tbPole.Value = strText
    
    If lbList.List(iIndex, 2) = "" Then Exit Sub
    If lbList.List(iIndex, 2) = "none" Then GoTo Skip_Callout
    
    vLine = Split(UCase(lbList.List(iIndex, 2)), " / ")
    
    tbCable.Value = vLine(0)
    strText = Replace(vLine(1), "\P", vbCr)
    tbCallout.Value = strText
    
Skip_Callout:
    strText = Replace(lbList.List(iIndex, 8), ";;", vbCr)
    If strText = "" Then
        tbUnits.Value = ""
    Else
        tbUnits.Value = strText
    End If
    
    Me.show
End Sub

Private Sub UserForm_Initialize()
    lbList.ColumnCount = 9
    lbList.ColumnWidths = "120;120;120;36;36;36;36;18;6"
    
    iIndex = -1
    
    On Error Resume Next
    
    Set objSSPole = ThisDrawing.SelectionSets.Add("objSSPole")
    If Not Err = 0 Then
        Set objSSPole = ThisDrawing.SelectionSets.Item("objSSPole")
    End If
    
    Set objSS = ThisDrawing.SelectionSets.Add("objSS")
    If Not Err = 0 Then
        Set objSS = ThisDrawing.SelectionSets.Item("objSS")
    End If
End Sub

Private Function ValidateCounts(strCable As String, strCallout As String)
    Dim strResult, strColor As String
    Dim vResult As Variant
    Dim vLine, vItem, vCount, vTemp As Variant
    
    Dim iCable, iCount, iTCount As Integer
    Dim iLow, iHigh As Integer
    
    vLine = Split(strCable, "(")
    vItem = Split(vLine(1), ")")
    iCable = CInt(vItem(0))
    iCount = 0
    strColor = "Y"
    
    vLine = Split(strCallout, "\P")
    For i = 0 To UBound(vLine)
        vItem = Split(vLine(i), ": ")
        vCount = Split(vItem(UBound(vItem)), "-")
        
        iTCount = iCount + 1
        While iTCount > 12
            iTCount = iTCount - 12
        Wend
        
        iLow = CInt(vCount(0))
        While iLow > 12
            iLow = iLow - 12
        Wend
        
        If Not iLow = iTCount Then strColor = "N"
        
        If UBound(vCount) = 0 Then
            iCount = iCount + 1
        Else
            iCount = iCount + CInt(vCount(1)) - CInt(vCount(0)) + 1
        End If
    Next i
    
    If iCount = iCable Then
        strResult = "Y"
    Else
        strResult = "N"
    End If
    
    'MsgBox strCable & vbCr & vbCr & strCallout
    
    strResult = strResult & "," & strColor
    vResult = Split(strResult, ",")
    
    ValidateCounts = vResult
End Function

Private Sub UpdatePole()
    If iPole < 0 Then GoTo Exit_Sub
    
    Dim objBlock As AcadBlockReference
    Dim vAtt, vLine As Variant
    Dim strText, strUnits As String
    Dim i, iPos As Integer
    
    strText = Replace(UCase(tbPole.Value), vbLf, "")
    strText = tbPoleCable.Value & " / " & Replace(strText, vbCr, " + ")
    
    strUnits = Replace(tbUnits.Value, vbLf, "")
    strUnits = Replace(strUnits, vbCr, ";;")
    
    lbList.List(iIndex, 1) = strText
    If Not strUnits = "" Then lbList.List(iIndex, 8) = strUnits
    
    Set objBlock = objSSPole.Item(iPole)
    vAtt = objBlock.GetAttributes
    Select Case objBlock.Name
        Case "sPole"
            iPos = 25
        Case Else
            iPos = 5
    End Select
    
    vAtt(iPos).TextString = strText
    vAtt(iPos + 2).TextString = strUnits
    
    objBlock.Update
    
    strStatus = "Pole"
    
Exit_Sub:
    tbPoleCable.Value = ""
    tbPole.Value = ""
    tbUnits.Value = ""
    
    iPole = -1
End Sub

Private Sub UpdateCallout()
    If iCallout < 0 Then GoTo Exit_Sub
    If tbCallout.Value = "" Then GoTo Exit_Sub
    
    Dim objBlock As AcadBlockReference
    Dim vAtt, vLine As Variant
    Dim strText As String
    Dim i As Integer
    
    strText = Replace(UCase(tbCallout.Value), vbLf, "")
    strText = Replace(strText, vbCr, "\P")
    
    lbList.List(iIndex, 2) = UCase(tbCable.Value) & " / " & strText
    
    vLine = Split(lbList.List(iIndex, 7), ";;")
    i = CInt(vLine(1))
    Set objBlock = objSS.Item(i)
    vAtt = objBlock.GetAttributes
    
    vLine = Split(UCase(tbCable.Value), ": ")
    tbCable.Value = vLine(1)
    vAtt(1).TextString = tbCable.Value
    vAtt(2).TextString = strText
    
    objBlock.Update
        
    vResult = ValidateCounts(tbCable.Value, strText)
    If vResult(0) = "Y" Then lbList.List(iIndex, 3) = "Y"
    If vResult(1) = "Y" Then lbList.List(iIndex, 4) = "Y"
    
    If strStatus = "" Then
        strStatus = "Callout has been updated."
    Else
        strStatus = strStatus & " and Callout have been updated."
    End If
    
Exit_Sub:
    tbCable.Value = ""
    tbCallout.Value = ""
    
    iCallout = -1
    cbUpdate.Enabled = False
End Sub

Private Function ConvertToCallout(strText As String)
    Dim vLine, vItem, vTemp As Variant
    Dim strLine As String
    
    vLine = Split(strText, " / ")
    vItem = Split(vLine(1), " + ")
    
    For i = 0 To UBound(vItem)
        vTemp = Split(vItem(i), ": ")
        vItem(i) = vTemp(0) & ": " & vTemp(1)
    Next i
    
    strLine = ""
    
    For i = 0 To UBound(vItem)
        If strLine = "" Then
            strLine = vItem(i)
        Else
            strLine = strLine & "\P" & vItem(i)
        End If
    Next i
    
    strLine = vLine(0) & " / " & strLine
    ConvertToCallout = strLine
End Function

Private Sub CheckUnits()
    If lbList.ListCount < 1 Then Exit Sub
    
    Dim vUnit, vLine, vItem, vTemp As Variant
    Dim strCable As String
    
    For i = 0 To lbList.ListCount - 1
        If lbList.List(i, 8) = "" Then GoTo Next_I
        
        vLine = Split(lbList.List(i, 1), " / ")
        vItem = Split(vLine(0), ": ")
        strCable = vItem(1)
        
        vUnit = Split(lbList.List(i, 8), ";;")
        For j = 0 To UBound(vUnit)
            If InStr(vUnit(j), strCable) > 0 Then
                If InStr(vUnit(j), "LOOP") = 0 Then
                    lbList.List(i, 6) = "Y"
                End If
            End If
        Next j
        
Next_I:
    Next i
End Sub

Attribute VB_Name = "ValidateCustomers"
Attribute VB_Base = "0{FA339090-D222-4BE4-9BC5-EF52FDE58E70}{D87D3457-E0A0-4E48-AFC2-DCD5D5148A25}"
Attribute VB_GlobalNameSpace = False
Attribute VB_Creatable = False
Attribute VB_PredeclaredId = True
Attribute VB_Exposed = False
Attribute VB_TemplateDerived = False
Attribute VB_Customizable = False
Private Sub cbFilter_Click()
    If cbCounts.Value = "" Then Exit Sub
    
    For i = lbCustomers.ListCount - 1 To 0 Step -1
        If Not lbCustomers.List(i, 0) = cbCounts.Value Then lbCustomers.RemoveItem i
    Next i
    
    tbCount.Value = lbCustomers.ListCount
    cbFilter.Enabled = False
    cbCounts.Enabled = False
End Sub

Private Sub cbGetCustomers_Click()
    Dim vDwgLL, vDwgUR As Variant
    Dim filterType, filterValue As Variant
    Dim grpCode(0) As Integer
    Dim grpValue(0) As Variant
    Dim objSS As AcadSelectionSet
    Dim objBlock As AcadBlockReference
    Dim vAttList As Variant
    Dim vLine, vTemp As Variant
    Dim iCount, iIndex, iTest As Integer
    Dim vCoords As Variant
    Dim strCoords As String
    
    On Error Resume Next
    
    lbCustomers.Clear
    cbCounts.Clear
    
    iCount = 0
    iIndex = 0
    iTest = 0
    
    Err = 0
    Me.Hide
    
    vDwgLL = ThisDrawing.Utility.GetPoint(, "Get DWG LL Corner: ")
    vDwgUR = ThisDrawing.Utility.GetCorner(vDwgLL, vbCr & "Get DWG UR Corner: ")
    
    If Not Err = 0 Then
        Me.show
        Exit Sub
    End If
    
    grpCode(0) = 2
    grpValue(0) = "Customer"
    filterType = grpCode
    filterValue = grpValue
    
    Set objSS = ThisDrawing.SelectionSets.Add("objSS")
    If Not Err = 0 Then
        Set objSS = ThisDrawing.SelectionSets.Item("objSS")
        objSS.Clear
        Err = 0
    End If
    
    objSS.Select acSelectionSetWindow, vDwgLL, vDwgUR, filterType, filterValue
    
    iCount = objSS.count
    
    For Each objBlock In objSS
        'Set objBlock = objSS.Item(i)
        vAttList = objBlock.GetAttributes
        
        If vAttList(0).TextString = "" Then GoTo Next_objBlock
        If vAttList(1).TextString = "Customer" Then GoTo Next_objBlock
        
        If vAttList(4).TextString = "" Then
            vLine = Split("none - none: none", " - ")
        Else
            vLine = Split(vAttList(4).TextString, " - ")
        End If
        
        vLine(1) = Replace(vLine(1), "(", "")
        vLine(1) = Replace(vLine(1), ")", "")
        vTemp = Split(vLine(1), ": ")
        
        vCoords = objBlock.InsertionPoint
        strCoords = vCoords(0) & "," & vCoords(1)
        
        lbCustomers.AddItem vTemp(0)
        lbCustomers.List(iIndex, 1) = vTemp(1)
        lbCustomers.List(iIndex, 2) = vLine(0)
        lbCustomers.List(iIndex, 3) = vAttList(1).TextString
        lbCustomers.List(iIndex, 4) = vAttList(2).TextString
        lbCustomers.List(iIndex, 5) = vAttList(0).TextString
        lbCustomers.List(iIndex, 6) = vAttList(3).TextString
        lbCustomers.List(iIndex, 7) = ""
        lbCustomers.List(iIndex, 8) = strCoords
        
        If cbCounts.ListCount < 1 Then
            cbCounts.AddItem vTemp(0)
        Else
            For i = 0 To cbCounts.ListCount - 1
                If cbCounts.List(i) = vTemp(0) Then GoTo Found_Count
            Next i
        
            cbCounts.AddItem vTemp(0)
        End If
        
Found_Count:
        
        iIndex = iIndex + 1
        
Next_objBlock:
    Next objBlock
    
    objSS.Clear
    objSS.Delete
    
    tbCount.Value = lbCustomers.ListCount
    cbFilter.Enabled = True
    cbCounts.Enabled = True
    
    Me.show
End Sub

Private Sub cbQuit_Click()
    Me.Hide
End Sub

Private Sub cbRemoveExtensions_Click()
    For i = lbCustomers.ListCount - 1 To 0 Step -1
        If lbCustomers.List(i, 5) = "EXTENSION" Then lbCustomers.RemoveItem i
    Next i
    
    tbCount.Value = lbCustomers.ListCount
End Sub

Private Sub cbRemoveRef_Click()
    For i = lbCustomers.ListCount - 1 To 0 Step -1
        If InStr(lbCustomers.List(i, 5), "REF") > 0 Then lbCustomers.RemoveItem i
    Next i
    
    tbCount.Value = lbCustomers.ListCount
End Sub

Private Sub cbSave_Click()
    If lbCustomers.ListCount = 0 Then Exit Sub
    
    Dim strFileName As String
    Dim strDWGName As String
    Dim vLine As Variant
    Dim strCopy, strLine As String
    
    
    strCopy = "CABLE NAME,COUNT,POLE NUMBER,HSE #,STREET NAME,TYPE,NOTE"
    
    For i = 0 To lbCustomers.ListCount - 1
        strLine = lbCustomers.List(i, 0) & "," & lbCustomers.List(i, 1) & "," & lbCustomers.List(i, 2)
        strLine = strLine & "," & lbCustomers.List(i, 3) & "," & lbCustomers.List(i, 4) & "," & lbCustomers.List(i, 5)
        strLine = strLine & "," & lbCustomers.List(i, 6)
        
        strCopy = strCopy & vbCr & strLine
    Next i
    
    strFileName = ThisDrawing.Path & "\"
    vLine = Split(ThisDrawing.Name, " ")
    strFileName = strFileName & vLine(0) & "-Customer List "
    
    Select Case cbCounts.Value
        Case ""
            strFileName = strFileName & "ALL"
        Case Else
            strFileName = strFileName & cbCounts.Value
    End Select
    
    strFileName = strFileName & ".csv"

    Open strFileName For Output As #1
        
    Print #1, strCopy
    Close #1
    
    MsgBox "Saved to File"
End Sub

Private Sub cbSort_Click()
    Dim strTemp, strTotal As String
    Dim iCount, iOffset As Integer
    Dim iIndex As Integer
    Dim strAtt(0 To 8) As String
    
    iCount = lbCustomers.ListCount - 1
    If iCount < 1 Then Exit Sub
    
    On Error Resume Next
    
    For a = iCount To 0 Step -1
        For b = 0 To a - 1
            If CInt(lbCustomers.List(b, 1)) > CInt(lbCustomers.List(b + 1, 1)) Then
                If Not Err = 0 Then
                    MsgBox "Error sorting list"
                    lbCustomers.Selected(b) = True
                    lbCustomers.ListIndex = b
                    Exit Sub
                End If
                
                strAtt(0) = lbCustomers.List(b + 1, 0)
                strAtt(1) = lbCustomers.List(b + 1, 1)
                strAtt(2) = lbCustomers.List(b + 1, 2)
                strAtt(3) = lbCustomers.List(b + 1, 3)
                strAtt(4) = lbCustomers.List(b + 1, 4)
                strAtt(5) = lbCustomers.List(b + 1, 5)
                strAtt(6) = lbCustomers.List(b + 1, 6)
                strAtt(7) = lbCustomers.List(b + 1, 7)
                strAtt(8) = lbCustomers.List(b + 1, 8)
                
                lbCustomers.List(b + 1, 0) = lbCustomers.List(b, 0)
                lbCustomers.List(b + 1, 1) = lbCustomers.List(b, 1)
                lbCustomers.List(b + 1, 2) = lbCustomers.List(b, 2)
                lbCustomers.List(b + 1, 3) = lbCustomers.List(b, 3)
                lbCustomers.List(b + 1, 4) = lbCustomers.List(b, 4)
                lbCustomers.List(b + 1, 5) = lbCustomers.List(b, 5)
                lbCustomers.List(b + 1, 6) = lbCustomers.List(b, 6)
                lbCustomers.List(b + 1, 7) = lbCustomers.List(b, 7)
                lbCustomers.List(b + 1, 8) = lbCustomers.List(b, 8)
                
                lbCustomers.List(b, 0) = strAtt(0)
                lbCustomers.List(b, 1) = strAtt(1)
                lbCustomers.List(b, 2) = strAtt(2)
                lbCustomers.List(b, 3) = strAtt(3)
                lbCustomers.List(b, 4) = strAtt(4)
                lbCustomers.List(b, 5) = strAtt(5)
                lbCustomers.List(b, 6) = strAtt(6)
                lbCustomers.List(b, 7) = strAtt(7)
                lbCustomers.List(b, 8) = strAtt(8)
            End If
        Next b
    Next a
End Sub

Private Sub lbCustomers_DblClick(ByVal Cancel As MSForms.ReturnBoolean)
    Dim objEntity As AcadEntity
    Dim vCoords, vReturnPnt As Variant
    Dim viewCoordsB(0 To 2) As Double
    Dim viewCoordsE(0 To 2) As Double
    Dim iIndex As Integer
    
    Me.Hide
    
    On Error Resume Next
    
    iIndex = lbCustomers.ListIndex
    
    vCoords = Split(lbCustomers.List(iIndex, 8), ",")
    
    viewCoordsB(0) = vCoords(0) - 300
    viewCoordsB(1) = vCoords(1) - 300
    viewCoordsB(2) = 0#
    viewCoordsE(0) = vCoords(0) + 300
    viewCoordsE(1) = vCoords(1) + 300
    viewCoordsE(2) = 0#
    
    ThisDrawing.Application.ZoomWindow viewCoordsB, viewCoordsE
    
    ThisDrawing.Utility.GetEntity objEntity, vReturnPnt, vbCr & "Any Key or Right Click to Exit:"
    
    Me.show
End Sub

Private Sub UserForm_Initialize()
    lbCustomers.Clear
    lbCustomers.ColumnCount = 9
    lbCustomers.ColumnWidths = "72;30;66;36;136;48;114;24;12"
    
    MsgBox "Please let me lnow if you are using this." & vbCr & "Trying to eliminate Forms we may not need."
End Sub

Attribute VB_Name = "ValidateFielding"
Attribute VB_Base = "0{43218EE5-39EF-45AF-A405-03FB6DE8749B}{09DF3393-9600-47D8-B1AF-47C10F884BA0}"
Attribute VB_GlobalNameSpace = False
Attribute VB_Creatable = False
Attribute VB_PredeclaredId = True
Attribute VB_Exposed = False
Attribute VB_TemplateDerived = False
Attribute VB_Customizable = False
Dim iConverted As Integer

Private Sub cbCheck_Click()
    cbPole.Value = True
    cbLL.Value = True
    cbGuys.Value = True
    cbBldgs.Value = True
    cbTrim.Value = True
    cbMM.Value = True
    cbNotes.Value = True
    cbBores.Value = True
End Sub

Private Sub cbLL_Click()
    If cbLL.Value = True Then cbPole.Value = True
End Sub

Private Sub cbUncheck_Click()
    cbPole.Value = False
    cbLL.Value = False
    cbGuys.Value = False
    cbBldgs.Value = False
    cbTrim.Value = False
    cbMM.Value = False
    cbNotes.Value = False
    cbBores.Value = False
End Sub

Private Sub cbValidate_Click()
    Dim objSS As AcadSelectionSet
    Dim objEntity As AcadEntity
    Dim objBlock As AcadBlockReference
    Dim filterType, filterValue As Variant
    Dim grpCode(0) As Integer
    Dim grpValue(0) As Variant
    Dim vAttList As Variant
    Dim strLine, strTemp As String
    Dim objOutlook As Outlook.Application
    Dim objMail As Outlook.MailItem
    Dim strTo, strSubject, strBody As String
        
    If cbPole.Value = True Then Call ValidatePoles
    
    If cbGuys.Value = True Then Call ValidateGuys
    
    If cbBldgs.Value = True Then Call ValidateBldgs
    
    If cbTrim.Value = True Then Call ValidateTrim
    
    If cbNotes.Value = True Then Call ValidateNotes
    
    If cbBores.Value = True Then Call CircleBores

    grpCode(0) = 2
    grpValue(0) = "Development"
    filterType = grpCode
    filterValue = grpValue
        
    On Error Resume Next
    Err = 0
        
    Set objSS = ThisDrawing.SelectionSets.Add("objSS")
    If Not Err = 0 Then
        Set objSS = ThisDrawing.SelectionSets.Item("objSS")
    End If
    
GoTo Skip_This
        
    objSS.Select acSelectionSetAll, , , filterType, filterValue
    strLine = ""
        
    For Each objBlock In objSS
        vAttList = objBlock.GetAttributes
        If Not vAttList(0).TextString = "" Then GoTo Next_objBlock
        If vAttList(1).TextString = "" Then GoTo Next_objBlock
        
        If strLine = "" Then
            strLine = vAttList(1).TextString & vbCr
        Else
            strLine = strLine & vbCr & vbCr & vAttList(1).TextString & vbCr
        End If
        
        If Not vAttList(2).TextString = "" Then strLine = strLine & "  Phase: " & vAttList(2).TextString
        If Not vAttList(3).TextString = "" Then strLine = strLine & "  Sec: " & vAttList(3).TextString
        If Not Right(strLine, 1) = vbCr Then strLine = strLine & vbCr
        
        Select Case UCase(vAttList(4).TextString)
            Case "AB"
                strLine = strLine & "APARTMENT BUILDING"
            Case "AC"
                strLine = strLine & "APARTMENT COMPLEX"
            Case "BP"
                strLine = strLine & "BUSINESS PARK"
            Case "C"
                strLine = strLine & "CONDOS"
            Case "IP"
                strLine = strLine & "INDUSTIAL PARK"
            Case "SD"
                strLine = strLine & "SUBDIVISION"
            Case "SM"
                strLine = strLine & "STRIP MALL"
            Case "TH"
                strLine = strLine & "TOWNHOMES"
            Case "TP"
                strLine = strLine & "TRAILER PARK"
            Case Else
                strLine = strLine & UCase(vAttList(4).TextString)
        End Select
        
        If Not vAttList(5).TextString = "" Then strLine = strLine & " Location:" & vbTab & vAttList(5).TextString
Next_objBlock:
    Next objBlock
    
    If Not strLine = "" Then
        strSubject = "New Development(s) found while fielding " & Replace(UCase(ThisDrawing.Name), ".DWG", "")
        'strTo = "jon.wilburn@integrity-us.com"
        strTo = "rich.taylor@integrity-us.com"
        
        strBody = Replace(UCase(strLine), vbCr, "<br>")
        strBody = Replace(UCase(strBody), vbTab, "&nbsp;&nbsp;&nbsp;&nbsp;")
        strBody = Replace(strBody, vbCr, "<br>")
        
        Set objOutlook = New Outlook.Application
        Set objMail = objOutlook.CreateItem(olMailItem)
    
        objMail.To = strTo
        objMail.Subject = strSubject
        objMail.HTMLBody = strBody
    
        objMail.Send
        
        strLine = "Email sent to Jon about new developments:" & vbCr & vbCr & strLine
        MsgBox strLine
    End If
    
Skip_This:
    
    grpValue(0) = "Planning Note"
    filterType = grpCode
    filterValue = grpValue
    Err = 0
    
    objSS.Clear
    objSS.Select acSelectionSetAll, , , filterType, filterValue
    strLine = ""
        
    For Each objBlock In objSS
        vAttList = objBlock.GetAttributes
        If vAttList(0).TextString = "" Then GoTo Next_Note
        If vAttList(0).TextString = "None" Then GoTo Next_Note
        
        If strLine = "" Then
            strLine = UCase(vAttList(0).TextString)
        Else
            strLine = strLine & vbCr & vbCr & UCase(vAttList(0).TextString)
        End If
        
        If Not vAttList(1).TextString = "" Then strLine = strLine & "  AT  " & UCase(vAttList(1).TextString)
        If Not vAttList(2).TextString = "" Then strLine = strLine & vbCr & " Note(s):  " & UCase(vAttList(2).TextString)
        strLine = strLine & vbCr & "TN83F:" & vbTab & objBlock.InsertionPoint(1) & "," & objBlock.InsertionPoint(0)
Next_Note:
    Next objBlock
    
    If Not strLine = "" Then
        strSubject = "Fielding Notes for Planning " & Replace(UCase(ThisDrawing.Name), ".DWG", "")
        'strTo = "jon.wilburn@integrity-us.com;adam.kemper@integrity-us.com"
        strTo = "rich.taylor@integrity-us.com"
        
        strBody = Replace(UCase(strLine), vbCr, "<br>")
        strBody = Replace(UCase(strBody), vbTab, "&nbsp;&nbsp;&nbsp;&nbsp;")
        strBody = Replace(strBody, vbCr, "<br>")
        
        Set objOutlook = New Outlook.Application
        Set objMail = objOutlook.CreateItem(olMailItem)
    
        objMail.To = strTo
        objMail.Subject = strSubject
        objMail.HTMLBody = strBody
    
        objMail.Send
        
        strLine = "Email sent to Planning with Fielders' Notes:" & vbCr & vbCr & strLine
        MsgBox strLine
    End If
    
    If cbMM.Value = True Then
        grpCode(0) = 2
        grpValue(0) = "mile marker,mile interstate"
        filterType = grpCode
        filterValue = grpValue
        
        objSS.Select acSelectionSetAll, , , filterType, filterValue
        
        For Each objEntity In objSS
            objEntity.Layer = "Integrity Notes"
        Next objEntity
    End If
    
    objSS.Clear
    objSS.Delete
    
    Me.Hide
    
End Sub

Private Sub cbQuit_Click()
    Me.Hide
End Sub

Private Sub ValidatePoles()
    Dim objSS As AcadSelectionSet
    Dim objPointBlock As AcadBlockReference
    Dim objNewBlock As AcadBlockReference
    Dim objEntity As AcadEntity
    Dim filterType, filterValue As Variant
    Dim grpCode(0) As Integer
    Dim grpValue(0) As Variant
    Dim vAttOld, vTemp, vLine As Variant
    Dim dScale As Double
    Dim iCount As Integer
    Dim strLine, strTemp As String
    Dim dN, dE As Double
    Dim vLL As Variant
    
    On Error Resume Next
    
    'dScale = 0.75
    dScale = CDbl(cbScale.Value) / 100
    iCount = 0

    grpCode(0) = 2
    grpValue(0) = "sPole"
    filterType = grpCode
    filterValue = grpValue
    
    Err = 0
    Set objSS = ThisDrawing.SelectionSets.Add("objSS")
    If Not Err = 0 Then
        Set objSS = ThisDrawing.SelectionSets.Item("objSS")
        Err = 0
    End If
    
    objSS.Select acSelectionSetAll, , , filterType, filterValue
    If Not Err = 0 Then GoTo Exit_Sub
        
    For Each objEntity In objSS
        Set objPointBlock = objEntity
        vAttOld = objPointBlock.GetAttributes
        
        dE = objPointBlock.InsertionPoint(0)
        dN = objPointBlock.InsertionPoint(1)
        vLL = TN83FtoLL(CDbl(dN), CDbl(dE))
          
        For i = 0 To UBound(vAttOld)
            Select Case i
                Case 2
                    vAttOld(2).TextString = UCase(vAttOld(2).TextString)
                    Select Case vAttOld(2).TextString
                        Case "MTEMC", "LUS", "DREMC", "NES", "SPWS", "DRE", "MTE", "MED"
                            objPointBlock.Layer = "Integrity Poles-Power"
                        Case Else
                            objPointBlock.Layer = "Integrity Poles-Other"
                    End Select
                Case 3
                    If InStr(vAttOld(3).TextString, "=") > 0 Then
                        vTemp = Split(vAttOld(3).TextString, "=")
                        vAttOld(3).TextString = vTemp(1)
                    End If
                Case 4
                    If Not vAttOld(4).TextString = "" Then
                        strTemp = Replace(vAttOld(4).TextString, " 1/2", ".5")
                        strTemp = Replace(strTemp, " 1/4", ".25")
                        
                        vLine = Split(strTemp, " ")
                        For n = 0 To UBound(vLine)
                            If vLine(n) = "NA" Then
                                vLine(n) = ""
                            Else
                                If InStr(vLine(n), "=") = 0 Then vLine(n) = "??=" & vLine(n)
                            End If
                        Next n
                        
                        strLine = ""
                        
                        For n = 0 To UBound(vLine)
                            If Not vLine(n) = "" Then
                                If strLine = "" Then
                                    strLine = vLine(n)
                                Else
                                    strLine = strLine & " " & vLine(n)
                                End If
                            End If
                        Next n
                        
                        vAttOld(4).TextString = strLine
                    End If
                Case 5
                    vAttOld(5).TextString = Replace(vAttOld(5).TextString, " ", "")
                Case 7
                    If cbLL.Value = True Then vAttOld(7).TextString = vLL(0) & "," & vLL(1)
                Case 8
                    Select Case UCase(vAttOld(8).TextString)
                        Case "M"
                            vAttOld(8).TextString = "MGNV"
                        Case "T"
                            vAttOld(8).TextString = "TGB"
                        Case "B"
                            vAttOld(8).TextString = "BROKEN GRD"
                        Case Else
                            vAttOld(8).TextString = "NO GRD"
                    End Select
                Case 9 To 26
                    strLine = Replace(vAttOld(i).TextString, "  ", " ")
                    strLine = Replace(strLine, "= ", "=")
                    
                    If Right(strLine, 1) = " " Then
                        strLine = Left(strLine, Len(strLine) - 1)
                    End If
                    If Left(strLine, 1) = " " Then
                        strLine = Right(strLine, Len(strLine) - 1)
                    End If
                    'If InStr(strLine, "LEVEL 3") > 0 Then strLine = Replace(strLine, "LEVEL 3", "LEVEL_3")
                    vAttOld(i).TextString = strLine
            End Select
        Next i
        
        If Not vAttOld(15).TextString = "" Then
            strLine = Replace(vAttOld(15).TextString, "UTC ", "")
            vTemp = Split(strLine, " ")
            If Not Left(vTemp(0), 1) = "T" Then strLine = vTemp(0) & "T"
            If UBound(vTemp) > 0 Then
                For i = 1 To UBound(vTemp)
                    strLine = strLine & " " & vTemp(i)
                    If Not Left(vTemp(i), 1) = "T" Then strTemp = strTemp & "T"
                Next i
            End If
            vAttOld(15).TextString = strLine
        End If
        
        objPointBlock.Update
Next_objEntity:
    Next objEntity
    
Exit_Sub:
    objSS.Clear
    objSS.Delete
End Sub

Private Sub ValidateGuys()
    ValidateGuyType ("ExGuyOL")
    ValidateGuyType ("ExGuyOR")
    ValidateGuyType ("ExAncOL")
    ValidateGuyType ("ExAncOR")
End Sub

Private Sub ValidateGuyType(strName As String)
    Dim objSS5 As AcadSelectionSet
    Dim objPointBlock As AcadBlockReference
    Dim objNewBlock As AcadBlockReference
    Dim objEntity As AcadEntity
    Dim filterType, filterValue As Variant
    Dim grpCode(0) As Integer
    Dim grpValue(0) As Variant
    Dim vAttOld As Variant
    Dim dScale As Double
    Dim iCount As Integer
    
    On Error Resume Next
    
    'dScale = 0.75
    dScale = CDbl(cbScale.Value) / 100
    iCount = 0

    grpCode(0) = 2
    grpValue(0) = strName
    filterType = grpCode
    filterValue = grpValue
    
    Err = 0
    Set objSS5 = ThisDrawing.SelectionSets.Add("objSS5")
    objSS5.Select acSelectionSetAll, , , filterType, filterValue
    If Not Err = 0 Then GoTo Exit_Sub
        
    For Each objEntity In objSS5
        Set objPointBlock = objEntity
        vAttOld = objPointBlock.GetAttributes
                
        Select Case strName
            Case "ExGuyOL", "ExGuyOR"
                If UBound(vAttOld) = 2 Then
                    vAttOld(2).TextString = "PE1-3G"
                Else
                    vAttOld(3).TextString = "PE1-3G"
                End If
            Case "ExAncOL", "ExAncOR"
                vAttOld(0).TextString = "PF1-5A"
        End Select
        objPointBlock.Update
Next_objEntity:
    Next objEntity
    
Exit_Sub:
    objSS5.Clear
    objSS5.Delete
End Sub

Private Sub ValidateBldgs()
    'ValidateBldgType ("Integrity Building-BUS")
    'ValidateBldgType ("Integrity Building-RES")
    'ValidateBldgType ("Integrity Building-TRL")
    'ValidateBldgType ("Integrity Building-MDU")
    'ValidateBldgType ("Integrity Building-SCH")
    'ValidateBldgType ("Integrity Building-CHU")
    'ValidateBldgType ("Integrity Building Misc")
    
    Dim filterType, filterValue As Variant
    Dim grpCode(0) As Integer
    Dim grpValue(0) As Variant
    Dim objSS As AcadSelectionSet
    Dim objBlock As AcadBlockReference
    Dim vAttList As Variant
    Dim iCount As Integer
    
    On Error Resume Next
    
    iCount = 0
    
    grpCode(0) = 2
    grpValue(0) = "Customer"
    filterType = grpCode
    filterValue = grpValue
    
    Err = 0
    Set objSS = ThisDrawing.SelectionSets.Add("objSS")
    If Not Err = 0 Then
        Set objSS = ThisDrawing.SelectionSets.Item("objSS")
        objSS.Clear
    End If
    
    objSS.Select acSelectionSetAll, , , filterType, filterValue
    MsgBox "Found:  " & objSS.count
    
    For Each objBlock In objSS
        vAttList = objBlock.GetAttributes
        
        vAttList(5).TextString = UCase(vAttList(5).TextString)
        
        Select Case vAttList(5).TextString
            Case "", "R"
                If Not vAttList(0).TextString = "RESIDENCE" Then
                    vAttList(0).TextString = "RESIDENCE"
                    iCount = iCount + 1
                End If
            Case "B"
                If Not vAttList(0).TextString = "BUSINESS" Then
                    vAttList(0).TextString = "BUSINESS"
                    iCount = iCount + 1
                End If
            Case "C"
                If Not vAttList(0).TextString = "CHURCH" Then
                    vAttList(0).TextString = "CHURCH"
                    iCount = iCount + 1
                End If
            Case "M"
                If Not vAttList(0).TextString = "MDU" Then
                    vAttList(0).TextString = "MDU"
                    iCount = iCount + 1
                End If
            Case "S"
                If Not vAttList(0).TextString = "SCHOOL" Then
                    vAttList(0).TextString = "SCHOOL"
                    iCount = iCount + 1
                End If
            Case "T"
                If Not vAttList(0).TextString = "TRAILER" Then
                    vAttList(0).TextString = "TRAILER"
                    iCount = iCount + 1
                End If
            Case "X"
                If Not vAttList(0).TextString = "EXTENSION" Then
                    vAttList(0).TextString = "EXTENSION"
                    iCount = iCount + 1
                End If
        End Select
        
        objBlock.Update
        
Next_objBlock:
    Next objBlock
    
    MsgBox "Converted  " & iCount & "  customers"
End Sub

Private Sub ValidateTrim()
    Dim objSS3 As AcadSelectionSet
    Dim objTrim As AcadBlockReference
    Dim attList As Variant
    Dim filterType, filterValue As Variant
    Dim grpCode(0) As Integer
    Dim grpValue(0) As Variant
    Dim entBlock As AcadEntity
    Dim iCount As Integer
    
    'Me.Hide
    iCount = 0
    
    grpCode(0) = 2
    grpValue(0) = "__Trim"
    filterType = grpCode
    filterValue = grpValue
    
    Set objSS3 = ThisDrawing.SelectionSets.Add("objSS3")
    objSS3.Select acSelectionSetAll, , , filterType, filterValue
    
    For Each objTrim In objSS3
        'If Not entBlock.ObjectName = "AcDbBlockReference" Then GoTo Next_entBlock
        'Set objTrim = entBlock
        'If Not objTrim.Name = "__Trim" Then GoTo Next_entBlock
        
        attList = objTrim.GetAttributes
        attList(0).TextString = "T.T=" & attList(0).TextString & "'"
        objTrim.Layer = "Integrity Notes"
        objTrim.Update
        
        iCount = iCount + 1
Next_entBlock:
    Next objTrim
    
    objSS3.Clear
    objSS3.Delete
    
    MsgBox "Trim Blocks: " & iCount
    'Me.show
End Sub

Private Sub ValidateNotes()
    Dim objSS3 As AcadSelectionSet
    Dim objTrim As AcadBlockReference
    Dim attList As Variant
    Dim filterType, filterValue As Variant
    Dim grpCode(0) As Integer
    Dim grpValue(0) As Variant
    Dim entBlock As AcadEntity
    Dim txtLine As AcadText
    Dim mtxtLine As AcadMText
    
    'Me.Hide
    
    grpCode(0) = 8
    grpValue(0) = "Annotations"
    filterType = grpCode
    filterValue = grpValue
    
    Set objSS3 = ThisDrawing.SelectionSets.Add("objSS3")
    objSS3.Select acSelectionSetAll, , , filterType, filterValue
    
    For Each entBlock In objSS3
        Select Case entBlock.ObjectName
            Case "AcDbText"
                Set txtLine = entBlock
                txtLine.TextString = UCase(txtLine.TextString)
                txtLine.Height = 6
                txtLine.Update
            Case "AcDbMText"
                Set mtxtLine = entBlock
                mtxtLine.TextString = UCase(mtxtLine.TextString)
                mtxtLine.Height = 6
                mtxtLine.Update
        End Select
Next_entBlock:
    Next entBlock
    
    objSS3.Clear
    objSS3.Delete
    
    'Me.show
End Sub

Private Sub CircleBores()
    Dim objCircle As AcadCircle
    Dim objText As AcadText
    Dim objMText As AcadMText
    Dim objBlock As AcadBlockReference
    Dim objSS As AcadSelectionSet
    Dim filterType, filterValue As Variant
    Dim grpCode(0) As Integer
    Dim grpValue(0) As Variant
    Dim vPnt1, vPnt2 As Variant
    Dim vAttList, vTemp, vCoords As Variant
    Dim strLine, strLength As String
    Dim dRadius As Double
    
    On Error Resume Next
    
    Me.Hide
    
    vPnt1 = ThisDrawing.Utility.GetPoint(, "Get BL Corner: ")
    vPnt2 = ThisDrawing.Utility.GetCorner(vPnt1, vbCr & "Get UR Corner: ")
    If Not Err = 0 Then GoTo Exit_Sub
    
    grpCode(0) = 2
    grpValue(0) = "Drop"
    filterType = grpCode
    filterValue = grpValue
    
    Set objSS = ThisDrawing.SelectionSets.Add("objSS")
    If Not Err = 0 Then Set objSS = ThisDrawing.SelectionSets.Item("objSS")
    
    objSS.Select acSelectionSetWindow, vPnt1, vPnt2, filterType, filterValue
    
    For Each objBlock In objSS
        vAttList = objBlock.GetAttributes
        strLine = UCase(vAttList(0).TextString)
        
        If InStr(strLine, "BORE") > 0 Then
            vTemp = Split(strLine, "=")
            strLength = Replace(vTemp(1), " ", "")
            strLength = Replace(strLength, "'", "")
            
            dRadius = CDbl(strLength) / 2
            If dRadius < 1 Then GoTo Next_objBlock
            
            vCoords = objBlock.InsertionPoint
            
            Set objCircle = ThisDrawing.ModelSpace.AddCircle(vCoords, dRadius)
            objCircle.Layer = objBlock.Layer
            objCircle.Update
        End If
Next_objBlock:
    Next objBlock
    
    objSS.Clear
    
    grpCode(0) = 0
    grpValue(0) = "TEXT"
    filterType = grpCode
    filterValue = grpValue
    
    objSS.Select acSelectionSetWindow, vPnt1, vPnt2, filterType, filterValue
    
    For Each objText In objSS
        strLine = UCase(objText.TextString)
        
        If InStr(strLine, "BORE") > 0 Then
            vTemp = Split(strLine, "=")
            strLength = Replace(vTemp(1), " ", "")
            strLength = Replace(strLength, "'", "")
            
            dRadius = CDbl(strLength) / 2
            If dRadius < 1 Then GoTo Next_ObjText
            
            vCoords = objText.InsertionPoint
            
            Set objCircle = ThisDrawing.ModelSpace.AddCircle(vCoords, dRadius)
            objCircle.Layer = objText.Layer
            objCircle.Update
        End If
Next_ObjText:
    Next objText
    
    objSS.Clear
    
    grpCode(0) = 0
    grpValue(0) = "MTEXT"
    filterType = grpCode
    filterValue = grpValue
    
    objSS.Select acSelectionSetWindow, vPnt1, vPnt2, filterType, filterValue
    
    For Each objMText In objSS
        strLine = UCase(objMText.TextString)
        
        If InStr(strLine, "BORE") > 0 Then
            vTemp = Split(strLine, "=")
            strLength = Replace(vTemp(1), " ", "")
            strLength = Replace(strLength, "'", "")
            
            dRadius = CDbl(strLength) / 2
            If dRadius < 1 Then GoTo Next_ObjMText
            
            vCoords = objMText.InsertionPoint
            
            Set objCircle = ThisDrawing.ModelSpace.AddCircle(vCoords, dRadius)
            objCircle.Layer = objMText.Layer
            objCircle.Update
        End If
Next_ObjMText:
    Next objMText
    
    objSS.Clear
    objSS.Delete
Exit_Sub:
    Me.show
End Sub

Private Sub UserForm_Initialize()
    cbScale.AddItem ""
    cbScale.AddItem "50"
    cbScale.AddItem "75"
    cbScale.AddItem "100"
    cbScale.Value = "75"
    
    iConverted = 0
End Sub

Private Function TN83FtoLL(dNorth As Double, dEast As Double)
    Dim dLat, dLong, dDLat As Double
    Dim dDiffE, dEast0 As Double
    Dim dDiffN, dNorth0 As Double
    Dim dR, dCAR, dCA, dU, dK As Double
    Dim LL(2) As Double
    
    dEast = dEast * 0.3048006096
    dNorth = dNorth * 0.3048006096
    
    dDiffE = dEast - 600000
    dDiffN = dNorth - 166504.1691
    
    dR = 8842127.1422 - dDiffN
    dCAR = Atn(dDiffE / dR)
    dCA = dCAR * 180 / 3.14159265359
    dLong = -86 + dCA / 0.585439726459
    
    dU = dDiffN - dDiffE * Tan(dCAR / 2)
    dDLat = dU * (0.00000901305249 + dU * (-6.77268E-15 + dU * (-3.72351E-20 + dU * -9.2828E-28)))
    dLat = 35.8340607459 + dDLat
    
    dK = 0.999948401424 + (1.23188E-14 * dU * dU) + (4.54E-22 * dU * dU * dU)
    
    LL(0) = dLat
    LL(1) = dLong
    LL(2) = dK
    
    TN83FtoLL = LL
End Function

Attribute VB_Name = "ValidateHO1"
Attribute VB_Base = "0{0B1656D9-1558-4F63-B14B-0AFDA0EA9305}{028C62AC-44D6-4455-9FB4-141794653FDE}"
Attribute VB_GlobalNameSpace = False
Attribute VB_Creatable = False
Attribute VB_PredeclaredId = True
Attribute VB_Exposed = False
Attribute VB_TemplateDerived = False
Attribute VB_Customizable = False
Dim objSS As AcadSelectionSet


Private Sub cbExport_Click()
    If lbPoles.ListCount < 1 Then Exit Sub
    
    Dim strExistingName, strFileName As String
    Dim strTemp, strFormName, strOriginal As String
    Dim strAttach, strBorder, strLine As String
    Dim vTemp, vItem, vLine As Variant
    Dim fName As String
    Dim objExcel As Workbook
    Dim objSheet As Worksheet
    Dim objDoc As Object
    Dim iRow As Integer
    
    iRow = 3
    'C:\Users\integrity.2\Dropbox\UNITED COMMUNICATIONS JOB INFORMATION\VBA\Integrity\VBA\Forms
    
    vTemp = Split(ThisDrawing.Name, " ")
    strExistingName = ThisDrawing.Path & "\" & vTemp(0) & " SPLICING SHEET.xlsx"
    
    vLine = Split(LCase(ThisDrawing.Path), "dropbox")
    strOriginal = vLine(0) & "Dropbox\UNITED COMMUNICATIONS JOB INFORMATION\VBA\Integrity\VBA\Forms\SPLICING SHEET.xlsx"
    
    fName = Dir(strFileName)
    If fName = "" Then
        Exit Sub
    End If
    
    'Set objExcel = CreateObject("Excel.Application")
    'objExcel.Visible = False
    
    fName = Dir(strExistingName)
    If fName = "" Then
        Set objExcel = Workbooks.Open(strOriginal)
        objExcel.SaveAs (strExistingName)
        MsgBox "Created New File."
    Else
        Set objExcel = Workbooks.Open(strExistingName)
        'MsgBox "Opened Existing File"
    End If
    
    Set objSheet = objExcel.Sheets("SPLICES")
    
    For i = 0 To lbPoles.ListCount - 1
        objSheet.Cells(iRow, 1).Value = lbPoles.List(i, 0)
        objSheet.Cells(iRow, 2).Value = lbPoles.List(i, 2)
        objSheet.Cells(iRow, 3).Value = lbPoles.List(i, 1)
        
        strLine = ""
        vTemp = Split(lbPoles.List(i, 4), "] ")
        vLine = Split(vTemp(1), " + ")
        For j = 0 To UBound(vLine)
            If vLine(j) = "" Then GoTo Next_J
            
            vItem = Split(vLine(j), ": ")
            If strLine = "" Then
                strLine = vItem(0) & ": " & vItem(1)
            Else
                strLine = strLine & " + " & vItem(0) & ": " & vItem(1)
            End If
Next_J:
        Next j
        objSheet.Cells(iRow, 4).Value = strLine
            
        iRow = iRow + 1
    Next i
    
    iRow = iRow - 1
    strBorder = "A3:D" & iRow
    objSheet.Range(strBorder).Borders.Weight = 2
    
    objSheet.Range("A2").AutoFilter
    
    objExcel.Save
    objExcel.Close
    
    '<---------------------------------------- Save data to csv file
    'Dim strPath, strName, strFile As String
    'Dim vTemp As Variant
    
    'strPath = ThisDrawing.Path
    'strName = ThisDrawing.Name
    'vTemp = Split(strName, " ")
    
    'strFile = strPath & "\" & vTemp(0) & " Closure Locations.csv"
    
    'Open strFile For Output As #1
    
    'Print #1, "Location,Closure Type,HO1,Counts Spliced"
    
    'For i = 0 To lbPoles.ListCount - 1
        'Print #1, lbPoles.List(i, 0) & "," & lbPoles.List(i, 2) & "," & lbPoles.List(i, 1) & "," & lbPoles.List(i, 4)
    'Next i
    
    'Close #1
End Sub

Private Sub cbGetData_Click()
    Dim objEntity As AcadEntity
    Dim objBlock As AcadBlockReference
    Dim objLWP As AcadLWPolyline
    Dim vAttList, vUnits, vItem, vLine As Variant
    Dim vTemp, vReturnPnt, vCoords As Variant
    Dim vCounts As Variant
    Dim filterType, filterValue As Variant
    Dim vPnt1, vPnt2 As Variant
    Dim grpCode(0) As Integer
    Dim grpValue(0) As Variant
    Dim dPnt1(0 To 2) As Double
    Dim dPnt2(0 To 2) As Double
    Dim strLine, strSpliced, strClosure As String
    Dim iTemp, iCounter, iHO1 As Integer
    Dim iStart, iEnd As Integer
    Dim dCoords() As Double

    grpCode(0) = 2
    grpValue(0) = "sPole,sPed,sHH,sPanel,Callout,sMH"
    filterType = grpCode
    filterValue = grpValue
    
    lbPoles.Clear
    lbCallouts.Clear
    
    cbRemoveSame.Enabled = True
    
  On Error Resume Next
  
    Me.Hide
    
    If cbType.Value = "Polygon" Then
        ThisDrawing.Utility.GetEntity objEntity, vReturnPnt, "Select Polygon Border: "
        If Not objEntity.ObjectName = "AcDbPolyline" Then
            MsgBox "Error: Invalid Selection."
            Me.show
            Exit Sub
        End If
    
        Set objLWP = objEntity
        vCoords = objLWP.Coordinates
    
        iTemp = (UBound(vCoords) + 1) / 2 * 3 - 1
        ReDim dCoords(iTemp) As Double
    
        iCounter = 0
        For i = 0 To UBound(vCoords) Step 2
            dCoords(iCounter) = vCoords(i)
            iCounter = iCounter + 1
            dCoords(iCounter) = vCoords(i + 1)
            iCounter = iCounter + 1
            dCoords(iCounter) = 0#
            iCounter = iCounter + 1
        Next i
    
        objSS.SelectByPolygon acSelectionSetCrossingPolygon, dCoords
        'objSS.SelectByPolygon acSelectionSetWindowPolygon, dCoords
    Else
        vPnt1 = ThisDrawing.Utility.GetPoint(, "Get BL Corner: ")
        vPnt2 = ThisDrawing.Utility.GetCorner(vPnt1, vbCr & "Get UR Corner: ")
    
        dPnt1(0) = vPnt1(0)
        dPnt1(1) = vPnt1(1)
        dPnt1(2) = vPnt1(2)
    
        dPnt2(0) = vPnt2(0)
        dPnt2(1) = vPnt2(1)
        dPnt2(2) = vPnt2(2)
  
        objSS.Select acSelectionSetWindow, dPnt1, dPnt2, filterType, filterValue
    End If
    
    ReDim dCoords(0 To 2) As Double
    
    For i = 0 To objSS.count - 1
        Set objBlock = objSS.Item(i)
            
        Select Case objBlock.Name
            Case "sPole"
                vAttList = objBlock.GetAttributes
                    
                If vAttList(0).TextString = "" Then GoTo Next_Object
                If vAttList(0).TextString = "POLE" Then GoTo Next_Object
                If vAttList(26).TextString = "" Then GoTo Next_Object
                
                If vAttList(26).TextString = "[A1] " Then
                    vAttList(26).TextString = ""
                    objBlock.Update
                    GoTo Next_Object
                End If
                
                strClosure = "none"
                vUnits = Split(vAttList(27).TextString, ";;")
                For j = 0 To UBound(vUnits)
                    Select Case Left(vUnits(j), 5)
                        Case "+HACO", "+HBFO", "+WHAC", "+WHBF"
                            vItem = Split(vUnits(j), "=")
                            strClosure = Replace(vItem(0), "+", "")
                            GoTo Found_Closure
                        End Select
                Next j
Found_Closure:
                iHO1 = 0
                
                strSpliced = vAttList(26).TextString
                vUnits = Split(strSpliced, " + ")
                For j = 0 To UBound(vUnits)
                    If vUnits(j) = "" Then GoTo Next_line
                    
                    vItem = Split(vUnits(j), ": ")
                    If InStr(vItem(1), "FUTURE") > 0 Then GoTo Next_line
                    vCounts = Split(vItem(1), "-")
                    If UBound(vCounts) = 0 Then
                        iHO1 = iHO1 + 1
                    Else
                        iStart = CInt(vCounts(0))
                        iEnd = CInt(vCounts(1))
                        
                        If iStart = iEnd Then
                            iHO1 = iHO1 + 1
                        Else
                            iHO1 = iHO1 + iEnd - iStart + 1
                        End If
                    End If
Next_line:
                Next j
                
                lbPoles.AddItem vAttList(0).TextString
                lbPoles.List(lbPoles.ListCount - 1, 1) = iHO1
                lbPoles.List(lbPoles.ListCount - 1, 2) = strClosure
                lbPoles.List(lbPoles.ListCount - 1, 3) = i
                lbPoles.List(lbPoles.ListCount - 1, 4) = strSpliced
                
            Case "sPed", "sHH", "sPanel"
                vAttList = objBlock.GetAttributes
                    
                If vAttList(0).TextString = "xx" Then GoTo Next_Object
                'If vAttList(3).TextString = "" Then GoTo Next_Object
                'If vAttList(3).TextString = "POLE" Then GoTo Next_Object
                If vAttList(6).TextString = "" Then GoTo Next_Object
                
                
                If vAttList(6).TextString = "[A1] " Then
                    vAttList(6).TextString = ""
                    objBlock.Update
                    GoTo Next_Object
                End If
                
                strClosure = "none"
                vUnits = Split(vAttList(7).TextString, ";;")
                For j = 0 To UBound(vUnits)
                    Select Case Left(vUnits(j), 5)
                        Case "+HACO", "+HBFO", "+WHAC", "+WHBF"
                            vItem = Split(vUnits(j), "=")
                            strClosure = Replace(vItem(0), "+", "")
                            GoTo Found_Closure2
                        End Select
                Next j
Found_Closure2:
                
                iHO1 = 0
                
                strSpliced = vAttList(6).TextString
                vUnits = Split(strSpliced, " + ")
                For j = 0 To UBound(vUnits)
                    If vUnits(j) = "" Then GoTo Next_Line2
                    
                    vItem = Split(vUnits(j), ": ")
                    If InStr(vItem(1), "FUTURE") > 0 Then GoTo Next_line
                    vCounts = Split(vItem(1), "-")
                    If UBound(vCounts) = 0 Then
                        iHO1 = iHO1 + 1
                    Else
                        iStart = CInt(vCounts(0))
                        iEnd = CInt(vCounts(1))
                        
                        If iStart = iEnd Then
                            iHO1 = iHO1 + 1
                        Else
                            iHO1 = iHO1 + iEnd - iStart + 1
                        End If
                    End If
Next_Line2:
                Next j
                
                lbPoles.AddItem vAttList(0).TextString
                lbPoles.List(lbPoles.ListCount - 1, 1) = iHO1
                lbPoles.List(lbPoles.ListCount - 1, 2) = strClosure
                lbPoles.List(lbPoles.ListCount - 1, 3) = i
                lbPoles.List(lbPoles.ListCount - 1, 4) = strSpliced
                
            Case "Callout"
                vAttList = objBlock.GetAttributes
                
                If objBlock.Layer = "Integrity Existing" Then GoTo Next_Object
                If Not Left(vAttList(1).TextString, 1) = "+" Then GoTo Next_Object
                
                vUnits = Split(vAttList(1).TextString, "=")
                iHO1 = CInt(vUnits(1))
                
                vUnits = Split(vAttList(0).TextString, ":")
                
                lbCallouts.AddItem vUnits(0)
                lbCallouts.List(lbCallouts.ListCount - 1, 1) = iHO1
                lbCallouts.List(lbCallouts.ListCount - 1, 3) = i
                
        End Select
                   
Next_Object:
    'Next objEntity
    Next i
    
Exit_Sub:
    Call GetTotals
    
    Me.show
End Sub

Private Sub cbQuit_Click()
    Me.Hide
End Sub

Private Sub cbRemoveSame_Click()
    If lbPoles.ListCount < 1 Then Exit Sub
    If lbCallouts.ListCount < 1 Then Exit Sub
    
    For i = lbPoles.ListCount - 1 To 0 Step -1
        For j = lbCallouts.ListCount - 1 To 0 Step -1
            If lbPoles.List(i, 0) = lbCallouts.List(j, 0) Then
                If lbPoles.List(i, 1) = lbCallouts.List(j, 1) Then
                    lbPoles.RemoveItem i
                    lbCallouts.RemoveItem j
                
                    GoTo Next_I
                End If
            End If
        Next j
Next_I:
    Next i
    
    Call GetTotals
End Sub

Private Sub cbUpdate_Click()
    Dim objBlock As AcadBlockReference
    Dim vAttList As Variant
    Dim vLine, vItem, vCounts As Variant
    Dim strLine As String
    Dim iIndex, iHO1 As Integer
    Dim iStart, iEnd As Integer
    
    iHO1 = 0
    
    If tbSingle.Enabled = True Then   ' lbCallouts Edit
        'Do something
    Else                              ' lbPoles Edit
        If tbMultiple.Value = "" Then
            strLine = ""
            lbPoles.List(lbPoles.ListIndex, 1) = 0
        Else
            strLine = Replace(tbMultiple.Value, vbCr, " + ")
            strLine = Replace(strLine, vbLf, "")
        
            vLine = Split(strLine, " + ")
            For i = 0 To UBound(vLine)
                vItem = Split(vLine(i), ": ")
                If UBound(vItem) < 1 Then GoTo Next_line
                
                vCounts = Split(vItem(1), "-")
                If UBound(vCounts) = 0 Then
                    iHO1 = iHO1 + 1
                Else
                    iStart = CInt(vCounts(0))
                    iEnd = CInt(vCounts(1))
                    
                    If iStart = iEnd Then
                        iHO1 = iHO1 + 1
                    Else
                        iHO1 = iHO1 + 1 + iEnd - iStart
                    End If
                End If
Next_line:
            Next i
            lbPoles.List(lbPoles.ListIndex, 1) = iHO1
        End If
        
        iIndex = CInt(lbPoles.List(lbPoles.ListIndex, 3))
        Set objBlock = objSS.Item(iIndex)
        vAttList = objBlock.GetAttributes
        
        Select Case objBlock.Name
            Case "sPole"
                vAttList(26).TextString = strLine
            Case Else
                vAttList(6).TextString = strLine
        End Select
        objBlock.Update
    End If
    
    lbPoles.Enabled = True
    lbCallouts.Enabled = True
    cbGetData.Enabled = True
    cbRemoveSame.Enabled = True
    
    cbUpdate.Enabled = False
    
    tbSingle.Value = ""
    tbSingle.Enabled = False
    
    tbMultiple.Value = ""
    
    Call GetTotals
End Sub

Private Sub lbCallouts_DblClick(ByVal Cancel As MSForms.ReturnBoolean)
    Dim objBlock As AcadBlockReference
    Dim vCoords, vAttList As Variant
    'Dim vLine, vItem As Variant
    'Dim strLine As String
    Dim viewCoordsB(0 To 2) As Double
    Dim viewCoordsE(0 To 2) As Double
    Dim iIndex As Integer
    
    Me.Hide
    
    iIndex = CInt(lbCallouts.List(lbCallouts.ListIndex, 2))
    Set objBlock = objSS.Item(iIndex)
    
    vCoords = objBlock.InsertionPoint
    
    viewCoordsB(0) = vCoords(0) - 200
    viewCoordsB(1) = vCoords(1) - 200
    viewCoordsB(2) = 0#
    viewCoordsE(0) = vCoords(0) + 200
    viewCoordsE(1) = vCoords(1) + 200
    viewCoordsE(2) = 0#
    
    ThisDrawing.Application.ZoomWindow viewCoordsB, viewCoordsE
    
    Me.show
End Sub

Private Sub lbPoles_DblClick(ByVal Cancel As MSForms.ReturnBoolean)
    Dim objBlock As AcadBlockReference
    Dim vCoords, vAttList As Variant
    Dim vLine, vItem As Variant
    Dim strLine As String
    Dim viewCoordsB(0 To 2) As Double
    Dim viewCoordsE(0 To 2) As Double
    Dim iIndex As Integer
    
    Me.Hide
    
    lbPoles.Enabled = False
    lbCallouts.Enabled = False
    cbGetData.Enabled = False
    cbRemoveSame.Enabled = False
    
    cbUpdate.Enabled = True
    
    iIndex = CInt(lbPoles.List(lbPoles.ListIndex, 3))
    Set objBlock = objSS.Item(iIndex)
    
    'vCoords = Split(lbPoles.List(lbPoles.ListIndex, 2), ",")
    vCoords = objBlock.InsertionPoint
    
    viewCoordsB(0) = vCoords(0) - 200
    viewCoordsB(1) = vCoords(1) - 200
    viewCoordsB(2) = 0#
    viewCoordsE(0) = vCoords(0) + 200
    viewCoordsE(1) = vCoords(1) + 200
    viewCoordsE(2) = 0#
    
    ThisDrawing.Application.ZoomWindow viewCoordsB, viewCoordsE
    
    vAttList = objBlock.GetAttributes
    
    Select Case objBlock.Name
        Case "sPole"
            tbMultiple.Value = Replace(vAttList(26).TextString, " + ", vbCr)
        Case Else
            tbMultiple.Value = Replace(vAttList(6).TextString, " + ", vbCr)
    End Select
    
    
    Me.show
End Sub

Private Sub UserForm_Initialize()
    lbPoles.ColumnCount = 5
    lbPoles.ColumnWidths = "120;48;60;28;4"
    
    lbCallouts.ColumnCount = 3
    lbCallouts.ColumnWidths = "120;48;24"
    
    cbType.AddItem "Window"
    cbType.AddItem "Polygon"
    cbType.Value = "Window"
    
  On Error Resume Next
    
    Set objSS = ThisDrawing.SelectionSets.Add("objSS")
    If Not Err = 0 Then
        Set objSS = ThisDrawing.SelectionSets.Item("objSS")
        Err = 0
    End If
End Sub

Private Sub GetTotals()
    Dim lTotal As Long
    
    lTotal = 0
    
    tbUnitCount.Value = lbPoles.ListCount
    tbSpanCount.Value = lbCallouts.ListCount
    
    If Not lbPoles.ListCount < 1 Then
        For i = 0 To lbPoles.ListCount - 1
            lTotal = lTotal + CInt(lbPoles.List(i, 1))
        Next i
        
        tbUnits.Value = lTotal
    Else
        tbUnits.Value = "0"
    End If
    
    lTotal = 0
    
    If Not lbCallouts.ListCount < 1 Then
        For i = 0 To lbCallouts.ListCount - 1
            lTotal = lTotal + CInt(lbCallouts.List(i, 1))
        Next i
        
        tbSpans.Value = lTotal
    Else
        tbSpans.Value = "0"
    End If
    
    tbDiffCount.Value = lbPoles.ListCount - lbCallouts.ListCount
    tbDiffTotal.Value = CLng(tbUnits.Value) - CLng(tbSpans.Value)
End Sub

Private Sub UserForm_Terminate()
    objSS.Clear
    objSS.Delete
End Sub

Attribute VB_Name = "ValidateMCL"
Attribute VB_Base = "0{7829B7FB-A50C-48D8-8768-36721C468713}{9CC08F8E-8454-4D07-A22B-58175A15C622}"
Attribute VB_GlobalNameSpace = False
Attribute VB_Creatable = False
Attribute VB_PredeclaredId = True
Attribute VB_Exposed = False
Attribute VB_TemplateDerived = False
Attribute VB_Customizable = False

Private Sub cbAddAdresses_Click()
    If lbList.ListCount < 1 Then Exit Sub
    
    Dim filterType, filterValue As Variant
    Dim grpCode(0) As Integer
    Dim grpValue(0) As Variant
    Dim objSS As AcadSelectionSet
    Dim objBlock As AcadBlockReference
    Dim vLine, vItem, vCount As Variant
    Dim vPnt1, vPnt2 As Variant
    Dim dPnt1(0 To 2) As Double
    Dim dPnt2(0 To 2) As Double
    Dim strText, strExistingName, strLine As String
    Dim iCount As Integer
    
    grpCode(0) = 2
    grpValue(0) = "Customer,SG"
    filterType = grpCode
    filterValue = grpValue
    
    On Error Resume Next
    
    Err = 0
    Set objSS = ThisDrawing.SelectionSets.Add("objSS")
    If Not Err = 0 Then
        Set objSS = ThisDrawing.SelectionSets.Item("objSS")
        objSS.Clear
    End If
    
    Me.Hide
    
    vPnt1 = ThisDrawing.Utility.GetPoint(, "Get BL Corner: ")
    vPnt2 = ThisDrawing.Utility.GetCorner(vPnt1, vbCr & "Get UR Corner: ")
    
    dPnt1(0) = vPnt1(0)
    dPnt1(1) = vPnt1(1)
    dPnt1(2) = vPnt1(2)
    
    dPnt2(0) = vPnt2(0)
    dPnt2(1) = vPnt2(1)
    dPnt2(2) = vPnt2(2)
    
    objSS.Select acSelectionSetWindow, dPnt1, dPnt2, filterType, filterValue
    
    vTemp = Split(ThisDrawing.Name, " ")
    strExistingName = ThisDrawing.Path & "\" & vTemp(0) & " SERVED ADDRESSES.csv"
    
    Open strExistingName For Output As #1
    
    Print #1, "House #,Street Name,TN83F N,TN83F E,Type"
    
    For Each objBlock In objSS
        vAttList = objBlock.GetAttributes
        
        Select Case objBlock.Name
            Case "SG"
                If vAttList(2).TextString = "" Then GoTo Next_objBlock
                
                strLine = "SmartGrid," & vAttList(1).TextString & "," & objBlock.InsertionPoint(1)
                strLine = strLine & "," & objBlock.InsertionPoint(0) & ",SmartGrid"
                Print #1, strLine
            Case Else
                If vAttList(4).TextString = "" Then GoTo Next_objBlock
                
                strLine = vAttList(1).TextString & "," & vAttList(2).TextString & "," & objBlock.InsertionPoint(1)
                strLine = strLine & "," & objBlock.InsertionPoint(0) & "," & vAttList(0).TextString
                Print #1, strLine
        End Select
        
Next_objBlock:
    Next objBlock
    
Clear_objSS:
    objSS.Clear
    objSS.Delete
    
    Close #1
    MsgBox "Done"
    Me.show
    
    Exit Sub
    
    
    
    
    
    
    
    If lbList.ListCount < 1 Then Exit Sub
    
    'Dim strExistingName, strFileName As String
    'Dim strTemp, strFormName, strOriginal As String
    'Dim strAttach, strBorder As String
    'Dim vTemp, vTemp2, vLine As Variant
    'Dim fName As String
    'Dim objExcel As Workbook
    'Dim objSheet As Worksheet
    'Dim objDoc As Object
    'Dim iRow As Integer
    
    vTemp = Split(ThisDrawing.Name, " ")
    strExistingName = ThisDrawing.Path & "\" & vTemp(0) & " Served Addresses.csv"
    
    Open strExistingName For Output As #1
    
    Print #1, "House #,Street Name"
    
    For i = 0 To lbList.ListCount - 1
        If Not lbList.List(i, 3) = "  " Then
            Print #1, Replace(lbList.List(i, 3), "  ", ",")
            
            'vTemp = Split(lbList.List(i, 3), "  ")
            'objSheet.Cells(iRow, 1).Value = vTemp(0)
            'objSheet.Cells(iRow, 2).Value = vTemp(1)
            
            'iRow = iRow + 1
        End If
    Next i
    
    Close #1
    MsgBox "Done"
    Exit Sub
    'iRow = 2
    
    vTemp = Split(ThisDrawing.Name, " ")
    strExistingName = ThisDrawing.Path & "\" & vTemp(0) & " FIBER COUNT SHEET.xlsx"
    
    vLine = Split(LCase(ThisDrawing.Path), "dropbox")
    strOriginal = vLine(0) & "Dropbox\UNITED COMMUNICATIONS JOB INFORMATION\VBA\Integrity\VBA\Forms\FIBER COUNT SHEET.xlsx"
    
    fName = Dir(strFileName)
    If fName = "" Then
        Exit Sub
    End If
    
    'Set objExcel = CreateObject("Excel.Application")
    'objExcel.Visible = False
    
    fName = Dir(strExistingName)
    If fName = "" Then
        Set objExcel = Workbooks.Open(strOriginal)
        objExcel.SaveAs (strExistingName)
        MsgBox "Created New File."
    Else
        Set objExcel = Workbooks.Open(strExistingName)
        'MsgBox "Opened Existing File"
    End If
    
    strTemp = "Served Address"
    For Each objSheet In objExcel.Sheets
        If objSheet.Name = strTemp Then GoTo Found_Sheet
    Next objSheet
    
    objExcel.Sheets.Add.Name = strTemp
    Set objSheet = objExcel.Sheets(strTemp)
Found_Sheet:
    
    objSheet.Rows(1).Font.Bold = True
    
    objSheet.Cells(1, 1).Value = "House #"
    objSheet.Cells(1, 2).Value = "Street Name"
    
    For i = 0 To lbList.ListCount - 1
        If Not lbList.List(i, 3) = "  " Then
            vTemp = Split(lbList.List(i, 3), "  ")
            objSheet.Cells(iRow, 1).Value = vTemp(0)
            objSheet.Cells(iRow, 2).Value = vTemp(1)
            
            iRow = iRow + 1
        End If
    Next i
'Exit_Sub:
    
    objSheet.Columns(1).ColumnWidth = 15
    objSheet.Columns(2).ColumnWidth = 20
    
    objSheet.Columns(1).HorizontalAlignment = 3
    objSheet.Columns(2).HorizontalAlignment = 3
    
    iRow = iRow - 1
    strBorder = "A1:B" & iRow
    objSheet.Range(strBorder).Borders.Weight = 2
    
    objSheet.Range("A1").AutoFilter
    
    objExcel.Save
    objExcel.Close
    
    MsgBox "Done."
End Sub

Private Sub cbAddSplitters_Click()
    If lbList.ListCount < 1 Then Exit Sub
    
    Dim strExistingName, strFileName As String
    Dim strTemp, strFormName, strOriginal As String
    Dim strAttach, strBorder As String
    Dim vTemp, vTemp2, vLine As Variant
    Dim fName As String
    Dim objExcel As Workbook
    Dim objSheet As Worksheet
    Dim objDoc As Object
    Dim iRow As Integer
    
    iRow = 2
    
    vTemp = Split(ThisDrawing.Name, " ")
    strExistingName = ThisDrawing.Path & "\" & vTemp(0) & " FIBER COUNT SHEET.xlsx"
    vLine = Split(LCase(ThisDrawing.Path), "dropbax")
    strOriginal = vLine(0) & "Dropbox\UNITED COMMUNICATIONS JOB INFORMATION\VBA\Integrity\VBA\Forms\FIBER COUNT SHEET.xlsx"
    
    fName = Dir(strFileName)
    If fName = "" Then
        Exit Sub
    End If
    
    'Set objExcel = CreateObject("Excel.Application")
    'objExcel.Visible = False
    
    fName = Dir(strExistingName)
    If fName = "" Then
        Set objExcel = Workbooks.Open(strOriginal)
        objExcel.SaveAs (strExistingName)
        MsgBox "Created New File."
    Else
        Set objExcel = Workbooks.Open(strExistingName)
        'MsgBox "Opened Existing File"
    End If
    
    strTemp = TabStrip1.SelectedItem.Caption
    For Each objSheet In objExcel.Sheets
        If objSheet.Name = strTemp Then GoTo Found_Sheet
    Next objSheet
    
    objExcel.Sheets.Add.Name = strTemp
    Set objSheet = objExcel.Sheets(strTemp)
Found_Sheet:
    
    objSheet.Rows(1).Font.Bold = True
    
    objSheet.Cells(1, 1).Value = strTemp
    objSheet.Cells(1, 2).Value = "Pole/Ped #"
    objSheet.Cells(1, 3).Value = "House #"
    objSheet.Cells(1, 4).Value = "Street Name"
    objSheet.Cells(1, 5).Value = "Type"
    objSheet.Cells(1, 6).Value = "Subscriber Info"
    objSheet.Cells(1, 7).Value = "Notes"
    objSheet.Cells(1, 8).Value = "Splitter Location"
    
    For i = 0 To lbList.ListCount - 1
        If lbList.List(i, 0) = strTemp Then
            If Not lbList.List(i, 4) = "SPLITTER" Then GoTo Next_line
            
            objSheet.Cells(iRow, 1).Value = lbList.List(i, 1)
            If Left(lbList.List(i, 2), 1) = "<" Then
                objSheet.Cells(iRow, 2).Value = ""
            Else
                objSheet.Cells(iRow, 2).Value = lbList.List(i, 2)
            End If
            vTemp = Split(lbList.List(i, 3), "  ")
            objSheet.Cells(iRow, 3).Value = vTemp(0)
            objSheet.Cells(iRow, 4).Value = vTemp(1)
            objSheet.Cells(iRow, 5).Value = lbList.List(i, 4)
            objSheet.Cells(iRow, 8).Value = lbList.List(i, 5)
            
            objSheet.Cells(iRow, 1).Interior.color = RGB(0, 176, 240)
            
            iRow = iRow + 1
        End If
Next_line:
    Next i
    
    objSheet.Columns(1).ColumnWidth = 15
    objSheet.Columns(2).ColumnWidth = 20
    objSheet.Columns(3).ColumnWidth = 15
    objSheet.Columns(4).ColumnWidth = 20
    objSheet.Columns(5).ColumnWidth = 10
    objSheet.Columns(6).ColumnWidth = 20
    objSheet.Columns(7).ColumnWidth = 20
    objSheet.Columns(8).ColumnWidth = 20
    
    objSheet.Columns(1).HorizontalAlignment = 3
    objSheet.Columns(2).HorizontalAlignment = 3
    objSheet.Columns(3).HorizontalAlignment = 3
    objSheet.Columns(4).HorizontalAlignment = 3
    objSheet.Columns(5).HorizontalAlignment = 3
    objSheet.Columns(6).HorizontalAlignment = 3
    objSheet.Columns(7).HorizontalAlignment = 3
    objSheet.Columns(8).HorizontalAlignment = 3
    
    iRow = iRow - 1
    strBorder = "A1:H" & iRow
    objSheet.Range(strBorder).Borders.Weight = 2
    
    objSheet.Range("A1").AutoFilter
    
    objExcel.Save
    objExcel.Close
End Sub

Private Sub cbCheckData_Click()
    If lbTab.ListCount < 1 Then Exit Sub
    
    For i = lbTab.ListCount - 1 To 0 Step -1
            If lbTab.List(i, 8) = "Y" Then
                lbTab.RemoveItem i
            Else
                If lbTab.List(i, 3) = "  " Then lbTab.RemoveItem i
            End If
    Next i
End Sub

Private Sub cbExport_Click()
    If lbList.ListCount < 1 Then Exit Sub
    
    Dim strExistingName, strFileName As String
    Dim strTemp, strFormName, strOriginal As String
    Dim strAttach, strBorder As String
    Dim vTemp, vTemp2, vLine As Variant
    Dim fName As String
    Dim objExcel As Workbook
    Dim objSheet As Worksheet
    Dim objDoc As Object
    Dim iRow As Integer
    
    iRow = 2
    
    vTemp = Split(ThisDrawing.Name, " ")
    strExistingName = ThisDrawing.Path & "\" & vTemp(0) & " FIBER COUNT SHEET.xlsx"
    
    vLine = Split(LCase(ThisDrawing.Path), "dropbox")
    strOriginal = vLine(0) & "Dropbox\UNITED COMMUNICATIONS JOB INFORMATION\VBA\Integrity\VBA\Forms\FIBER COUNT SHEET.xlsx"
    
    fName = Dir(strFileName)
    If fName = "" Then
        Exit Sub
    End If
    
    'Set objExcel = CreateObject("Excel.Application")
    'objExcel.Visible = False
    
    fName = Dir(strExistingName)
    If fName = "" Then
        Set objExcel = Workbooks.Open(strOriginal)
        objExcel.SaveAs (strExistingName)
        MsgBox "Created New File."
    Else
        Set objExcel = Workbooks.Open(strExistingName)
        'MsgBox "Opened Existing File"
    End If
    
    strTemp = TabStrip1.SelectedItem.Caption
    For Each objSheet In objExcel.Sheets
        If objSheet.Name = strTemp Then GoTo Found_Sheet
    Next objSheet
    
    objExcel.Sheets.Add.Name = strTemp
    Set objSheet = objExcel.Sheets(strTemp)
Found_Sheet:
    
    objSheet.Rows(1).Font.Bold = True
    
    objSheet.Cells(1, 1).Value = strTemp
    objSheet.Cells(1, 2).Value = "Pole/Ped #"
    objSheet.Cells(1, 3).Value = "House #"
    objSheet.Cells(1, 4).Value = "Street Name"
    objSheet.Cells(1, 5).Value = "Type"
    objSheet.Cells(1, 6).Value = "Subscriber Info"
    objSheet.Cells(1, 7).Value = "Notes"
    
    For i = 0 To lbList.ListCount - 1
        If lbList.List(i, 0) = strTemp Then
            objSheet.Cells(iRow, 1).Value = lbList.List(i, 1)
            If Left(lbList.List(i, 2), 1) = "<" Then
                objSheet.Cells(iRow, 2).Value = ""
            Else
                objSheet.Cells(iRow, 2).Value = lbList.List(i, 2)
            End If
            vTemp = Split(lbList.List(i, 3), "  ")
            objSheet.Cells(iRow, 3).Value = vTemp(0)
            objSheet.Cells(iRow, 4).Value = vTemp(1)
            objSheet.Cells(iRow, 5).Value = lbList.List(i, 4)
            objSheet.Cells(iRow, 6).Value = lbList.List(i, 5)
            
            If lbList.List(i, 8) = "Y" Then
                If Not lbList.List(i, 4) = "  " Then objSheet.Cells(iRow, 1).Interior.color = RGB(146, 208, 80)
            End If
            
            iRow = iRow + 1
        End If
    Next i
    
    objSheet.Columns(1).ColumnWidth = 15
    objSheet.Columns(2).ColumnWidth = 20
    objSheet.Columns(3).ColumnWidth = 15
    objSheet.Columns(4).ColumnWidth = 20
    objSheet.Columns(5).ColumnWidth = 10
    objSheet.Columns(6).ColumnWidth = 20
    objSheet.Columns(7).ColumnWidth = 20
    
    objSheet.Columns(1).HorizontalAlignment = 3
    objSheet.Columns(2).HorizontalAlignment = 3
    objSheet.Columns(3).HorizontalAlignment = 3
    objSheet.Columns(4).HorizontalAlignment = 3
    objSheet.Columns(5).HorizontalAlignment = 3
    objSheet.Columns(6).HorizontalAlignment = 3
    objSheet.Columns(7).HorizontalAlignment = 3
    
    iRow = iRow - 1
    strBorder = "A1:G" & iRow
    objSheet.Range(strBorder).Borders.Weight = 2
    
    objSheet.Range("A1").AutoFilter
    
    objExcel.Save
    objExcel.Close
End Sub

Private Sub cbQuit_Click()
    Me.Hide
End Sub

Private Sub TabStrip1_Change()
    Dim strTab As String
    
    strTab = TabStrip1.SelectedItem.Caption
    
    If strTab = "All" Then
        Call GetAll
    Else
        Call GetCable(CStr(strTab))
    End If
End Sub

Private Sub UserForm_Initialize()
    lbList.ColumnCount = 9
    lbList.ColumnWidths = "48;48;48;48;48;48;48;48;48;48"
    
    lbTab.ColumnCount = 9
    lbTab.ColumnWidths = "72;36;120;144;24;144;144;24;30"
    
    On Error Resume Next
    
    Dim strFile, strFolder, strTemp As String
    Dim strFileName As String
    Dim vName, vLine, vItem As Variant
    Dim strLine, strTab, strCable As String
    Dim fName As String
    Dim iIndex, iCount As Integer
    
    strFolder = ThisDrawing.Path & "\*.*"
    
    strFile = Dir$(strFolder)
    
    Do While strFile <> ""
        If InStr(strFile, ".mcl") Then
            strTab = Replace(strFile, ".mcl", "")
            vLine = Split(strTab, " -")
            TabStrip1.Tabs.Add vLine(1), vLine(1)
            
            strFileName = ThisDrawing.Path & "\" & strFile
            
            Open strFileName For Input As #2
            
            Line Input #2, strLine
            strCable = vLine(1)
    
            While Not EOF(2)
                Line Input #2, strLine
                If strLine = "" Then GoTo Next_line
                
                vLine = Split(strLine, vbTab)
        
                lbList.AddItem strCable
                iIndex = lbList.ListCount - 1
        
                lbList.List(iIndex, 1) = vLine(0)
                
                If Left(vLine(1), 1) = "<" Then
                    lbList.List(iIndex, 2) = " "
                Else
                    lbList.List(iIndex, 2) = vLine(1)
                End If
                
                If Left(vLine(2), 1) = "<" Then
                    lbList.List(iIndex, 3) = "  "
                Else
                    lbList.List(iIndex, 3) = vLine(2) & "  " & vLine(3)
                End If
                
                If Left(vLine(4), 1) = "<" Then
                    lbList.List(iIndex, 4) = " "
                Else
                    lbList.List(iIndex, 4) = vLine(4)
                End If
                
                If Left(vLine(5), 1) = "<" Then
                    lbList.List(iIndex, 5) = " "
                Else
                    lbList.List(iIndex, 5) = vLine(5)
                End If
                
                lbList.List(iIndex, 6) = "n/a"
                lbList.List(iIndex, 7) = " "
                lbList.List(iIndex, 8) = " "
Next_line:
            Wend
    
            Close #2
        End If
        strFile = Dir$
    Loop
    
    Call GetCustomers
    
    Call GetAll
    
    TextBox1.Value = lbTab.ListCount
End Sub

Private Sub GetAll()
    If lbList.ListCount < 1 Then Exit Sub
    
    lbTab.Clear
    
    For i = 0 To lbList.ListCount - 1
        lbTab.AddItem lbList.List(i, 0)
        lbTab.List(i, 1) = lbList.List(i, 1)
        lbTab.List(i, 2) = lbList.List(i, 2)
        lbTab.List(i, 3) = lbList.List(i, 3)
        lbTab.List(i, 4) = lbList.List(i, 4)
        lbTab.List(i, 5) = lbList.List(i, 5)
        lbTab.List(i, 6) = lbList.List(i, 6)
        lbTab.List(i, 7) = lbList.List(i, 7)
        lbTab.List(i, 8) = lbList.List(i, 8)
    Next i
End Sub

Private Sub GetCable(strCable As String)
    If lbList.ListCount < 1 Then Exit Sub
    
    Dim iIndex As Integer
    
    lbTab.Clear
    iIndex = 0
    
    For i = 0 To lbList.ListCount - 1
        If lbList.List(i, 0) = strCable Then
            lbTab.AddItem lbList.List(i, 0)
            lbTab.List(iIndex, 1) = lbList.List(i, 1)
            lbTab.List(iIndex, 2) = lbList.List(i, 2)
            lbTab.List(iIndex, 3) = lbList.List(i, 3)
            lbTab.List(iIndex, 4) = lbList.List(i, 4)
            lbTab.List(iIndex, 5) = lbList.List(i, 5)
            lbTab.List(iIndex, 6) = lbList.List(i, 6)
            lbTab.List(iIndex, 7) = lbList.List(i, 7)
            lbTab.List(iIndex, 8) = lbList.List(i, 8)
            
            iIndex = iIndex + 1
        End If
    Next i
End Sub

Private Sub GetCustomers()
    If lbList.ListCount < 1 Then Exit Sub
    
    Dim filterType, filterValue As Variant
    Dim grpCode(0) As Integer
    Dim grpValue(0) As Variant
    Dim objSS As AcadSelectionSet
    Dim objBlock As AcadBlockReference
    Dim vLine, vItem, vCount As Variant
    Dim vPnt1, vPnt2 As Variant
    Dim dPnt1(0 To 2) As Double
    Dim dPnt2(0 To 2) As Double
    Dim strText, strExistingName, strLine As String
    Dim iCount As Integer
    
    grpCode(0) = 2
    grpValue(0) = "Customer,SG"
    filterType = grpCode
    filterValue = grpValue
    
    On Error Resume Next
    
    Err = 0
    Set objSS = ThisDrawing.SelectionSets.Add("objSS")
    If Not Err = 0 Then
        Set objSS = ThisDrawing.SelectionSets.Item("objSS")
        objSS.Clear
    End If
    
    vPnt1 = ThisDrawing.Utility.GetPoint(, "Get BL Corner: ")
    vPnt2 = ThisDrawing.Utility.GetCorner(vPnt1, vbCr & "Get UR Corner: ")
    
    dPnt1(0) = vPnt1(0)
    dPnt1(1) = vPnt1(1)
    dPnt1(2) = vPnt1(2)
    
    dPnt2(0) = vPnt2(0)
    dPnt2(1) = vPnt2(1)
    dPnt2(2) = vPnt2(2)
    
    objSS.Select acSelectionSetWindow, dPnt1, dPnt2, filterType, filterValue
    
    vTemp = Split(ThisDrawing.Name, " ")
    strExistingName = ThisDrawing.Path & "\" & vTemp(0) & " Served Addresses.csv"
    
    Open strExistingName For Output As #1
    
    Print #1, "House #,Street Name,TN83F N,TN83F E,Type"
    
    For Each objBlock In objSS
        vAttList = objBlock.GetAttributes
        
        Select Case objBlock.Name
            Case "SG"
                If vAttList(2).TextString = "" Then GoTo Next_objBlock
                
                strLine = "SmartGrid," & vAttList(1).TextString & "," & objBlock.InsertionPoint(1)
                strLine = strLine & "," & objBlock.InsertionPoint(0) & ",SmartGrid"
                Print #1, strLine
                
                vLine = Split(vAttList(2).TextString, " - ")
                If UBound(vLine) < 1 Then GoTo Next_objBlock
                
                vCount = Split(vLine(1), ": ")
                If InStr(vCount(0), "(") > 0 Then
                    vCount(0) = Replace(vCount(0), "(", "")
                    vCount(1) = Replace(vCount(1), ")", "")
                End If
                
                For i = 0 To lbList.ListCount - 1
                    If vCount(0) = lbList.List(i, 0) Then
                        If vCount(1) = lbList.List(i, 1) Then
                            lbList.List(i, 6) = "SG  " & vAttList(1).TextString
                            lbList.List(i, 7) = "SMARTGRID"
                            GoTo Next_objBlock
                        End If
                    End If
                Next i
            Case Else
                If vAttList(4).TextString = "" Then GoTo Next_objBlock
                
                strLine = vAttList(1).TextString & "," & vAttList(2).TextString & "," & objBlock.InsertionPoint(1)
                strLine = strLine & "," & objBlock.InsertionPoint(0) & "," & vAttList(0).TextString
                Print #1, strLine
                
                vLine = Split(vAttList(4).TextString, " - ")
                If UBound(vLine) < 1 Then GoTo Next_objBlock
                
                vCount = Split(vLine(1), ": ")
                If InStr(vCount(0), "(") > 0 Then
                    vCount(0) = Replace(vCount(0), "(", "")
                    vCount(1) = Replace(vCount(1), ")", "")
                End If
                
                For i = 0 To lbList.ListCount - 1
                    If vCount(0) = lbList.List(i, 0) Then
                        If vCount(1) = lbList.List(i, 1) Then
                            lbList.List(i, 6) = vAttList(1).TextString & "  " & vAttList(2).TextString
                            lbList.List(i, 7) = vAttList(0).TextString
                            GoTo Next_objBlock
                        End If
                    End If
                Next i
        End Select
        
Next_objBlock:
    Next objBlock
    
Clear_objSS:
    objSS.Clear
    objSS.Delete
    
    Close #1
    
    Call ValidateCustomers
End Sub

Private Sub ValidateCustomers()
    If lbList.ListCount < 1 Then Exit Sub
    
    For i = 0 To lbList.ListCount - 1
        If lbList.List(i, 3) = lbList.List(i, 6) Then
            If lbList.List(i, 4) = lbList.List(i, 7) Then lbList.List(i, 8) = "Y"
        End If
        
        If lbList.List(i, 2) = "<>" Then
            If lbList.List(i, 6) = "n/a" Then lbList.List(i, 8) = "Y"
        End If
        
        If lbList.List(i, 2) = " " Then
            If lbList.List(i, 6) = "n/a" Then lbList.List(i, 8) = "Y"
        End If
    Next i
End Sub

Attribute VB_Name = "ValidateML"
Attribute VB_Base = "0{AA5CF7D4-CA0E-49D1-8B6C-C3C284AE6A63}{0A0E81A8-DFA4-4215-80AC-3FDCE682F93D}"
Attribute VB_GlobalNameSpace = False
Attribute VB_Creatable = False
Attribute VB_PredeclaredId = True
Attribute VB_Exposed = False
Attribute VB_TemplateDerived = False
Attribute VB_Customizable = False

Private Sub cbQuit_Click()
    Me.Hide
End Sub

Private Sub cbValidate_Click()
    Dim iDWG, iFrom, iTestDWG As Integer
    Dim strFrom, strTo, strDWG As String
    Dim strTestFrom, strTestTo, strTestDWG As String
    Dim vFrom, vTo As Variant
    
    For i = 0 To lbMatches.ListCount - 1
        strFrom = lbMatches.List(i, 0)
        strDWG = lbMatches.List(i, 1)
        strTo = lbMatches.List(i, 2)
        
        For j = 0 To lbMatches.ListCount - 1
            strTestFrom = lbMatches.List(j, 0)
            strTestDWG = lbMatches.List(j, 1)
            strTestTo = lbMatches.List(j, 2)
            
            If InStr(strFrom, strTestDWG) Then
                If InStr(strTestTo, strDWG) Then
                    strTestTo = Replace(strTestTo, strDWG, "")
                    strTestTo = Replace(strTestTo, "  ", " ")
                    lbMatches.List(j, 2) = strTestTo
                    
                    strFrom = Replace(strFrom, strTestDWG, "")
                    strFrom = Replace(strFrom, "  ", " ")
                    lbMatches.List(i, 0) = strFrom
                End If
                
            End If
        Next j
    Next i
    
    For i = lbMatches.ListCount - 1 To 0 Step -1
        strFrom = Replace(lbMatches.List(i, 0), " ", "")
        strTo = Replace(lbMatches.List(i, 2), " ", "")
        If strFrom = "" Then
            If strTo = "" Then lbMatches.RemoveItem i
        End If
    Next i
End Sub

Private Sub lbMatches_DblClick(ByVal Cancel As MSForms.ReturnBoolean)
    Dim str As String
    Dim strArray As Variant
    Dim viewCoordsB(0 To 2) As Double
    Dim viewCoordsE(0 To 2) As Double
    
    Me.Hide
    
    'str = lbMatches.List(lbMatches.ListIndex)
    'strArray = Split(str, vbTab)
    
    viewCoordsB(0) = lbMatches.List(lbMatches.ListIndex, 3)
    viewCoordsB(1) = lbMatches.List(lbMatches.ListIndex, 4)
    viewCoordsB(2) = 0#
    viewCoordsE(0) = viewCoordsB(0) + 1650 * CDbl(lbMatches.List(lbMatches.ListIndex, 5))
    viewCoordsE(1) = viewCoordsB(1) + 1050 * CDbl(lbMatches.List(lbMatches.ListIndex, 5))
    viewCoordsE(2) = 0#
    
    ThisDrawing.Application.ZoomWindow viewCoordsB, viewCoordsE
    Me.show
End Sub

Private Sub UserForm_Initialize()
    lbMatches.Clear
    lbMatches.ColumnCount = 6
    lbMatches.ColumnWidths = "42;42;200;80;80;20"
    
    Dim objSS3 As AcadSelectionSet
    Dim entBlock As AcadObject
    Dim obrTemp As AcadBlockReference
    Dim attItem2, vTemp As Variant
    Dim mode As Integer
    Dim filterType, filterValue As Variant
    Dim grpCode(0) As Integer
    Dim grpValue(0) As Variant
    Dim vPnt1, vPnt2 As Variant
    Dim str, strList As String
    Dim iCount As Integer
    Dim dPnt1(0 To 2) As Double
    Dim dPnt2(0 To 2) As Double
    
  On Error Resume Next
  
    strList = ""
    iCount = 0
    
    vPnt1 = ThisDrawing.Utility.GetPoint(, "Get BL Corner: ")
    vPnt2 = ThisDrawing.Utility.GetCorner(vPnt1, vbCr & "Get UR Corner: ")
    
    dPnt1(0) = vPnt1(0)
    dPnt1(1) = vPnt1(1)
    dPnt1(2) = vPnt1(2)
    
    dPnt2(0) = vPnt2(0)
    dPnt2(1) = vPnt2(1)
    dPnt2(2) = vPnt2(2)
    
    grpCode(0) = 2
    grpValue(0) = "SS-11x17"
    filterType = grpCode
    filterValue = grpValue
    
    Err = 0
    Set objSS3 = ThisDrawing.SelectionSets.Add("objSS3")
    If Not Err = 0 Then Set objSS3 = ThisDrawing.SelectionSets.List("objSS3")
    
    objSS3.Select acSelectionSetWindow, dPnt1, dPnt2, filterType, filterValue
    
    'MsgBox objSS3.count
    
    Err = 0
    For Each entBlock In objSS3
        Set obrTemp = entBlock
        attItem2 = obrTemp.GetAttributes
        
        vTemp = Split(attItem2(0).TextString, " ")
        
        If UBound(vTemp) < 1 Then GoTo Next_entBlock
        
        lbMatches.AddItem
        lbMatches.List(iCount, 0) = ""
        lbMatches.List(iCount, 1) = vTemp(1)
        lbMatches.List(iCount, 2) = ""
        lbMatches.List(iCount, 3) = obrTemp.InsertionPoint(0)
        lbMatches.List(iCount, 4) = obrTemp.InsertionPoint(1)
        lbMatches.List(iCount, 5) = obrTemp.XScaleFactor
        
        iCount = iCount + 1
Next_entBlock:
        Err = 0
    Next entBlock
    
    tbDWGType.Value = vTemp(0)
    
Exit_Sub:
    objSS3.Delete
    
    Call GetMatchlines
    
End Sub

Private Sub GetMatchlines()
    Dim objSS As AcadSelectionSet
    Dim objEntity As AcadEntity
    Dim objText As AcadText
    
    Dim filterType, filterValue As Variant
    Dim grpCode(0) As Integer
    Dim grpValue(0) As Variant
    Dim strLayer As String
    
    Dim iDWG As Integer
    Dim strDWG As String
    Dim dLL(0 To 2) As Double
    Dim dUR(0 To 2) As Double
    Dim dScale As Double
    
    Dim vTemp As Variant
    Dim iTest As Integer
    Dim strText As String
    
    On Error Resume Next
    
    Select Case tbDWGType.Value
        Case ""
            strLayer = "Integrity Sheets"
        Case "DWG"
            strLayer = "Integrity Sheets"
        Case Else
            strLayer = "Integrity Permits-" & tbDWGType.Value
    End Select
    
    grpCode(0) = 8
    grpValue(0) = strLayer
    filterType = grpCode
    filterValue = grpValue
    
    Err = 0
    Set objSS = ThisDrawing.SelectionSets.Add("objSS")
    If Not Err = 0 Then
        Set objSS = ThisDrawing.SelectionSets.Item("objSS")
        Err = 0
    End If
    
    objSS.Clear
    
    For i = 0 To lbMatches.ListCount - 1
        If lbMatches.List(i, 1) = "" Then GoTo Next_I
        
        strDWG = lbMatches.List(i, 1)
        iDWG = CInt(lbMatches.List(i, 1))
        dLL(0) = CDbl(lbMatches.List(i, 3))
        dLL(1) = CDbl(lbMatches.List(i, 4))
        dLL(2) = 0#
        
        dScale = CDbl(lbMatches.List(i, 5))
        dUR(0) = dLL(0) + (1652 * dScale)
        dUR(1) = dLL(1) + (1052 * dScale)
        dUR(2) = 0#
        
        'MsgBox iDWG & vbCr & dLL(0) & vbCr & dLL(1) & vbCr & dScale
        'MsgBox dUR(0) & vbCr & dUR(1)
        
        objSS.Select acSelectionSetWindow, dLL, dUR, filterType, filterValue
        If Not Err = 0 Then
            MsgBox Err.Description
            Err = 0
        End If
        
        'MsgBox objSS.count
        'GoTo Next_I
        
        For Each objEntity In objSS
            'MsgBox objEntity.ObjectName
            If TypeOf objEntity Is AcadText Then
                Set objText = objEntity
                vTemp = Split(objText.TextString, " ")
                strTest = vTemp(2)
                iTest = CInt(vTemp(2))
                
                'MsgBox objText.TextString & vbCr & vTemp(2) & vbCr & iTest
                
                If iTest > iDWG Then
                    If lbMatches.List(i, 2) = "" Then
                        lbMatches.List(i, 2) = strTest
                    Else
                        lbMatches.List(i, 2) = lbMatches.List(i, 2) & " " & strTest
                    End If
                Else
                    If lbMatches.List(i, 0) = "" Then
                        lbMatches.List(i, 0) = strTest
                    Else
                        lbMatches.List(i, 0) = lbMatches.List(i, 0) & " " & strTest
                    End If
                End If
            End If
        Next objEntity
        
        objSS.Clear
Next_I:
    Next i
End Sub

Attribute VB_Name = "VerifyACAtributes"
Attribute VB_Base = "0{EFAFA3B3-25AB-4C9D-867A-86A9534BFD1A}{48B5B355-0D46-4193-97F7-EBAF7BC4AAA2}"
Attribute VB_GlobalNameSpace = False
Attribute VB_Creatable = False
Attribute VB_PredeclaredId = True
Attribute VB_Exposed = False
Attribute VB_TemplateDerived = False
Attribute VB_Customizable = False
Dim iPoleIndex, iCalloutIndex As Integer
Dim iList As Integer

Private Sub cbCalloutUpdate_Click()
    If Not lbCallout.List(iCalloutIndex, 0) = tbCompany.Value Then
        lbCallout.List(iCalloutIndex, 0) = tbCompany.Value
        lbCallout.List(iCalloutIndex, 4) = "Y"
    End If
    
    If Not lbCallout.List(iCalloutIndex, 1) = tbHeight.Value Then
        lbCallout.List(iCalloutIndex, 1) = tbHeight.Value
        lbCallout.List(iCalloutIndex, 4) = "Y"
    End If
    
    If Not lbCallout.List(iCalloutIndex, 2) = tbMR.Value Then
        lbCallout.List(iCalloutIndex, 2) = tbMR.Value
        lbCallout.List(iCalloutIndex, 4) = "Y"
    End If
    
    cbCalloutUpdate.Enabled = False
End Sub

Private Sub cbCancel_Click()
    lbPole.Clear
    lbCallout.Clear
    
    Me.Hide
End Sub

Private Sub cbPoleUpdate_Click()
    If Not lbPole.List(iPoleIndex, 1) = tbText.Value Then
        lbPole.List(iPoleIndex, 1) = tbText.Value
        lbPole.List(iPoleIndex, 2) = "Y"
    End If
    
    tbText.Value = ""
    cbPoleUpdate.Enabled = False
End Sub

Private Sub cbSave_Click()
    Me.Hide
End Sub

Private Sub lbCallout_DblClick(ByVal Cancel As MSForms.ReturnBoolean)
    iList = 1
    iCalloutIndex = lbCallout.ListIndex
    
    tbCompany.Value = lbCallout.List(iCalloutIndex, 0)
    tbHeight.Value = lbCallout.List(iCalloutIndex, 1)
    tbMR.Value = lbCallout.List(iCalloutIndex, 2)
    
    cbCalloutUpdate.Enabled = True
    tbCompany.SetFocus
End Sub

Private Sub lbPole_DblClick(ByVal Cancel As MSForms.ReturnBoolean)
    iList = 0
    iPoleIndex = lbPole.ListIndex
    tbText.Value = lbPole.List(iPoleIndex, 1)
    
    cbPoleUpdate.Enabled = True
    tbText.SetFocus
End Sub

Private Sub UserForm_Initialize()
    lbPole.ColumnCount = 3
    lbPole.ColumnWidths = "72;108;24"
    
    lbCallout.ColumnCount = 5
    lbCallout.ColumnWidths = "96;36;84;36;36"
End Sub

Attribute VB_Name = "VerifyAttachmentCallouts"
Attribute VB_Base = "0{F8B22FD3-2670-43D4-A4A4-F80CE289B796}{04897444-8883-4580-9213-4F5891FC7F3D}"
Attribute VB_GlobalNameSpace = False
Attribute VB_Creatable = False
Attribute VB_PredeclaredId = True
Attribute VB_Exposed = False
Attribute VB_TemplateDerived = False
Attribute VB_Customizable = False
Dim objSS1 As AcadSelectionSet
Dim objSS2 As AcadSelectionSet
    
Private Sub cbFindDiffer_Click()
    If lbAll.ListCount < 1 Then Exit Sub
    
    Dim vBlock, vCallout As Variant
    Dim strBlock, strCallout As String
    
    For i = 0 To lbAll.ListCount - 1
        If lbAll.List(i, 1) = "" Then GoTo Next_line
        If lbAll.List(i, 2) = "" Then GoTo Next_line
        
        vBlock = Split(lbAll.List(i, 1), ";;")
        vCallout = Split(lbAll.List(i, 2), ";;")
        
        For j = 0 To UBound(vBlock)
            For k = 0 To UBound(vCallout)
                If vBlock(j) = vCallout(k) Then
                    vBlock(j) = ""
                    vCallout(k) = ""
                    
                    GoTo Next_Item
                End If
            Next k
Next_Item:
        Next j
        
        strBlock = ""
        For j = 0 To UBound(vBlock)
            If Not vBlock(j) = "" Then
                If strBlock = "" Then
                    strBlock = vBlock(j)
                Else
                    strBlock = strBlock & ";;" & vBlock(j)
                End If
            End If
        Next j
        
        strCallout = ""
        For j = 0 To UBound(vCallout)
            If Not vCallout(j) = "" Then
                If strCallout = "" Then
                    strCallout = vCallout(j)
                Else
                    strCallout = strCallout & ";;" & vCallout(j)
                End If
            End If
        Next j
        
        lbAll.List(i, 1) = strBlock
        lbAll.List(i, 2) = strCallout
Next_line:
    Next i
    
    For i = lbAll.ListCount - 1 To 0 Step -1
        If lbAll.List(i, 1) = "" Then
            If lbAll.List(i, 2) = "" Then lbAll.RemoveItem i
        End If
    Next i
    
    tbListCount.Value = lbAll.ListCount
End Sub

Private Sub cbGetBlocks_Click()
    Dim filterType, filterValue As Variant
    Dim grpCode(0) As Integer
    Dim grpValue(0) As Variant
    Dim objBlock As AcadBlockReference
    Dim vAttList As Variant
    Dim vItem, vLine, vTemp As Variant
    Dim vPnt1, vPnt2, vCoords As Variant
    Dim strPole, strCompany, strAttach As String
    Dim strExist, strProp, strTemp As String
    Dim strAttachments, strExtra As String
    Dim iFeet, iInch, iDiff As Integer
    
    On Error Resume Next
    
    Me.Hide
    
    lbAll.Clear
        
    Err = 0
    vPnt1 = ThisDrawing.Utility.GetPoint(, "Get BL Corner: ")
    vPnt2 = ThisDrawing.Utility.GetCorner(vPnt1, vbCr & "Get UR Corner: ")
    If Not Err = 0 Then GoTo Exit_Sub
    
    grpCode(0) = 2
    grpValue(0) = "sPole"
    filterType = grpCode
    filterValue = grpValue
    
    objSS1.Select acSelectionSetWindow, vPnt1, vPnt2, filterType, filterValue
    
    For n = 0 To objSS1.count - 1
    'For Each objBlock In objSS
        Set objBlock = objSS1.Item(n)
        vAttList = objBlock.GetAttributes
        If vAttList(0).TextString = "POLE" Then GoTo Next_objBlock
        If vAttList(0).TextString = "" Then GoTo Next_objBlock
        
        strAttachments = ""
        
        lbAll.AddItem vAttList(0).TextString, 0
        vCoords = objBlock.InsertionPoint
        
        lbAll.List(0, 1) = "x"
        lbAll.List(0, 2) = ""
        lbAll.List(0, 3) = vCoords(0) & "," & vCoords(1)
        lbAll.List(0, 4) = n
        
        For i = 9 To 23
            If Not vAttList(i).TextString = "" Then
                vLine = Split(UCase(vAttList(i).TextString), " ")
                
                Select Case i
                    Case Is = 9
                        For j = 0 To UBound(vLine)
                            If strAttachments = "" Then
                                strAttachments = "NEUTRAL=" & vLine(j)
                            Else
                                strAttachments = strAttachments & ";;" & "NEUTRAL=" & vLine(j)
                            End If
                        Next j
                    Case Is = 10
                        For j = 0 To UBound(vLine)
                            If strAttachments = "" Then
                                strAttachments = "TRANSFORMER=" & vLine(j)
                            Else
                                strAttachments = strAttachments & ";;" & "TRANSFORMER=" & vLine(j)
                            End If
                        Next j
                    Case Is = 11
                        For j = 0 To UBound(vLine)
                            If strAttachments = "" Then
                                strAttachments = "LOW POWER=" & vLine(j)
                            Else
                                strAttachments = strAttachments & ";;" & "LOW POWER=" & vLine(j)
                            End If
                        Next j
                    Case Is = 12
                        For j = 0 To UBound(vLine)
                            If strAttachments = "" Then
                                strAttachments = "ANTENNA=" & vLine(j)
                            Else
                                strAttachments = strAttachments & ";;" & "ANTENNA=" & vLine(j)
                            End If
                        Next j
                    Case Is = 13
                        For j = 0 To UBound(vLine)
                            If strAttachments = "" Then
                                strAttachments = "ST LT CIR=" & vLine(j)
                            Else
                                strAttachments = strAttachments & ";;" & "ST LT CIR=" & vLine(j)
                            End If
                        Next j
                    Case Is = 14
                        For j = 0 To UBound(vLine)
                            If strAttachments = "" Then
                                strAttachments = "ST LT=" & vLine(j)
                            Else
                                strAttachments = strAttachments & ";;" & "ST LT=" & vLine(j)
                            End If
                        Next j
                    Case Is = 15
                        For j = 0 To UBound(vLine)
                            If strAttachments = "" Then
                                strAttachments = "NEW 6M=" & vLine(j)
                            Else
                                strAttachments = strAttachments & ";;" & "NEW 6M=" & vLine(j)
                            End If
                        Next j
                    Case Else
                        vTemp = Split(UCase(vAttList(i).TextString), "=")
                        vLine = Split(vTemp(1), " ")
                        
                        If strAttachments = "" Then
                            strAttachments = vTemp(0) & "=" & vLine(0)
                        Else
                            strAttachments = strAttachments & ";;" & vTemp(0) & "=" & vLine(0)
                        End If
                        
                        If UBound(vLine) > 0 Then
                            For j = 1 To UBound(vLine)
                                strAttachments = strAttachments & ";;" & vTemp(0) & "=" & vLine(j)
                            Next j
                        End If
                End Select
            End If
        Next i
        
        If strAttachments = "" Then
            lbAll.List(0, 1) = ""
        Else
            lbAll.List(0, 1) = strAttachments
        End If
        
Next_objBlock:
    'Next objBlock
    Next n
    
    'objSS.Clear
    
    grpCode(0) = 2
    grpValue(0) = "pole_attach"
    filterType = grpCode
    filterValue = grpValue
    
    objSS2.Select acSelectionSetWindow, vPnt1, vPnt2, filterType, filterValue
    
    For n = 0 To objSS2.count - 1
    'For Each objBlock In objSS
        Set objBlock = objSS2.Item(n)
        vAttList = objBlock.GetAttributes
        If vAttList(0).TextString = "" Then GoTo Next_Callout
        
        strExtra = ""
        strPole = vAttList(0).TextString
        strCompany = vAttList(2).TextString
        If InStr(strCompany, " C-WIRE") > 0 Then
            strExtra = "C"
            strCompany = Replace(strCompany, " C-WIRE", "")
        End If
        
        If InStr(strCompany, " DROP") > 0 Then
            If strExtra = "" Then
                strExtra = "D"
            Else
                strExtra = strExtra & "D"
            End If
            strCompany = Replace(strCompany, " DROP", "")
        End If
        
        If InStr(strCompany, " OHG") > 0 Then
            If strExtra = "" Then
                strExtra = "O"
            Else
                strExtra = strExtra & "O"
            End If
            strCompany = Replace(strCompany, " OHG", "")
        End If
        
        If InStr(strCompany, "LASH TO ") > 0 Then
            If strExtra = "" Then
                strExtra = "V"
            Else
                strExtra = strExtra & "V"
            End If
            strCompany = Replace(strCompany, "LASH TO ", "")
        End If
        
        strExist = Replace(vAttList(3).TextString, "'", "-")
        strExist = Replace(strExist, """", "")
        
        If Not vAttList(4).TextString = "" Then
            strTemp = UCase(vAttList(4).TextString)
            
            Select Case Left(strTemp, 1)
                Case "A"
                    strExist = strExist & "X"
                Case "F"
                    strCompany = "NEW 6M"
                    strExist = strExist & "F"
                Case "L", "R"
                    vLine = Split(strExist, "-")
                    iProp = CInt(vLine(0)) * 12
                    If UBound(vLine) > 0 Then iProp = iProp + CInt(vLine(1))
                    
                    vLine = Split(strTemp, " ")
                    strAttach = Replace(vLine(1), """", "")
                    iDiff = CInt(strAttach)
                    
                    If Left(strTemp, 1) = "L" Then
                        iExist = iProp + iDiff
                    Else
                        iExist = iProp - iDiff
                    End If
                    
                    iFeet = Int(iExist / 12)
                    iInch = iExist - (iFeet * 12)
                    
                    If iInch < 0 Then
                        While iInch < 0
                            iInch = iInch + 12
                            iFeet = iFeet - 1
                        Wend
                    End If
                    
                    If iInch > 11 Then
                        While iInch > 11
                            iInch = iInch - 12
                            iFeet = iFeet + 1
                        Wend
                    End If
                    
                    strExist = "(" & iFeet & "-" & iInch & ")" & strExist
                Case "M"
                    strCompany = "NEW 6M"
                    strExist = strExist & "T"
                Case "N"
                    strCompany = "NEW 6M"
                    strExist = strExist
                Case "T"
                    strExist = "(" & strExist & ")" & strExist
            End Select
        End If
        
        strAttachments = strCompany & "=" & strExist & strExtra
        
        If lbAll.ListCount > 0 Then
            For i = 0 To lbAll.ListCount - 1
                If lbAll.List(i, 0) = strPole Then
                    lbAll.List(i, 4) = lbAll.List(i, 4) & ";;" & n
                    
                    If lbAll.List(i, 2) = "" Then
                        lbAll.List(i, 2) = strAttachments
                    Else
                        lbAll.List(i, 2) = strAttachments & ";;" & lbAll.List(i, 2)
                    End If
                End If
            Next i
        End If
        
Next_Callout:
    'Next objBlock
    Next n
    
Exit_Sub:
    'objSS.Clear
    'objSS.Delete
    
    tbListCount.Value = lbAll.ListCount
    Me.show
End Sub

Private Sub cbQuit_Click()
    Me.Hide
    Unload Me
End Sub

Private Sub lbAll_DblClick(ByVal Cancel As MSForms.ReturnBoolean)
    Dim vLine As Variant
    Dim viewCoordsB(0 To 2) As Double
    Dim viewCoordsE(0 To 2) As Double
    
    Me.Hide
    
    vLine = Split(lbAll.List(lbAll.ListIndex, 3), ",")
    
    viewCoordsB(0) = CDbl(vLine(0)) - 300
    viewCoordsB(1) = CDbl(vLine(1)) - 300
    viewCoordsB(2) = 0#
    viewCoordsE(0) = viewCoordsB(0) + 600
    viewCoordsE(1) = viewCoordsB(1) + 600
    viewCoordsE(2) = 0#
    
    ThisDrawing.Application.ZoomWindow viewCoordsB, viewCoordsE
    
    Dim objBlock As AcadBlockReference
    Dim vAtt As Variant
    Dim strLine As String
    'Dim iIndex As Integer
    
    Load VerifyACAtributes
        VerifyACAtributes.Caption = lbAll.List(lbAll.ListIndex, 0) & " " & VerifyACAtributes.Caption
        vLine = Split(lbAll.List(lbAll.ListIndex, 4), ";;")
        
        Set objBlock = objSS1.Item(CInt(vLine(0)))
        vAtt = objBlock.GetAttributes
        
        For i = 9 To 23
            VerifyACAtributes.lbPole.AddItem vAtt(i).TagString
            VerifyACAtributes.lbPole.List(i - 9, 1) = vAtt(i).TextString
            VerifyACAtributes.lbPole.List(i - 9, 2) = ""
        Next i
        
        If UBound(vLine) > 0 Then
            For i = 1 To UBound(vLine)
                Set objBlock = objSS2.Item(CInt(vLine(i)))
                vAtt = objBlock.GetAttributes
                
                VerifyACAtributes.lbCallout.AddItem vAtt(2).TextString, 0
                'iIndex = VerifyACAtributes.lbCallout.ListCount - 1
                VerifyACAtributes.lbCallout.List(0, 1) = vAtt(3).TextString
                VerifyACAtributes.lbCallout.List(0, 2) = vAtt(4).TextString
                VerifyACAtributes.lbCallout.List(0, 3) = vLine(i)
                VerifyACAtributes.lbCallout.List(0, 4) = ""
            Next i
        End If
        
        VerifyACAtributes.show
        
        If VerifyACAtributes.lbPole.ListCount = 0 Then GoTo No_Updates
        
        Set objBlock = objSS1.Item(CInt(vLine(0)))
        vAtt = objBlock.GetAttributes
            
        For i = 0 To VerifyACAtributes.lbPole.ListCount - 1
            If VerifyACAtributes.lbPole.List(i, 2) = "Y" Then
                vAtt(i + 9).TextString = VerifyACAtributes.lbPole.List(i, 1)
            End If
        Next i
            
        objBlock.Update
        
        For i = 0 To VerifyACAtributes.lbCallout.ListCount - 1
            If VerifyACAtributes.lbCallout.List(i, 4) = "Y" Then
                Set objBlock = objSS2.Item(CInt(VerifyACAtributes.lbCallout.List(i, 3)))
                vAtt = objBlock.GetAttributes
                
                vAtt(2).TextString = VerifyACAtributes.lbCallout.List(i, 0)
                vAtt(3).TextString = VerifyACAtributes.lbCallout.List(i, 1)
                vAtt(4).TextString = VerifyACAtributes.lbCallout.List(i, 2)
                
                objBlock.Update
            End If
        Next i
        
No_Updates:
    Unload VerifyACAtributes
    
    Me.show
End Sub

Private Sub lbAll_KeyDown(ByVal KeyCode As MSForms.ReturnInteger, ByVal Shift As Integer)
    Select Case KeyCode
        Case vbKeyReturn
            MsgBox lbAll.List(lbAll.ListIndex, 4)
    End Select
End Sub

Private Sub UserForm_Initialize()
    lbAll.ColumnCount = 5
    lbAll.ColumnWidths = "120;192;180;6;6"
    
    On Error Resume Next
    
    Err = 0
    Set objSS1 = ThisDrawing.SelectionSets.Add("objSS1")
    If Not Err = 0 Then
        Set objSS1 = ThisDrawing.SelectionSets.Item("objSS1")
        objSS1.Clear
    End If
    
    Err = 0
    Set objSS2 = ThisDrawing.SelectionSets.Add("objSS2")
    If Not Err = 0 Then
        Set objSS2 = ThisDrawing.SelectionSets.Item("objSS2")
        objSS2.Clear
    End If
End Sub

Private Sub UserForm_Terminate()
    objSS1.Clear
    objSS1.Delete
    
    objSS2.Clear
    objSS2.Delete
End Sub

Attribute VB_Name = "VerifyUnits"
Attribute VB_Base = "0{E6ABEC6C-1A5B-42C6-844D-10CCA942469F}{AD3BAF23-2EC6-43FC-B00E-635283813F51}"
Attribute VB_GlobalNameSpace = False
Attribute VB_Creatable = False
Attribute VB_PredeclaredId = True
Attribute VB_Exposed = False
Attribute VB_TemplateDerived = False
Attribute VB_Customizable = False
Private Sub cbExport_Click()
    If lbUnits.ListCount < 1 Then Exit Sub
    
    Dim strPath, strName, strFile As String
    Dim vTemp As Variant
    
    strPath = ThisDrawing.Path
    strName = ThisDrawing.Name
    vTemp = Split(strName, " ")
    
    strFile = strPath & "\" & vTemp(0) & " Unit Errors.csv"
    
    Open strFile For Output As #1
    
    Print #1, "Structure Number,Block Units,Callout Units"
    
    For i = 0 To lbUnits.ListCount - 1
        Print #1, lbUnits.List(i, 0) & "," & lbUnits.List(i, 1) & "," & lbUnits.List(i, 2)
    Next i
    
    Close #1
End Sub

Private Sub cbFindDiffer_Click()
    If lbUnits.ListCount < 1 Then Exit Sub
    
    Dim vPole, vUnit As Variant
    Dim strPole, strUnit As String
    
    For i = lbUnits.ListCount - 1 To 0 Step -1
        vPole = Split(lbUnits.List(i, 1), ";;")
        vUnit = Split(lbUnits.List(i, 2), ";;")
        
        For j = 0 To UBound(vPole)
            For k = 0 To UBound(vUnit)
                If vPole(j) = vUnit(k) Then
                    vPole(j) = ""
                    vUnit(k) = ""
                    GoTo Next_Pole
                End If
            Next k
Next_Pole:
        Next j
        
        strPole = ""
        For j = 0 To UBound(vPole)
            If Not vPole(j) = "" Then
                If strPole = "" Then
                    strPole = vPole(j)
                Else
                    strPole = strPole & " & " & vPole(j)
                End If
            End If
        Next j
        strPole = Replace(strPole, "+", "")
        
        strUnit = ""
        For j = 0 To UBound(vUnit)
            If Not vUnit(j) = "" Then
                If strUnit = "" Then
                    strUnit = vUnit(j)
                Else
                    strUnit = strUnit & " & " & vUnit(j)
                End If
            End If
        Next j
        strUnit = Replace(strUnit, "+", "")
        
        If strUnit = "" Then
            If strPole = "" Then
                lbUnits.RemoveItem i
                GoTo Next_I
            End If
        End If
        
        lbUnits.List(i, 1) = strPole
        
        lbUnits.List(i, 2) = strUnit
Next_I:
    Next i
    
    tbListCount.Value = lbUnits.ListCount
End Sub

Private Sub cbGetBlocks_Click()
    Dim objSS As AcadSelectionSet
    Dim objBlock As AcadBlockReference
    Dim vAttList As Variant
    Dim filterType, filterValue As Variant
    Dim vPnt1, vPnt2 As Variant
    Dim grpCode(0) As Integer
    Dim grpValue(0) As Variant
    Dim dPnt1(0 To 2) As Double
    Dim dPnt2(0 To 2) As Double

    grpCode(0) = 2
    grpValue(0) = "sPole,sPed,sHH,sFP,sPanel,sMH"
    'grpValue(0) = "pole_unit"
    filterType = grpCode
    filterValue = grpValue
    
    lbUnits.Clear
    
  On Error Resume Next
    Me.Hide
    
    vPnt1 = ThisDrawing.Utility.GetPoint(, "Get BL Corner: ")
    vPnt2 = ThisDrawing.Utility.GetCorner(vPnt1, vbCr & "Get UR Corner: ")
    
    dPnt1(0) = vPnt1(0)
    dPnt1(1) = vPnt1(1)
    dPnt1(2) = vPnt1(2)
    
    dPnt2(0) = vPnt2(0)
    dPnt2(1) = vPnt2(1)
    dPnt2(2) = vPnt2(2)
    
    Set objSS = ThisDrawing.SelectionSets.Add("objSS")
    If Not Err = 0 Then
        Set objSS = ThisDrawing.SelectionSets.Item("objSS")
        objSS.Clear
        Err = 0
    End If
    objSS.Select acSelectionSetWindow, dPnt1, dPnt2, filterType, filterValue
    
    For Each objBlock In objSS
        vAttList = objBlock.GetAttributes
        
        If vAttList(0).TextString = "" Then GoTo Next_objBlock
        If vAttList(0).TextString = "POLE" Then GoTo Next_objBlock
        If vAttList(0).TextString = "PED" Then GoTo Next_objBlock
        If vAttList(0).TextString = "HH" Then GoTo Next_objBlock
        If vAttList(0).TextString = "PANEL" Then GoTo Next_objBlock
        If vAttList(0).TextString = "MH" Then GoTo Next_objBlock
        
        lbUnits.AddItem vAttList(0).TextString
        Select Case objBlock.Name
            Case "sPole"
                lbUnits.List(lbUnits.ListCount - 1, 1) = vAttList(27).TextString
            Case Else
                lbUnits.List(lbUnits.ListCount - 1, 1) = vAttList(7).TextString
        End Select
        lbUnits.List(lbUnits.ListCount - 1, 2) = ""
        lbUnits.List(lbUnits.ListCount - 1, 3) = objBlock.InsertionPoint(0) & "," & objBlock.InsertionPoint(1)
Next_objBlock:
    Next objBlock
    
    objSS.Clear

    grpCode(0) = 2
    grpValue(0) = "pole_unit"
    filterType = grpCode
    filterValue = grpValue
    
    objSS.Select acSelectionSetWindow, dPnt1, dPnt2, filterType, filterValue
    
    For Each objBlock In objSS
        vAttList = objBlock.GetAttributes
        
        For i = 0 To lbUnits.ListCount - 1
            If vAttList(0).TextString = lbUnits.List(i, 0) Then
                If lbUnits.List(i, 2) = "" Then
                    lbUnits.List(i, 2) = vAttList(3).TextString
                Else
                    lbUnits.List(i, 2) = lbUnits.List(i, 2) & ";;" & vAttList(3).TextString
                End If
                
                GoTo Next_Pole_Unit
            End If
        Next i
            
        lbUnits.AddItem vAttList(0).TextString
        lbUnits.List(lbUnits.ListCount - 1, 1) = ""
        lbUnits.List(lbUnits.ListCount - 1, 2) = vAttList(3).TextString
        lbUnits.List(lbUnits.ListCount - 1, 3) = objBlock.InsertionPoint(0) & "," & objBlock.InsertionPoint(1)
        
Next_Pole_Unit:
    Next objBlock
    
Exit_Sub:
    objSS.Clear
    objSS.Delete
    
    tbListCount.Value = lbUnits.ListCount
    
    Me.show
End Sub

Private Sub cbQuit_Click()
    Me.Hide
End Sub

Private Sub lbUnits_DblClick(ByVal Cancel As MSForms.ReturnBoolean)
    Dim vCoords As Variant
    Dim viewCoordsB(0 To 2) As Double
    Dim viewCoordsE(0 To 2) As Double
    
    Me.Hide
    
    vCoords = Split(lbUnits.List(lbUnits.ListIndex, 3), ",")
    
    viewCoordsB(0) = CDbl(vCoords(0)) - 300
    viewCoordsB(1) = CDbl(vCoords(1)) - 300
    viewCoordsB(2) = 0#
    viewCoordsE(0) = CDbl(vCoords(0)) + 300
    viewCoordsE(1) = CDbl(vCoords(1)) + 300
    viewCoordsE(2) = 0#
    
    ThisDrawing.Application.ZoomWindow viewCoordsB, viewCoordsE
    Me.show
End Sub

Private Sub UserForm_Initialize()
    lbUnits.ColumnCount = 4
    lbUnits.ColumnWidths = "120;192;180;6"
End Sub

Attribute VB_Name = "aaPlaceCable"
Attribute VB_Base = "0{0EE5F767-FF9D-4A09-85EB-21A4BBEF30EB}{099EA323-B9DF-45C3-AE1A-2C7901C05A9B}"
Attribute VB_GlobalNameSpace = False
Attribute VB_Creatable = False
Attribute VB_PredeclaredId = True
Attribute VB_Exposed = False
Attribute VB_TemplateDerived = False
Attribute VB_Customizable = False
Const Pi = 3.14159265358979

Private Sub PlaceCable()
    If tbNumber.Value = "" Then Exit Sub
    
    Dim objEntity As AcadEntity
    Dim objLine As AcadLWPolyline
    Dim objSpan As AcadBlockReference
    Dim objPole As AcadBlockReference
    Dim objPrevious As AcadBlockReference
    Dim strLayer, strTextLayer, strAnchorLayer As String
    Dim strCable, strCounts, strLine As String
    Dim strResult, strNote As String
    Dim strRoute As String
    Dim iNumber, iIncrement As Integer
    Dim vBasePnt As Variant
    Dim vAttItem, vAttPrevious As Variant
    Dim vInfo, vAttList As Variant
    Dim X(0 To 2), Y(0 To 2), Z(0 To 2) As Double
    Dim dInsertPnt(0 To 2), dLeaderPnt(0 To 3) As Double
    Dim dTextPnt(0 To 2) As Double
    Dim dInfo(0 To 6) As Double
    Dim xDiff, yDiff, dDist As Double
    Dim dRotate, dScale, distance As Double
    'Dim dScale As Double
    Dim iCounter As Integer
    
    strLayer = "Integrity " & cbStatus.Value
    strTextLayer = "Integrity " & cbStatus.Value
    strAnchorLayer = "Integrity " & cbStatus.Value
    If cbType.Value = "CO" Then
            If cbSuffix.Value = "E" Then strAnchorLayer = "Integrity Existing"
    End If
    
    strCable = cbType.Value & "(" & cbSize.Value & ")"
    If Not cbSuffix.Value = "" Then strCable = strCable & cbSuffix.Value
    
    strCounts = Replace(tbCounts.Value, vbLf, "")
    strCounts = Replace(strCounts, vbCr, " + ")
    
    strRoute = UCase(tbRoute.Value)
    iNumber = CInt(tbNumber.Value)
    iIncrement = CInt(tbIncrement.Value)
    
    Me.Hide
    
  On Error Resume Next
    
    ThisDrawing.Utility.GetEntity objEntity, vBasePnt, "From Pole: "
    If Not Err = 0 Then GoTo Exit_Sub
    
    If TypeOf objEntity Is AcadBlockReference Then
        Set objPrevious = objEntity
    Else
        GoTo Exit_Sub
    End If
    
    X(1) = objPrevious.InsertionPoint(0)
    Y(1) = objPrevious.InsertionPoint(1)
    Z(1) = 0#
    
    X(2) = 0#
    Y(2) = 0#
    Z(2) = 0#
    
    dScale = 1#
    iCounter = 0
    
Add_Another:
    
    ThisDrawing.Utility.GetEntity objEntity, vBasePnt, "To Pole: "
    If Not Err = 0 Then GoTo Stop_Placing
    
    If TypeOf objEntity Is AcadBlockReference Then
        Set objPole = objEntity
    Else
        GoTo Stop_Placing
    End If
    
    X(0) = objPole.InsertionPoint(0)
    Y(0) = objPole.InsertionPoint(1)
    Z(0) = 0#
    
    If iCounter = 0 Then
        X(2) = X(0)
        Y(2) = Y(0)
        Z(2) = 0#
    End If
    
    dLeaderPnt(0) = X(1)
    dLeaderPnt(1) = Y(1)
    dLeaderPnt(2) = X(0)
    dLeaderPnt(3) = Y(0)
    
    If cbCable.Value = True Then
        Set objLine = ThisDrawing.ModelSpace.AddLightWeightPolyline(dLeaderPnt)
        objLine.Layer = strLayer
        objLine.Update
    End If
    
    dTextPnt(0) = (dLeaderPnt(0) + dLeaderPnt(2)) / 2
    dTextPnt(1) = (dLeaderPnt(1) + dLeaderPnt(3)) / 2
    dTextPnt(2) = 0#
      
    xDiff = dLeaderPnt(2) - dLeaderPnt(0)
    yDiff = dLeaderPnt(3) - dLeaderPnt(1)
        
    If (yDiff = 0) Then
        dRotate = 0
    ElseIf (xDiff = 0) Then
        dRotate = Pi / 2
    Else
        dRotate = Atn(yDiff / xDiff)
    End If
    distance = Int(Math.Sqr(xDiff ^ 2 + yDiff ^ 2)) + 1
    
    Set objSpan = ThisDrawing.ModelSpace.InsertBlock(dTextPnt, "cable_span", dScale, dScale, dScale, dRotate)
    objSpan.Layer = strTextLayer
    
    vAttItem = objSpan.GetAttributes
    
    vAttItem(0).TextString = ""
    vAttItem(1).TextString = strCable
    vAttItem(2).TextString = distance & "'"
    objSpan.Update
    
    vAttPrevious = objPrevious.GetAttributes
    
    If cbGuy.Value = True Or cbExistGuys.Value = True Then
        If iCounter = 0 Then
            strTemp = PlaceGuy((X(1)), (Y(1)), (X(0)), (Y(0)), (X(0)), (Y(0)))
            'vAttPrevious(0).TextString = strRoute & iNumber
            'strTemp = "+PM2A=1;;"
        Else
            strTemp = PlaceGuy((X(1)), (Y(1)), (X(0)), (Y(0)), (X(2)), (Y(2)))
            'strTemp = ""
        End If
        
        If cbExistGuys.Value = True Then strTemp = ""
            
        If Not strTemp = "" Then
            If vAttPrevious(27).TextString = "" Then
                vAttPrevious(27).TextString = strTemp
            Else
                vAttPrevious(27).TextString = vAttPrevious(27).TextString & ";;" & strTemp
            End If
        End If
    End If
    objPrevious.Update
    'iCounter = 1
    
    strLine = ""
    
    strResult = ThisDrawing.Utility.GetString(0, "Need a Closure [y/n]:(n)")
    If Err = 0 Then
        If LCase(Left(strResult, 1)) = "y" Then
            dInfo(0) = distance
            dInfo(1) = dScale
            dInfo(2) = dRotate
            dInfo(3) = X(0)
            dInfo(4) = Y(0)
            dInfo(5) = X(1)
            dInfo(6) = Y(1)
            
            vInfo = dInfo
            Call PlaceClosure(vInfo)
            
            strLine = "+" & cbType.Value & "(" & cbSize.Value & ")" & cbSuffix.Value & "=" & tbCoil.Value & "  LOOP;;"
            Select Case cbType.Value
                Case "CO", "ADSS"
                    strLine = strLine & "+HACO("
                Case Else
                    strLine = strLine & "+HBFO("
            End Select
            strLine = strLine & cbSize.Value & ")=1  " & cbClosure.Value
        End If
    Else
        Err = 0
    End If
    
    If strLine = "" Then
        strLine = "+" & cbType.Value & "(" & cbSize.Value & ")" & cbSuffix.Value & "=" & distance & ";;"
    Else
        strLine = "+" & cbType.Value & "(" & cbSize.Value & ")" & cbSuffix.Value & "=" & distance & ";;" & strLine
    End If
    
    strNote = strRoute & " - " & (iNumber) & ";;" & FixStructureNumber(vAttPrevious(0).TextString) & ";;" & distance & ";;"
    strNote = strNote & tbTrunk.Value & ":0:0;; ;; ;; ;; ;;" & strCable & " / " & strCounts
       
    vAttList = objPole.GetAttributes
    
    If cbType.Value = "CO" Then
        Select Case Left(UCase(vAttList(8).TextString), 1)
            Case "M", "m"
                strLine = strLine & ";;+PM2A=1"
        End Select
    End If
    
    vAttList(0).TextString = strRoute & iNumber
    
    If vAttList(27).TextString = "" Then
        vAttList(27).TextString = strLine
    Else
        vAttList(27).TextString = vAttList(27).TextString & ";;" & strLine
    End If
    
    vAttList(28).TextString = strNote
    
    objPole.Update
    
    Err = 0
    strLine = ""
    iCounter = 1
    iNumber = iNumber + iIncrement
    
    X(2) = X(1)
    Y(2) = Y(1)
    Z(2) = Z(1)
    
    X(1) = X(0)
    Y(1) = Y(0)
    Z(1) = Z(0)
    
    Set objPrevious = objPole
    
    GoTo Add_Another    '<--------------------------------------------------------------Get Another Pole
    
Stop_Placing:
    If Not iCounter = 0 Then
        If cbGuy.Value = True Or cbExistGuys.Value = True Then
            strTemp = PlaceGuy((X(1)), (Y(1)), (X(2)), (Y(2)), (X(2)), (Y(2)))
        
            strLine = ";;+PE1-3G=1;;+PF1-5A=1;;+PM11=1"
        End If
        
        'strNote = strRoute & " - " & (iNumber + iIncrement) & ";;" & strRoute & " - " & iNumber & ";;" & distance & ";;"
        'strNote = strNote & " ;; ;; ;; ;; ;;" & strCable
        
        iNumber = iNumber + iIncrement
        
        vAttList = objPole.GetAttributes
        'vAttList(0).TextString = strRoute & iNumber
        
        If vAttList(27).TextString = "" Then
            vAttList(27).TextString = strLine
        Else
            vAttList(27).TextString = vAttList(27).TextString & ";;" & strLine
        End If
        
        'vAttList(28).TextString = strNote
        
        objPole.Update
    End If
    
Exit_Sub:
    
    tbNumber.Value = iNumber
    
    Me.show
End Sub

Private Sub cbExistGuys_Click()
    If cbExistGuys.Value = True Then cbGuy.Value = False
End Sub

Private Sub cbGuy_Click()
    If cbGuy.Value = True Then cbExistGuys.Value = False
End Sub

Private Sub cbPlace_Click()
    Call PlaceCable
    
    'Save data to pole attribute (28)
    'Save data to other attribute (8) when ready and created
    
End Sub

Private Sub cbSize_Change()
    Dim strPath As String
    
    strPath = LCase(ThisDrawing.Path)
    
    If InStr(strPath, "united") > 0 Then
        Select Case CInt(cbSize.Value)
            Case Is < 49
                cbClosure.Value = "FOSC A"
            Case Is > 96
                cbClosure.Value = "FOSC D"
            Case Else
                cbClosure.Value = "FOSC B"
        End Select
    Else
        Select Case CInt(cbSize.Value)
            Case Is < 25
                cbClosure.Value = "G4"
            Case Is > 144
                cbClosure.Value = "G6"
            Case Else
                cbClosure.Value = "G5"
        End Select
    End If
    
    Call UpdateCounts
End Sub

Private Sub cbSuffix_Change()
    If cbType.Value = "CO" Then
        If cbSuffix.Value = "E" Then
            cbGuy.Value = False
            cbExistGuys.Value = True
        Else
            cbGuy.Value = True
            cbExistGuys.Value = False
        End If
    Else
        cbGuy.Value = False
    End If
End Sub

Private Sub cbSuffix_Exit(ByVal Cancel As MSForms.ReturnBoolean)
    cbSuffix.Value = UCase(cbSuffix.Value)
End Sub

Private Sub cbType_Change()
    cbSuffix.Clear
    cbExistGuys.Value = False
    
    Select Case cbType.Value
        Case "CO"
            cbSuffix.AddItem "E"
            cbSuffix.AddItem "6M"
            cbSuffix.AddItem "6M-EHS"
            cbSuffix.AddItem "10M"
            cbSuffix.AddItem "16M"
            cbSuffix.Value = "6M-EHS"
            
            'cbClosure.Value = "Aerial"
            cbExistGuys.Value = False
            cbGuy.Value = True
            tbCoil.Value = "100"
        Case "ADSS"
            'cbClosure.Value = "Aerial"
            cbGuy.Value = False
            tbCoil.Value = "50"
        Case "BFO"
            'cbClosure.Value = "Buried"
            cbGuy.Value = False
            tbCoil.Value = "20"
        Case Else
            'cbClosure.Value = "Buried"
            cbGuy.Value = False
            tbCoil.Value = "50"
    End Select
End Sub

Private Sub Label49_Click()
    Dim objEntity As AcadEntity
    Dim objBlock As AcadBlockReference
    Dim vAttLst, vReturnPnt As Variant
    
    On Error Resume Next
    
    Me.Hide
    ThisDrawing.Utility.GetEntity objEntity, vReturnPnt, vbCr & "Select Structure:"
    If Not Err = 0 Then GoTo Exit_Sub
    If Not TypeOf objEntity Is AcadBlockReference Then GoTo Exit_Sub
    
    Set objBlock = objEntity
    Select Case objBlock.Name
        Case "sPole", "sPed", "sHH", "sPanel"
        Case Else
            GoTo Exit_Sub
    End Select
    
    vAttList = objBlock.GetAttributes
    
    tbRoute.Value = vAttList(0).TextString
Exit_Sub:
    Me.show
End Sub

Private Sub tbF1_Change()
    If cbSize.Value = "" Then Exit Sub
    
    Call UpdateCounts
End Sub

Private Sub tbTrunk_Change()
    If cbSize.Value = "" Then Exit Sub
    
    Call UpdateCounts
End Sub

Private Sub UserForm_Initialize()
    cbType.AddItem "ADSS"
    cbType.AddItem "BFO"
    cbType.AddItem "CO"
    cbType.AddItem "UO"
    cbType.Value = "CO"
    
    cbSize.AddItem "12"
    cbSize.AddItem "24"
    cbSize.AddItem "36"
    cbSize.AddItem "48"
    cbSize.AddItem "72"
    cbSize.AddItem "96"
    cbSize.AddItem "144"
    cbSize.AddItem "216"
    cbSize.AddItem "288"
    cbSize.AddItem "360"
    cbSize.AddItem "432"
    cbSize.AddItem "576"
    cbSize.AddItem "864"
    cbSize.Value = "24"
    
    cbStatus.AddItem "Existing"
    cbStatus.AddItem "Proposed"
    cbStatus.AddItem "Future"
    cbStatus.AddItem "Remove"
    cbStatus.Value = "Proposed"
    
    cbClosure.AddItem ""
    cbClosure.AddItem "#1413"
    cbClosure.AddItem "FOSC A"
    cbClosure.AddItem "FOSC B"
    cbClosure.AddItem "FOSC D"
    cbClosure.AddItem "G4"
    cbClosure.AddItem "G5"
    cbClosure.AddItem "G6"
    cbClosure.AddItem "G6S"
    
    tbRoute.Value = "QQ/"
    tbRoute.SetFocus
    
    tbCounts.Value = "F2: 1-24"
End Sub

Private Function PlaceGuy(X0 As Double, Y0 As Double, X1 As Double, Y1 As Double, X2 As Double, Y2 As Double)
    Dim startPnt(0 To 2), midPnt(0 To 2), endPnt(0 To 2) As Double
    Dim firstAng, endAng, defAng, rotateAng, ancAng, pull, tempPull As Double
    Dim dRotate, Pi, dTemp As Double
    Dim returnPoint As Variant
    Dim insertPnt(0 To 2) As Double
    Dim n, result, iDirection As Integer  'iDirection 0=L 1=R
    Dim str, str2, strTemp As String
    Dim layerObj As AcadLayer
    Dim strPull, strResult As String
    Dim vPoleCoords As Variant
    Dim entPole As AcadObject
    Dim obrGP As AcadBlockReference
    Dim attItem, basePnt As Variant
    Dim iCount As Integer
    
    Pi = 3.14159265359
    
'On Error GoTo Exit_Sub
    
    If (X1 - X0) = 0 Then
        If (Y1 - Y0) < 0 Then
            firstAng = 3 * Pi / 2
        Else
            firstAng = Pi / 2
        End If
    Else
        firstAng = Math.Atn((Y1 - Y0) / (X1 - X0))
        If (X1 - X0) < 0 Then
            firstAng = Pi + firstAng
        ElseIf (Y1 - Y0) < 0 Then
            firstAng = 2 * Pi + firstAng
        End If
    End If
    
    If (X2 - X0) = 0 Then
        If (Y2 - Y0) < 0 Then
            endAng = 3 * Pi / 2
        Else
            endAng = Pi / 2
        End If
    Else
        endAng = Math.Atn((Y2 - Y0) / (X2 - X0))
        If (X2 - X0) < 0 Then
            endAng = Pi + endAng
        ElseIf (Y2 - Y0) < 0 Then
            endAng = 2 * Pi + endAng
        End If
    End If
    
    Select Case Abs(endAng - firstAng)
        Case Is = 0
            rotateAng = firstAng + Pi
        Case Is < Pi
            rotateAng = (endAng + firstAng) / 2 + Pi
        Case Else
            rotateAng = (endAng + firstAng) / 2
    End Select
    
    If rotateAng > (2 * Pi) Then rotateAng = rotateAng - (2 * Pi)
    If rotateAng < 0 Then rotateAng = rotateAng + (2 * Pi)
    
    defAng = firstAng + Pi - endAng
    pull = Math.Round(Math.Abs(100 * Math.Sin(defAng / 2)))
    
    If pull < 3 Then
        PlaceGuy = ""
        Exit Function
    End If
    
    If (rotateAng > (Pi / 2)) And (rotateAng <= (3 * Pi / 2)) Then
        str = "ExGuyOL"
        str2 = "ExAncOL"
    Else
        str = "ExGuyOR"
        str2 = "ExAncOR"
    End If
    
    'insertPnt = ThisDrawing.Utility.GetPoint(, "Place Guy:")
    insertPnt(0) = X0
    insertPnt(1) = Y0
    insertPnt(2) = 0#
    
    If pull >= 50 Then  '<------------------------------------- Get strPull
        strPull = "DE"
        
        dTemp = Abs(firstAng - endAng)
        
        If dTemp < 0.0002 Then
            Call AddAnchorGuy(insertPnt, CStr(str2), CStr(str), CStr(strPull), CDbl(rotateAng))
        
            strTemp = "+PE1-3G=1;;+PF1-5A=1;;+PM11=1"
        Else
            Call AddAnchorGuy(insertPnt, CStr(str2), CStr(str), CStr(strPull), (firstAng + Pi))
            Call AddAnchorGuy(insertPnt, CStr(str2), CStr(str), CStr(strPull), (endAng + Pi))
        
            strTemp = "+PM2A=1;;+PE1-3G=2;;+PF1-5A=2;;+PM11=2"
        End If
    Else
        strPull = pull
        Call AddAnchorGuy(insertPnt, CStr(str2), CStr(str), CStr(strPull), CDbl(rotateAng))
        
        strTemp = "+PE1-3G=1;;+PF1-5A=1;;+PM11=1"
    End If
    
Exit_Sub:
    PlaceGuy = strTemp
End Function

Private Sub AddAnchorGuy(vInsert As Variant, strAnc As String, strGuy As String, strPull As String, dRotate As Double)
    Dim objBlock As AcadBlockReference
    Dim vAttList As Variant
    Dim dScale As Double
    Dim dInsert(2) As Double
    
    dInsert(0) = vInsert(0)
    dInsert(1) = vInsert(1)
    dInsert(2) = vInsert(2)
    dScale = 1#
        
    Set objBlock = ThisDrawing.ModelSpace.InsertBlock(dInsert, strGuy, dScale, dScale, dScale, dRotate)
    If cbExistGuys.Value = True Then
        objBlock.Layer = "Integrity Existing"
    Else
        objBlock.Layer = "Integrity " & cbStatus.Value
    End If
    vAttList = objBlock.GetAttributes
    vAttList(2).TextString = "PE1-3G"
    objBlock.Update

    Set objBlock = ThisDrawing.ModelSpace.InsertBlock(dInsert, strAnc, dScale, dScale, dScale, dRotate)
    If cbExistGuys.Value = True Then
        objBlock.Layer = "Integrity Existing"
    Else
        objBlock.Layer = "Integrity " & cbStatus.Value
    End If
    vAttList = objBlock.GetAttributes
    vAttList(0).TextString = "PF1-5A"
    If strPull = "DE" Then
        vAttList(1).TextString = "P= DE"
    Else
        vAttList(1).TextString = "P= " & strPull
    End If
    objBlock.Update
End Sub

Private Sub PlaceClosure(vInfo As Variant)
    Dim dDist, dScale, dRotate As Double
    Dim dInsertPnt(2) As Double
    Dim dBackPnt(2) As Double
    
    dDist = vInfo(0)
    dScale = vInfo(1)
    dRotate = vInfo(2)
    
    dInsertPnt(0) = vInfo(3)
    dInsertPnt(1) = vInfo(4)
    dInsertPnt(2) = 0#
    
    dBackPnt(0) = vInfo(5)
    dBackPnt(1) = vInfo(6)
    dBackPnt(2) = 0#
    
    
    
    Dim obrMClosure As AcadBlockReference
    Dim obrMCoil As AcadBlockReference
    'Dim objBlock, obrGP3 As AcadBlockReference
    'Dim vReturnPnt, vEndPnt As Variant
    Dim vAttList As Variant
    Dim dDiff(0 To 3) As Double
    Dim strBlockName, strTermType As String
    'Dim layerObj As AcadLayer
    'Dim returnPnt, vPoleCoords As Variant
    Dim str, strLayer As String
    Dim vBlockCoords(0 To 2) As Double
    Dim i As Integer

    Me.Hide

    strTermType = ""

  On Error Resume Next

    str = ""
    Err = 0

    dDiff(0) = dBackPnt(0) - dInsertPnt(0)
    dDiff(1) = dBackPnt(1) - dInsertPnt(1)
    dDiff(2) = Math.Sqr(dDiff(0) * dDiff(0) + (dDiff(1) * dDiff(1)))

    dInsertPnt(0) = dInsertPnt(0) + 15 * dScale * dDiff(0) / dDiff(2)
    dInsertPnt(1) = dInsertPnt(1) + 15 * dScale * dDiff(1) / dDiff(2)
    dInsertPnt(2) = 0#

    strLayer = "Integrity Map Splices-Aerial"

    strBlockName = "Map splice"
    Set obrMClosure = ThisDrawing.ModelSpace.InsertBlock(dInsertPnt, strBlockName, dScale, dScale, dScale, dRotate)
    obrMClosure.Layer = strLayer
    vAttList = obrMClosure.GetAttributes

    If Not cbClosure.Value = "" Then vAttList(0).TextString = cbClosure.Value
    'vAttList(1).TextString = str
    obrMClosure.Update

place_coil:

    dInsertPnt(0) = dInsertPnt(0) + 15 * dScale * dDiff(0) / dDiff(2)
    dInsertPnt(1) = dInsertPnt(1) + 15 * dScale * dDiff(1) / dDiff(2)

    If dDiff(0) > 0 Then
        dInsertPnt(0) = dInsertPnt(0) + 9 * dScale * dDiff(1) / dDiff(2)
        dInsertPnt(1) = dInsertPnt(1) - 9 * dScale * dDiff(0) / dDiff(2)
    Else
        dInsertPnt(0) = dInsertPnt(0) - 9 * dScale * dDiff(1) / dDiff(2)
        dInsertPnt(1) = dInsertPnt(1) + 9 * dScale * dDiff(0) / dDiff(2)
    End If

    strLayer = "Integrity Map Coils-Aerial"   'Replace(strLayer, "Splices", "Coils")

    Set obrMCoil = ThisDrawing.ModelSpace.InsertBlock(dInsertPnt, "Map coil", dScale, dScale, dScale, 0#)
    obrMCoil.Layer = strLayer
    vAttList = obrMCoil.GetAttributes
    If Not tbCoil.Value = "" Then vAttList(0).TextString = tbCoil.Value & "'"
    vAttList(1).TextString = tbCoilCable.Value & "F"
    obrMCoil.Update

Exit_Sub:
    
End Sub

Private Sub UpdateCounts()
    Dim iSize, iCount As Integer
    Dim iTrunk, iF1, iF2 As Integer
    Dim strCount As String
    
    iCount = 0
    iSize = CInt(cbSize.Value)
    If tbTrunk.Value = "" Then
        iTrunk = 0
    Else
        iTrunk = CInt(tbTrunk.Value)
    End If
    If tbF1.Value = "" Then
        iF1 = 0
    Else
        iF1 = CInt(tbF1.Value)
    End If
    
    strCounts = ""
    If iTrunk > 0 Then
        If Not iTrunk < iSize Then
            strCounts = "TRUNK: 1-" & iSize
            GoTo Full
        Else
            strCounts = "TRUNK: 1-" & iTrunk & vbCr
            iCount = iTrunk
        End If
    End If
    If iF1 > 0 Then
        If Not iCount + iF1 < iSize Then
            strCounts = strCounts & "F1: " & (iCount + 1) & "-" & iSize
            GoTo Full
        Else
            strCounts = strCounts & "F1: " & (iCount + 1) & "-" & (iCount + iF1) & vbCr
            iCount = iCount + iF1
        End If
    End If
    strCounts = strCounts & "F2: " & (iCount + 1) & "-" & iSize
    
Full:
    
    tbCounts.Value = strCounts
End Sub

Private Function FixStructureNumber(strLine As String)
    Dim vL, vR As Variant
    Dim strNumber, strResult As String
    
    vL = Split(strLine, "L")
    vR = Split(vL(UBound(vL)), "R")
    strNumber = vR(UBound(vR))
    
    strResult = Left(strLine, Len(strLine) - Len(strNumber)) & " - " & strNumber
    
    FixStructureNumber = strResult
End Function

Attribute VB_Name = "aaPlaceDrops"
Attribute VB_Base = "0{B7BF1CB7-2825-4837-8C83-C1E91DAF6043}{363A1757-E5BC-4827-83DE-A9A420EE8647}"
Attribute VB_GlobalNameSpace = False
Attribute VB_Creatable = False
Attribute VB_PredeclaredId = True
Attribute VB_Exposed = False
Attribute VB_TemplateDerived = False
Attribute VB_Customizable = False
Dim objStructure As AcadBlockReference

Private Sub cbGetCustomers_Click()
    Call GetSub
    Exit Sub
    
    Dim objSS As AcadSelectionSet
    Dim objBlock As AcadBlockReference
    Dim vAttList As Variant
    Dim strLine As String
    Dim iCount As Integer
    
    iCount = lbSubs.ListCount + 1
    
    On Error Resume Next
    
    Set objSS = ThisDrawing.SelectionSets.Add("objSS")
    If Not Err = 0 Then
        Set objSS = ThisDrawing.SelectionSets.Item("objSS")
        objSS.Clear
        Err = 0
    End If
    
    Me.Hide
    
    objSS.SelectOnScreen
    
    For Each objBlock In objSS
        If objBlock.Name = "Customer" Then
            vAttList = objBlock.GetAttributes
            If InStr(vAttList(4).TextString, tbStructure.Value & "-") > 0 Then GoTo Next_Customer
            
            vAttList(4).TextString = tbStructure.Value & " - " & iCount
            objBlock.Update
            
            strLine = vAttList(1).TextString & " " & vAttList(2).TextString
            lbSubs.AddItem strLine
            lbSubs.List(lbSubs.ListCount - 1, 1) = Left(vAttList(0).TextString, 1)
            
            iCount = iCount + 1
        End If
Next_Customer:
    Next objBlock
    
    tbListCount.Value = lbSubs.ListCount
    
    
    If lbSubs.ListCount > 0 Then
        Dim iR, iB As Integer
        
        iR = 0: iB = 0
        
        For i = 0 To lbSubs.ListCount - 1
            Select Case lbSubs.List(i, 1)
                Case "R", "C", "M", "T"
                    iR = iR + 1
                Case "B", "S"
                    iB = iB + 1
            End Select
        Next i
        
        Dim vData As Variant
        
        vData = Split(tbData.Value, vbCr)
        vData(5) = iR & "," & iB
        strLine = vData(0)
        For i = 1 To UBound(vData)
            strLine = strLine & vbCr & vData(i)
        Next i
        
        tbData.Value = strLine
    End If
    
    Me.show
End Sub

Private Sub cbGetStructure_Click()
    Dim objEntity As AcadEntity
    Dim vAttList As Variant
    Dim vReturnPnt As Variant
    
    On Error Resume Next
    Me.Hide
    
    ThisDrawing.Utility.GetEntity objEntity, vReturnPnt
    If Not Err = 0 Then
        MsgBox "Error"
        GoTo Exit_Sub
    End If
    
    If Not TypeOf objEntity Is AcadBlockReference Then
        MsgBox "Not a block"
        GoTo Exit_Sub
    End If
    
    Set objStructure = objEntity
    
    Select Case objStructure.Name
        Case "sPole"
            vAttList = objStructure.GetAttributes
            tbStructure.Value = vAttList(0).TextString
        Case Else
            MsgBox "Invalid block"
    End Select
    
Exit_Sub:
    
    lbSubs.Clear
    If Not vAttList(28).TextString = "" Then tbData.Value = Replace(vAttList(28).TextString, ";;", vbCr)
    
    Me.show
End Sub

Private Sub cbSaveStructure_Click()
    If tbData.Value = "" Then Exit Sub
    
    Dim vAttList As Variant
    Dim strLine As String
    
    strLine = Replace(tbData.Value, vbCr, ";;")
    strLine = Replace(strLine, vbLf, "")
    
    vAttList = objStructure.GetAttributes
    vAttList(28).TextString = strLine
    
    objStructure.Update
End Sub

Private Sub UserForm_Initialize()
    lbSubs.ColumnCount = 2
    lbSubs.ColumnWidths = "168;54"
End Sub

Private Sub GetSub()
    Dim objEntity As AcadEntity
    Dim objBlock As AcadBlockReference
    Dim objLWP As AcadLWPolyline
    Dim vAttList, vReturnPnt As Variant
    Dim strResult As String
    Dim iCount, iAerial As Integer
    
    On Error Resume Next
    Me.Hide
    
Get_Customer:
    iCount = lbSubs.ListCount + 1
    ThisDrawing.Utility.GetEntity objEntity, vReturnPnt, vbCr & "Select Customer:"
    If Not Err = 0 Then GoTo Exit_Sub
    
    If Not TypeOf objEntity Is AcadBlockReference Then GoTo Exit_Sub
    Set objBlock = objEntity
    If Not objBlock.Name = "Customer" Then GoTo Exit_Sub
    
    vAttList = objBlock.GetAttributes
    vAttList(4).TextString = tbStructure.Value & " - " & iCount
    objBlock.Update
    
    lbSubs.AddItem vAttList(1).TextString & " " & vAttList(2).TextString
    lbSubs.List(iCount - 1, 1) = Left(vAttList(0).TextString, 1)
    
    If cbDrops.Value = False Then GoTo Get_Customer
    
    strResult = ThisDrawing.Utility.GetString(False, vbCr & "Aerial/Buried segment:")
    Select Case Left(UCase(strResult), 1)
        Case "B"
        Case Else
    End Select
    
    Err = 0
    GoTo Get_Customer
    
Exit_Sub:
    
    If lbSubs.ListCount > 0 Then
        Dim iR, iB As Integer
        
        iR = 0: iB = 0
        
        For i = 0 To lbSubs.ListCount - 1
            Select Case lbSubs.List(i, 1)
                Case "R", "C", "M", "T"
                    iR = iR + 1
                Case "B", "S"
                    iB = iB + 1
            End Select
        Next i
        
        Dim vData As Variant
        
        vData = Split(tbData.Value, vbCr)
        vData(5) = iR & "," & iB
        strLine = vData(0)
        For i = 1 To UBound(vData)
            strLine = strLine & vbCr & vData(i)
        Next i
        
        tbData.Value = strLine
    End If
    
    Me.show
End Sub

Attribute VB_Name = "aaPlanningWorksheet"
Attribute VB_Base = "0{7793B80D-66C7-41AC-8BBC-96A4FA096D3F}{BBA625F1-7A36-4724-88B7-F7E06DA9B4C2}"
Attribute VB_GlobalNameSpace = False
Attribute VB_Creatable = False
Attribute VB_PredeclaredId = True
Attribute VB_Exposed = False
Attribute VB_TemplateDerived = False
Attribute VB_Customizable = False
Dim objSS As AcadSelectionSet
    
Private Sub cbAddSB_Click()
    If lbStructures.ListCount < 1 Then Exit Sub
    
    Dim strLine, strTemp As String
    Dim objBlock As AcadBlockReference
    Dim vAttList, vLine, vItem As Variant
    
    If tbNewBoundary.Value = "" Then
        strLine = " "
    Else
        strLine = tbNewBoundary.Value
    End If
    
    For i = 0 To lbStructures.ListCount - 1
        If lbStructures.Selected(i) = True Then
            lbStructures.List(i, 8) = strLine
            
            Set objBlock = objSS.Item(CInt(lbStructures.List(i, 0)))
            vAttList = objBlock.GetAttributes
            
            vLine = Split(vAttList(28).TextString, ";;")
            vLine(7) = strLine
            
            strTemp = vLine(0)
            For j = 1 To UBound(vLine)
                strTemp = strTemp & ";;" & vLine(j)
            Next j
            vAttList(28).TextString = strTemp
            objBlock.Update
        End If
    Next i
    
    For i = 0 To cbBoundary.ListCount - 1
        If cbBoundary.List(i) = strLine Then Exit Sub
    Next i
    
    cbBoundary.AddItem strLine
End Sub

Private Sub cbAddSplitter_Click()
    If lbStructures.ListCount < 1 Then Exit Sub
    If Not cbBoundary.Value = "All" Then
        MsgBox "Need to display All boundaries"
        Exit Sub
    End If
    
    Dim objBlock As AcadBlockReference
    Dim vAttList, vLine, vItem As Variant
    Dim strTemp As String
    Dim strLine, strPrevious As String
    
    strPrevious = ""
    
    For i = 0 To lbStructures.ListCount - 1
        If lbStructures.Selected(i) = True Then
            strLine = Replace(lbStructures.List(i, 1), " - ", "")
            lbStructures.List(i, 5) = cbSplitter.Value
            lbStructures.List(i, 8) = strLine
            tbNewBoundary.Value = strLine
            
            strPrevious = lbStructures.List(i, 2)
        
            Set objBlock = objSS.Item(CInt(lbStructures.List(i, 0)))
            vAttList = objBlock.GetAttributes
            
            vLine = Split(vAttList(28).TextString, ";;")
            If vLine(3) = " " Then
                vLine(3) = "0:1:0"
            Else
                vItem = Split(vLine(3), ":")
                Select Case UBound(vItem)
                    Case Is = 0
                        vLine(3) = vLine(3) & ":1:0"
                    Case Is = 1
                        vLine(3) = vItem(0) & ":" & CInt(vItem(1)) + 1 & ":0"
                    Case Is > 1
                        vLine(3) = vItem(0) & ":" & CInt(vItem(1)) + 1 & ":" & vItem(2)
                End Select
            End If
            vLine(4) = cbSplitter.Value
            vLine(7) = strLine
            
            lbStructures.List(i, 4) = vLine(3)
            
            strTemp = vLine(0)
            For j = 1 To UBound(vLine)
                strTemp = strTemp & ";;" & vLine(j)
            Next j
            vAttList(28).TextString = strTemp
            objBlock.Update
            
            GoTo Exit_Sub
        End If
    Next i
    
Exit_Sub:
    
    If strPrevious = "" Then Exit Sub
    
    For i = 0 To lbStructures.ListCount - 1
        If lbStructures.List(i, 1) = strPrevious Then
            Set objBlock = objSS.Item(CInt(lbStructures.List(i, 0)))
            vAttList = objBlock.GetAttributes
            
            vLine = Split(vAttList(28).TextString, ";;")
            If vLine(3) = " " Then
                vLine(3) = "0:1:0"
            Else
                vItem = Split(vLine(3), ":")
                Select Case UBound(vItem)
                    Case Is = 0
                        vLine(3) = vLine(3) & ":1:0"
                    Case Is = 1
                        vLine(3) = vItem(0) & ":" & CInt(vItem(1)) + 1 & ":0"
                    Case Is > 1
                        vLine(3) = vItem(0) & ":" & CInt(vItem(1)) + 1 & ":" & vItem(2)
                End Select
            End If
            
            lbStructures.List(i, 4) = vLine(3)
            
            strTemp = vLine(0)
            For j = 1 To UBound(vLine)
                strTemp = strTemp & ";;" & vLine(j)
            Next j
            vAttList(28).TextString = strTemp
            objBlock.Update
            
            strPrevious = lbStructures.List(i, 2)
            
            i = -1
        End If
    Next i
End Sub

Private Sub cbBoundary_Change()
    Call GetList
End Sub

Private Sub cbGetStructures_Click()
    Dim filterType, filterValue As Variant
    Dim grpCode(0) As Integer
    Dim grpValue(0) As Variant
    Dim objBlock As AcadBlockReference
    Dim vAttList As Variant
    Dim vLine As Variant
    Dim vPnt1, vPnt2 As Variant
    'Dim strPole, strOwner, strCompany, strNew As String
    'Dim strExisting, strProposed, strExtra, strNote As String
    'Dim strAttachments As String
    'Dim strDWG As String
    Dim iIndex As Integer
    'Dim iExist, iProp, iPole As Integer
    
    On Error Resume Next
    
    Me.Hide
    
    lbStructures.Clear
    'lbCompany.Clear
    'cbCompany.Clear
    'tbOwners.Value = ""
    'strDWG = "Window"
    'iPole = 0
        
    Err = 0
    vPnt1 = ThisDrawing.Utility.GetPoint(, "Get BL Corner: ")
    vPnt2 = ThisDrawing.Utility.GetCorner(vPnt1, vbCr & "Get UR Corner: ")
    If Not Err = 0 Then GoTo Exit_Sub
    
    grpCode(0) = 2
    grpValue(0) = "sPole"
    filterType = grpCode
    filterValue = grpValue
    
    objSS.Clear
    objSS.Select acSelectionSetWindow, vPnt1, vPnt2, filterType, filterValue
    
    iIndex = 0
    cbBoundary.Clear
    cbBoundary.AddItem "All"
    cbBoundary.AddItem " "
    cbBoundary.Value = "All"
    
'    For Each objBlock In objSS
'        vAttList = objBlock.GetAttributes
'        If vAttList(28).TextString = "" Then GoTo Next_objBlock
'
'        vLine = Split(vAttList(28).TextString, ";;")
'        lbStructures.AddItem iIndex
'        lbStructures.List(iIndex, 1) = vLine(0)
'        lbStructures.List(iIndex, 2) = vLine(1)
'        lbStructures.List(iIndex, 3) = vLine(2)
'        lbStructures.List(iIndex, 4) = vLine(3)
'        lbStructures.List(iIndex, 5) = vLine(4)
'        lbStructures.List(iIndex, 6) = vLine(5)
'        lbStructures.List(iIndex, 7) = vLine(6)
'        lbStructures.List(iIndex, 8) = vLine(7)
'        lbStructures.List(iIndex, 9) = vLine(8)
'
'        iIndex = iIndex + 1
'Next_objBlock:
'    Next objBlock
    
    If lbStructures.ListCount > 0 Then
        For i = 0 To lbStructures.ListCount - 1
            For j = 0 To cbBoundary.ListCount - 1
                If cbBoundary.List(j) = lbStructures.List(i, 8) Then GoTo Next_Structure
            Next j
            
            cbBoundary.AddItem lbStructures.List(i, 8)
            
Next_Structure:
        Next i
    End If
    
Exit_Sub:
    
    tbListCount.Value = lbStructures.ListCount
    
    Call SortList
    
    Me.show
End Sub

Private Sub cbTraceStructure_Click()
    If lbStructures.ListCount < 1 Then Exit Sub
    If Not cbBoundary.Value = "All" Then
        MsgBox "Need to display All boundaries"
        Exit Sub
    End If
    If tbTrace.Value = "" Then
        MsgBox "Need to enter a structure number"
        Exit Sub
    End If
    
    Dim objBlock As AcadBlockReference
    Dim vAttList, vLine, vItem As Variant
    Dim strTemp As String
    Dim strLine, strPrevious As String
    
    strPrevious = tbTrace.Value
    lbStructures.Clear
    
    For i = 0 To objSS.count - 1
        Set objBlock = objSS.Item(i)
        vAttList = objBlock.GetAttributes
        If InStr(vAttList(28).TextString, ";;") > 0 Then
            vLine = Split(vAttList(28).TextString, ";;")
            If vLine(0) = strPrevious Then
                lbStructures.AddItem i, 0
                lbStructures.List(0, 1) = vLine(0)
                lbStructures.List(0, 2) = vLine(1)
                lbStructures.List(0, 3) = vLine(2)
                lbStructures.List(0, 4) = vLine(3)
                lbStructures.List(0, 5) = vLine(4)
                lbStructures.List(0, 6) = vLine(5)
                lbStructures.List(0, 7) = vLine(6)
                lbStructures.List(0, 8) = vLine(7)
                lbStructures.List(0, 9) = vLine(8)
                
                strPrevious = vLine(1)
                i = -1
            End If
        End If
    Next i
    
    Call GetTotals
End Sub

Private Sub Label60_Click()
    If lbStructures.ListCount < 1 Then Exit Sub
    
    For i = 0 To lbStructures.ListCount - 1
        If lbStructures.Selected(i) = True Then
            cbBoundary.Value = lbStructures.List(i, 8)
            Exit Sub
        End If
    Next i
End Sub

Private Sub Label62_Click()
    If lbStructures.ListCount < 1 Then Exit Sub
    
    For i = 0 To lbStructures.ListCount - 1
        If lbStructures.Selected(i) = True Then
            tbNewBoundary.Value = lbStructures.List(i, 8)
            Exit Sub
        End If
    Next i
End Sub

Private Sub Label66_Click()
    If lbStructures.ListCount < 1 Then Exit Sub
    
    For i = 0 To lbStructures.ListCount - 1
        If lbStructures.Selected(i) = True Then
            tbTrace.Value = lbStructures.List(i, 1)
            Exit Sub
        End If
    Next i
End Sub

Private Sub LabelPan_Click()
    Dim entPole As AcadObject
    Dim basePnt As Variant
    
    Me.Hide
  On Error Resume Next
    
    ThisDrawing.Utility.GetEntity entPole, basePnt, "Left Click to Exit: "
    
    Me.show
End Sub

Private Sub lbStructures_DblClick(ByVal Cancel As MSForms.ReturnBoolean)
    If lbStructures.ListIndex < 0 Then Exit Sub
    
    Dim iIndex As Integer
    Dim vLine As Variant
    Dim strLine As String
    
    iIndex = lbStructures.ListIndex
    
    Me.Hide
    
    Load aaStructureData
        aaStructureData.tbNumber.Value = lbStructures.List(iIndex, 1)
        aaStructureData.tbPrevious.Value = lbStructures.List(iIndex, 2)
        aaStructureData.tbDistance.Value = lbStructures.List(iIndex, 3)
        
        vLine = Split(lbStructures.List(iIndex, 4), ":")
        Select Case UBound(vLine)
            Case Is = 0
                aaStructureData.tbTrunk.Value = vLine(0)
            Case Is = 1
                aaStructureData.tbTrunk.Value = vLine(0)
                aaStructureData.tbF1.Value = vLine(1)
            Case Is > 1
                aaStructureData.tbTrunk.Value = vLine(0)
                aaStructureData.tbF1.Value = vLine(1)
                aaStructureData.tbF15.Value = vLine(2)
        End Select
        aaStructureData.tbSplitter.Value = lbStructures.List(iIndex, 5)
        
        vLine = Split(lbStructures.List(iIndex, 6), ",")
        aaStructureData.tbRES.Value = vLine(0)
        If UBound(vLine) > 0 Then aaStructureData.tbBUS.Value = vLine(1)
        
        aaStructureData.tbTaps.Value = lbStructures.List(iIndex, 7)
        aaStructureData.tbBoundary.Value = lbStructures.List(iIndex, 8)
        aaStructureData.tbCable.Value = lbStructures.List(iIndex, 9)
        
        aaStructureData.show
        
        If aaStructureData.iSave = 0 Then GoTo Exit_Sub
        
        lbStructures.List(iIndex, 1) = aaStructureData.tbNumber.Value
        lbStructures.List(iIndex, 2) = aaStructureData.tbPrevious.Value
        lbStructures.List(iIndex, 3) = aaStructureData.tbDistance.Value
        strLine = aaStructureData.tbTrunk.Value & ":" & aaStructureData.tbF1.Value & ":" & aaStructureData.tbF15.Value
        lbStructures.List(iIndex, 4) = strLine
        lbStructures.List(iIndex, 5) = aaStructureData.tbSplitter.Value
        strLine = aaStructureData.tbRES.Value & "," & aaStructureData.tbBUS.Value
        lbStructures.List(iIndex, 6) = strLine
        lbStructures.List(iIndex, 7) = aaStructureData.tbTaps.Value
        lbStructures.List(iIndex, 8) = aaStructureData.tbBoundary.Value
        lbStructures.List(iIndex, 9) = aaStructureData.tbCable.Value
        
    Unload aaStructureData
    
    strLine = lbStructures.List(iIndex, 1)
    For i = 1 To 9
        strLine = strLine & ";;" & lbStructures.List(iIndex, i)
    Next i
    
    Dim objBlock As AcadBlockReference
    Dim vAttList As Variant
    
    Set objBlock = objSS.Item(CInt(lbStructures.List(iIndex, 0)))
    vAttList = objBlock.GetAttributes
    vAttList(28).TextString = strLine
    objBlock.Update
    
Exit_Sub:
    
    Me.show
End Sub

Private Sub UserForm_Deactivate()
    objSS.Clear
    objSS.Delete
End Sub

Private Sub UserForm_Initialize()
    lbStructures.ColumnCount = 10
    lbStructures.ColumnWidths = "36;120;120;24;48;36;72;144;96;234"
    
    cbSplitter.AddItem "2"
    cbSplitter.AddItem "4"
    cbSplitter.AddItem "8"
    cbSplitter.AddItem "16"
    cbSplitter.AddItem "32"
    cbSplitter.AddItem "64"
    'cbSplitter.AddItem "2:16"
    'cbSplitter.AddItem "2:32"
    'cbSplitter.AddItem "0:16"
    'cbSplitter.AddItem "0:32"
    
    'cbSplitter.AddItem "4:8"
    'cbSplitter.AddItem "4:16"
    'cbSplitter.AddItem "8:2"
    'cbSplitter.AddItem "8:4"
    'cbSplitter.AddItem "8:8"
    'cbSplitter.AddItem "16:2"
    'cbSplitter.AddItem "16:4"
    
    cbSplitter.Value = "32"
    
    On Error Resume Next
    
    Err = 0
    Set objSS = ThisDrawing.SelectionSets.Add("objSS")
    If Not Err = 0 Then
        Set objSS = ThisDrawing.SelectionSets.Item("objSS")
    End If
End Sub

Private Sub GetList()
    If cbBoundary.Value = "" Then Exit Sub
    If cbBoundary.ListCount < 1 Then Exit Sub
    If objSS.count < 1 Then Exit Sub
    
    Dim objBlock As AcadBlockReference
    Dim vAttList, vItem As Variant
    
    lbStructures.Clear
    
    For i = 0 To objSS.count - 1
        Set objBlock = objSS.Item(i)
        vAttList = objBlock.GetAttributes
        
        If vAttList(28).TextString = "" Then GoTo Next_Object
        vItem = Split(vAttList(28).TextString, ";;")
        
        If Not UBound(vItem) = 8 Then GoTo Next_Object
        If Not cbBoundary.Value = "All" Then
            If Not vItem(7) = cbBoundary.Value Then GoTo Next_Object
        End If
        
        lbStructures.AddItem i
        lbStructures.List(lbStructures.ListCount - 1, 1) = vItem(0)
        lbStructures.List(lbStructures.ListCount - 1, 2) = vItem(1)
        lbStructures.List(lbStructures.ListCount - 1, 3) = vItem(2)
        lbStructures.List(lbStructures.ListCount - 1, 4) = vItem(3)
        lbStructures.List(lbStructures.ListCount - 1, 5) = vItem(4)
        lbStructures.List(lbStructures.ListCount - 1, 6) = vItem(5)
        lbStructures.List(lbStructures.ListCount - 1, 7) = vItem(6)
        lbStructures.List(lbStructures.ListCount - 1, 8) = vItem(7)
        lbStructures.List(lbStructures.ListCount - 1, 9) = vItem(8)
        
Next_Object:
    Next i
    
    tbListCount = lbStructures.ListCount
    
    Call SortList
    Call GetTotals
End Sub

Private Sub SortList()
    If lbStructures.ListCount < 1 Then Exit Sub
    
    Dim vNumber, vL, vR As Variant
    Dim strRoute, strPole As String
    Dim strRoute1, strPole1 As String
    Dim strAtt(9) As String
    Dim iCount As Integer
    Dim dPole, dPole1 As Double
    
    On Error Resume Next
    
    iCount = lbStructures.ListCount - 1
    
    For a = iCount To 0 Step -1
        For b = 0 To a - 1
            vNumber = Split(lbStructures.List(b, 1), " - ")
            strRoute = vNumber(0)
            strPole = vNumber(1)
            dPole = CDbl(strPole)
            
            vNumber = Split(lbStructures.List(b + 1, 1), " - ")
            strRoute1 = vNumber(0)
            strPole1 = vNumber(1)
            dPole1 = CDbl(strPole1)
            
            If strRoute > strRoute1 Then
                    strAtt(0) = lbStructures.List(b + 1, 0)
                    strAtt(1) = lbStructures.List(b + 1, 1)
                    strAtt(2) = lbStructures.List(b + 1, 2)
                    strAtt(3) = lbStructures.List(b + 1, 3)
                    strAtt(4) = lbStructures.List(b + 1, 4)
                    strAtt(5) = lbStructures.List(b + 1, 5)
                    strAtt(6) = lbStructures.List(b + 1, 6)
                    strAtt(7) = lbStructures.List(b + 1, 7)
                    strAtt(8) = lbStructures.List(b + 1, 8)
                    strAtt(9) = lbStructures.List(b + 1, 9)
                
                    lbStructures.List(b + 1, 0) = lbStructures.List(b, 0)
                    lbStructures.List(b + 1, 1) = lbStructures.List(b, 1)
                    lbStructures.List(b + 1, 2) = lbStructures.List(b, 2)
                    lbStructures.List(b + 1, 3) = lbStructures.List(b, 3)
                    lbStructures.List(b + 1, 4) = lbStructures.List(b, 4)
                    lbStructures.List(b + 1, 5) = lbStructures.List(b, 5)
                    lbStructures.List(b + 1, 6) = lbStructures.List(b, 6)
                    lbStructures.List(b + 1, 7) = lbStructures.List(b, 7)
                    lbStructures.List(b + 1, 8) = lbStructures.List(b, 8)
                    lbStructures.List(b + 1, 9) = lbStructures.List(b, 9)
                
                    lbStructures.List(b, 0) = strAtt(0)
                    lbStructures.List(b, 1) = strAtt(1)
                    lbStructures.List(b, 2) = strAtt(2)
                    lbStructures.List(b, 3) = strAtt(3)
                    lbStructures.List(b, 4) = strAtt(4)
                    lbStructures.List(b, 5) = strAtt(5)
                    lbStructures.List(b, 6) = strAtt(6)
                    lbStructures.List(b, 7) = strAtt(7)
                    lbStructures.List(b, 8) = strAtt(8)
                    lbStructures.List(b, 9) = strAtt(9)
            ElseIf strRoute = strRoute1 Then
                If dPole > dPole1 Then
                'If strPole > strPole1 Then
                        strAtt(0) = lbStructures.List(b + 1, 0)
                        strAtt(1) = lbStructures.List(b + 1, 1)
                        strAtt(2) = lbStructures.List(b + 1, 2)
                        strAtt(3) = lbStructures.List(b + 1, 3)
                        strAtt(4) = lbStructures.List(b + 1, 4)
                        strAtt(5) = lbStructures.List(b + 1, 5)
                        strAtt(6) = lbStructures.List(b + 1, 6)
                        strAtt(7) = lbStructures.List(b + 1, 7)
                        strAtt(8) = lbStructures.List(b + 1, 8)
                        strAtt(9) = lbStructures.List(b + 1, 9)
                
                        lbStructures.List(b + 1, 0) = lbStructures.List(b, 0)
                        lbStructures.List(b + 1, 1) = lbStructures.List(b, 1)
                        lbStructures.List(b + 1, 2) = lbStructures.List(b, 2)
                        lbStructures.List(b + 1, 3) = lbStructures.List(b, 3)
                        lbStructures.List(b + 1, 4) = lbStructures.List(b, 4)
                        lbStructures.List(b + 1, 5) = lbStructures.List(b, 5)
                        lbStructures.List(b + 1, 6) = lbStructures.List(b, 6)
                        lbStructures.List(b + 1, 7) = lbStructures.List(b, 7)
                        lbStructures.List(b + 1, 8) = lbStructures.List(b, 8)
                        lbStructures.List(b + 1, 9) = lbStructures.List(b, 9)
                
                        lbStructures.List(b, 0) = strAtt(0)
                        lbStructures.List(b, 1) = strAtt(1)
                        lbStructures.List(b, 2) = strAtt(2)
                        lbStructures.List(b, 3) = strAtt(3)
                        lbStructures.List(b, 4) = strAtt(4)
                        lbStructures.List(b, 5) = strAtt(5)
                        lbStructures.List(b, 6) = strAtt(6)
                        lbStructures.List(b, 7) = strAtt(7)
                        lbStructures.List(b, 8) = strAtt(8)
                        lbStructures.List(b, 9) = strAtt(9)
                End If
            End If
        Next b
    Next a
End Sub

Private Sub GetTotals()
    If lbStructures.ListCount < 1 Then Exit Sub
    
    Dim vLine, vItem As Variant
    Dim iRes, iBus As Integer
    Dim iCoil, iCoilSize As Integer
    Dim lLength As Long
    
    iRes = 0
    iBus = 0
    iCoil = 1
    lLength = 0
    
    iCoilSize = CInt(tbACoilSize.Value)
    
    For i = 0 To lbStructures.ListCount - 1
        If Not lbStructures.List(i, 3) = "" Then lLength = lLength + CLng(lbStructures.List(i, 3))
        
        If InStr(lbStructures.List(i, 6), ",") > 0 Then
            vItem = Split(lbStructures.List(i, 6), ",")
            iRes = iRes + CInt(vItem(0))
            iBus = iBus + CInt(vItem(1))
        End If
        
        If InStr(lbStructures.List(i, 6), ",") > 0 Or Not lbStructures.List(i, 5) = " " Then iCoil = iCoil + 1
    Next i
    
    tbListCount = lbStructures.ListCount
    tbTotalLength.Value = lLength
    tbResBus.Value = iRes & "," & iBus
    tbNumberACoil.Value = iCoil
    
    tbLenCoil.Value = lLength + (iCoil * iCoilSize)
End Sub

Attribute VB_Name = "aaStructureData"
Attribute VB_Base = "0{9CCF866D-E19E-4B07-AAE8-25A0C61A4837}{9389E391-AFC0-4551-A85A-AD5D572A33F6}"
Attribute VB_GlobalNameSpace = False
Attribute VB_Creatable = False
Attribute VB_PredeclaredId = True
Attribute VB_Exposed = False
Attribute VB_TemplateDerived = False
Attribute VB_Customizable = False
Public iSave As Integer

Private Sub cbUpdate_Click()
    iSave = 1
    Me.Hide
End Sub

Private Sub UserForm_Initialize()
    iSave = 0
End Sub

Attribute VB_Name = "xxValidateMCL"
Attribute VB_Base = "0{78ED5783-68FC-4F47-A449-14254D06E118}{89426223-BDE3-4CA7-9662-EC97B8488B7A}"
Attribute VB_GlobalNameSpace = False
Attribute VB_Creatable = False
Attribute VB_PredeclaredId = True
Attribute VB_Exposed = False
Attribute VB_TemplateDerived = False
Attribute VB_Customizable = False
'Dim objSS As AcadSelectionSet

Private Sub cbCheckData_Click()
    If lbList.ListCount < 1 Then Exit Sub
    
    For i = lbList.ListCount - 1 To 0 Step -1
            If lbList.List(i, 6) = "Y" Then lbList.RemoveItem i
    Next i
End Sub

Private Sub cbGetCustomers_Click()
    If lbList.ListCount < 1 Then Exit Sub
    
    
    Dim filterType, filterValue As Variant
    Dim grpCode(0) As Integer
    Dim grpValue(0) As Variant
    Dim objSS As AcadSelectionSet
    Dim objBlock As AcadBlockReference
    Dim vLine, vItem, vCount As Variant
    Dim vPnt1, vPnt2 As Variant
    Dim dPnt1(0 To 2) As Double
    Dim dPnt2(0 To 2) As Double
    Dim strText As String
    Dim iCount As Integer
    
    grpCode(0) = 2
    grpValue(0) = "Customer,SG"
    filterType = grpCode
    filterValue = grpValue
    
    On Error Resume Next
    
    Err = 0
    Set objSS = ThisDrawing.SelectionSets.Add("objSS")
    If Not Err = 0 Then
        Set objSS = ThisDrawing.SelectionSets.Item("objSS")
        objSS.Clear
    End If
    
    Me.Hide
    
    vPnt1 = ThisDrawing.Utility.GetPoint(, "Get BL Corner: ")
    vPnt2 = ThisDrawing.Utility.GetCorner(vPnt1, vbCr & "Get UR Corner: ")
    
    dPnt1(0) = vPnt1(0)
    dPnt1(1) = vPnt1(1)
    dPnt1(2) = vPnt1(2)
    
    dPnt2(0) = vPnt2(0)
    dPnt2(1) = vPnt2(1)
    dPnt2(2) = vPnt2(2)
    
    'objSS.Clear
    'objSS.Select acSelectionSetAll, , , filterType, filterValue
    objSS.Select acSelectionSetWindow, dPnt1, dPnt2, filterType, filterValue
    
    For Each objBlock In objSS
        vAttList = objBlock.GetAttributes
        
        Select Case objBlock.Name
            Case "SG"
                If vAttList(2).TextString = "" Then GoTo Next_objBlock
                
                vLine = Split(vAttList(2).TextString, " - ")
                If UBound(vLine) < 1 Then GoTo Next_objBlock
                
                vCount = Split(vLine(1), ": ")
                If InStr(vCount(0), "(") > 0 Then
                    vCount(0) = Replace(vCount(0), "(", "")
                    vCount(1) = Replace(vCount(1), ")", "")
                End If
                
                If Not vCount(0) = tbCableName.Value Then GoTo Next_objBlock
                
                iCount = CInt(vCount(1))
                
                
                
                
                
                strText = vLine(1) & vbTab & "SG - " & vAttList(1).TextString
            Case Else
                If vAttList(4).TextString = "" Then GoTo Next_objBlock
                
                vLine = Split(vAttList(4).TextString, " - ")
                If UBound(vLine) < 1 Then GoTo Next_objBlock
                
                vCount = Split(vLine(1), ": ")
                If InStr(vCount(0), "(") > 0 Then
                    vCount(0) = Replace(vCount(0), "(", "")
                    vCount(1) = Replace(vCount(1), ")", "")
                End If
                
                'MsgBox vCount(0) & "*" & vbCr & tbCableName.Value & "*"
                If Not vCount(0) = tbCableName.Value Then GoTo Next_objBlock
                
                iCount = CInt(vCount(1)) - 1
                lbList.List(iCount, 4) = vAttList(1).TextString & "  " & vAttList(2).TextString
                lbList.List(iCount, 5) = Left(vAttList(0).TextString, 1)
        End Select
        
Next_objBlock:
    Next objBlock
    
Clear_objSS:
    objSS.Clear
    objSS.Delete
    
    Call ValidateCustomers
    
    Me.show
End Sub

Private Sub cbList_Change()
    Dim strFileName As String
    Dim vLine As Variant
    Dim strLine As String
    Dim fName As String
    Dim iIndex As Integer
    
    strFileName = LCase(ThisDrawing.Path) & "\" & cbList.Value & ".mcl"
    
    fName = Dir(strFileName)
    
    Open strFileName For Input As #2
    
    Line Input #2, strLine
    tbCableName.Value = Replace(strLine, " ", "")
    
    lbList.Clear
    
    While Not EOF(2)
        Line Input #2, strLine
        vLine = Split(strLine, vbTab)
        
        lbList.AddItem vLine(0)
        iIndex = lbList.ListCount - 1
        
        lbList.List(iIndex, 1) = vLine(1)
        lbList.List(iIndex, 2) = vLine(2) & "  " & vLine(3)
        If Left(vLine(4), 1) = "<" Then
            lbList.List(iIndex, 3) = " "
        Else
            lbList.List(iIndex, 3) = Left(vLine(4), 1)
        End If
        lbList.List(iIndex, 4) = "n/a"
        lbList.List(iIndex, 5) = " "
        lbList.List(iIndex, 6) = " "
    Wend
    
    Close #2
End Sub

Private Sub cbQuit_Click()
    Me.Hide
End Sub

Private Sub UserForm_Initialize()
    lbList.ColumnCount = 7
    lbList.ColumnWidths = "36;120;144,24,144,24,30"
    
    On Error Resume Next
    
    'Err = 0
    'Set objSS = ThisDrawing.SelectionSets.Add("objSS")
    'If Not Err = 0 Then
        'Set objSS = ThisDrawing.SelectionSets.Item("objSS")
        'objSS.Clear
    'End If
    
    Dim strFile, strFolder, strTemp As String
    Dim vName, vLine, vItem As Variant
    Dim strLine As String
    Dim fName As String
    Dim iIndex, iCount As Integer
    
    strFolder = ThisDrawing.Path & "\*.*"
    
    strFile = Dir$(strFolder)
    
    Do While strFile <> ""
        If InStr(strFile, ".mcl") Then
            cbList.AddItem Replace(strFile, ".mcl", "")
        End If
        strFile = Dir$
    Loop
    
    If cbList.ListCount < 1 Then Exit Sub
    iCount = cbList.ListCount - 1
    
    'Sort list
    
    For a = iCount To 0 Step -1
        For b = 0 To a - 1
            If cbList.List(b) > cbList.List(b + 1) Then
                strTemp = cbList.List(b + 1)
                
                cbList.List(b + 1) = cbList.List(b)
                
                cbList.List(b) = strTemp
            End If
        Next b
    Next a
    
End Sub

Private Sub UserForm_Terminate()
    'objSS.Clear
    'objSS.Delete
End Sub

Private Sub ValidateCustomers()
    If lbList.ListCount < 1 Then Exit Sub
    
    For i = 0 To lbList.ListCount - 1
        If lbList.List(i, 2) = lbList.List(i, 4) Then
            If lbList.List(i, 3) = lbList.List(i, 5) Then lbList.List(i, 6) = "Y"
        End If
        
        If lbList.List(i, 1) = "<>" Then
            If lbList.List(i, 4) = "n/a" Then lbList.List(i, 6) = "Y"
        End If
    Next i
End Sub

Attribute VB_Name = "yCrystalClearFibers"
Attribute VB_Base = "0{449CF94B-A418-4FCC-8FB7-9DC8C9837BAC}{09405E29-04F8-456B-BE98-35E442FA1A3A}"
Attribute VB_GlobalNameSpace = False
Attribute VB_Creatable = False
Attribute VB_PredeclaredId = True
Attribute VB_Exposed = False
Attribute VB_TemplateDerived = False
Attribute VB_Customizable = False
Private Sub cbGetBlocks_Click()
    If lbLots.ListCount < 1 Then Exit Sub
    
    Dim filterType, filterValue As Variant
    Dim grpCode(0) As Integer
    Dim grpValue(0) As Variant
    Dim objSS As AcadSelectionSet
    Dim objBlock As AcadBlockReference
    Dim objCircle As AcadCircle
    Dim vPnt1, vPnt2 As Variant
    Dim vAttList As Variant
    Dim dPnt1(0 To 2) As Double
    Dim dPnt2(0 To 2) As Double
    Dim strSearch As String
    
    grpCode(0) = 2
    grpValue(0) = "Customer"
    filterType = grpCode
    filterValue = grpValue
    
    On Error Resume Next
    
    Err = 0
    Set objSS = ThisDrawing.SelectionSets.Add("objSS")
    If Not Err = 0 Then
        Set objSS = ThisDrawing.SelectionSets.Item("objSS")
        objSS.Clear
    End If
    
    Me.Hide
    
    vPnt1 = ThisDrawing.Utility.GetPoint(, "Get BL Corner: ")
    vPnt2 = ThisDrawing.Utility.GetCorner(vPnt1, vbCr & "Get UR Corner: ")
    
    dPnt1(0) = vPnt1(0)
    dPnt1(1) = vPnt1(1)
    dPnt1(2) = vPnt1(2)
    
    dPnt2(0) = vPnt2(0)
    dPnt2(1) = vPnt2(1)
    dPnt2(2) = vPnt2(2)
    
    objSS.Select acSelectionSetWindow, dPnt1, dPnt2, filterType, filterValue
    
    For Each objBlock In objSS
        vAttList = objBlock.GetAttributes
        If vAttList(4).TextString = "" Then
            strSearch = UCase(vAttList(1).TextString & " " & vAttList(2).TextString)
            
            strSearch = Replace(strSearch, "STE", "SUITE")
            strSearch = Replace(strSearch, " PL", ",")
            If InStr(strSearch, " BLVD S") > 0 Then strSearch = Replace(strSearch, " BLVD", ",")
        Else
            strSearch = vAttList(4).TextString
        End If
        
        For i = lbLots.ListCount - 1 To 0 Step -1
            If strSearch = lbLots.List(i, 2) Then
                vAttList(4).TextString = lbLots.List(i, 0) & ": " & lbLots.List(i, 1)
                objBlock.Update
                
                lbLots.RemoveItem i
                
                GoTo Next_objBlock
            End If
        Next i
        
        lbMissing.AddItem vAttList(1).TextString & " " & vAttList(2).TextString
        lbMissing.List(lbMissing.ListCount - 1, 1) = strSearch
        
        vAttList(4).TextString = "LOT: " & strSearch
        objBlock.Update
        
        Set objCircle = ThisDrawing.ModelSpace.AddCircle(objBlock.InsertionPoint, 30#)
        objCircle.Layer = "Integrity Notes"
        objCircle.Update
        
Next_objBlock:
    Next objBlock
    
Exit_Sub:
    objSS.Clear
    objSS.Delete
    
    tbLListcount.Value = lbLots.ListCount
    tbCListcount.Value = lbMissing.ListCount
    
    Me.show
End Sub

Private Sub cbRemove_Click()
    If lbLots.ListCount < 1 Then Exit Sub
    
    For i = lbLots.ListCount - 1 To 0 Step -1
        If lbLots.List(i, 3) = "Y" Then lbLots.RemoveItem i
    Next i
    
    tbLListcount.Value = lbLots.ListCount
End Sub

Private Sub cbRemoveLot_Click()
    If lbLots.ListCount < 1 Then Exit Sub
    
    For i = lbLots.ListCount - 1 To 0 Step -1
        If lbLots.List(i, 2) = tbLotText.Value Then lbLots.RemoveItem i
    Next i
    
    tbLListcount.Value = lbLots.ListCount
End Sub

Private Sub LabelPan_Click()
    Dim entPole As AcadObject
    Dim basePnt As Variant
    
    Me.Hide
  On Error Resume Next
    
    ThisDrawing.Utility.GetEntity entPole, basePnt, "Left Click to Exit: "
    
    Me.show
End Sub

Private Sub UserForm_Initialize()
    lbLots.ColumnCount = 4
    lbLots.ColumnWidths = "60;60;60;54"
    
    lbMissing.ColumnCount = 2
    lbMissing.ColumnWidths = "150;54"
    
    Dim fName As String
    Dim objExcel As Workbook
    Dim objSheet As Worksheet
    Dim objDoc As Object
    Dim strFileName As String
    Dim iRow, iIndex As Integer
    
    strFileName = ThisDrawing.Path & "\Panel-Port-Lot.xlsx" 'Panel-Port-Lot.xlsx
    'MsgBox strFileName
    
    fName = Dir(strFileName)
    If fName = "" Then
        MsgBox "File not found."
        Exit Sub
    Else
        Set objExcel = Workbooks.Open(strFileName)
    End If
    
    Set objSheet = objExcel.Sheets("All")
    iRow = 1
    
    While Not objSheet.Cells(iRow, 1) = ""
        lbLots.AddItem objSheet.Cells(iRow, 1)
        iIndex = lbLots.ListCount - 1
        lbLots.List(iIndex, 1) = objSheet.Cells(iRow, 2)
        lbLots.List(iIndex, 2) = UCase(objSheet.Cells(iRow, 3))
        
        iRow = iRow + 1
    Wend
    
    objExcel.Close
    
    tbLListcount.Value = lbLots.ListCount
End Sub

Attribute VB_Name = "yCrystalClearNotes"
Attribute VB_Base = "0{B15D3FEB-69AD-4E68-8F08-BFCE53D39B8E}{FD06D7D7-EED5-46AC-93A4-E2F883E8A403}"
Attribute VB_GlobalNameSpace = False
Attribute VB_Creatable = False
Attribute VB_PredeclaredId = True
Attribute VB_Exposed = False
Attribute VB_TemplateDerived = False
Attribute VB_Customizable = False
Private Sub cbGet_Click()
    Dim objEntity As AcadEntity
    Dim vReturnPnt As Variant
    Dim objBlock As AcadBlockReference
    Dim vAttList As Variant
    Dim vLine As Variant
    
    On Error Resume Next
    
    Me.Hide
    
Get_Another:
    
    ThisDrawing.Utility.GetEntity objEntity, vReturnPnt
    If Not Err = 0 Then GoTo Exit_Sub
    If Not TypeOf objEntity Is AcadBlockReference Then GoTo Exit_Sub
    
    Set objBlock = objEntity
    If Not objBlock.Name = "Customer" Then GoTo Exit_Sub
    
    vAttList = objBlock.GetAttributes
        
    vLine = Split(vAttList(4).TextString, ": ")
        
    If UBound(vLine) = 0 Then
        lbFibers.AddItem "???"
        lbFibers.List(lbFibers.ListCount - 1, 1) = vLine(0)
        lbFibers.List(lbFibers.ListCount - 1, 2) = vAttList(1).TextString & " " & vAttList(2).TextString
    Else
        lbFibers.AddItem vLine(0)
        lbFibers.List(lbFibers.ListCount - 1, 1) = vLine(1)
        lbFibers.List(lbFibers.ListCount - 1, 2) = vAttList(1).TextString & " " & vAttList(2).TextString
    End If
    
    GoTo Get_Another
    
Exit_Sub:
    
    Call SortList
    cbPlace.SetFocus
    
    Me.show
End Sub

Private Sub cbPlace_Click()
    If lbFibers.ListCount < 1 Then Exit Sub
    
    Dim objMText As AcadMText
    Dim vBasePnt, vLL As Variant
    Dim strLine, strTemp, strColors As String
    Dim dInsert(2) As Double
    Dim dScale As Double
    Dim iLength As Integer
    
    On Error Resume Next
    Me.Hide
    
    vBasePnt = ThisDrawing.Utility.GetPoint(, "Select Note Placement: ")
    If Not Err = 0 Then GoTo Exit_Sub
    
    dInsert(0) = vBasePnt(0)
    dInsert(1) = vBasePnt(1)
    dInsert(2) = 0#
    
    dScale = CDbl(tbTextHeight.Value)
    
    Select Case lbFibers.List(0, 0)
        Case "LOT", "???"
            strColors = "? / ?"
            iLength = 5
        Case Else
            strColors = GetColors(CInt(lbFibers.List(0, 1)))
            iLength = GetLength(CStr(strColors))
    End Select
    
    strLine = lbFibers.List(0, 0) & ": " & lbFibers.List(0, 1)
    If Len(strLine) < 11 Then
        strLine = strLine & vbTab & vbTab & strColors
    Else
        strLine = strLine & vbTab & strColors
    End If
            
    If iLength < 7 Then
        strLine = strLine & vbTab & vbTab & lbFibers.List(0, 2)
    Else
        strLine = strLine & vbTab & lbFibers.List(0, 2)
    End If
    
    If lbFibers.ListCount > 1 Then
        For i = 1 To lbFibers.ListCount - 1
            Select Case lbFibers.List(i, 0)
                Case "LOT", "???"
                    strColors = "? / ?"
                    iLength = 5
                Case Else
                    strColors = GetColors(CInt(lbFibers.List(i, 1)))
                    iLength = GetLength(CStr(strColors))
            End Select
            
            strTemp = lbFibers.List(i, 0) & ": " & lbFibers.List(i, 1)
            If Len(strTemp) < 11 Then
                strTemp = strTemp & vbTab & vbTab & strColors
            Else
                strTemp = strTemp & vbTab & strColors
            End If
            
            If iLength < 7 Then
                strTemp = strTemp & vbTab & vbTab & lbFibers.List(i, 2)
            Else
                strTemp = strTemp & vbTab & lbFibers.List(i, 2)
            End If
            
            strLine = strLine & "\P" & strTemp
        Next i
    End If

    Set objMText = ThisDrawing.ModelSpace.AddMText(dInsert, 0, strLine)
    objMText.Layer = cbNoteLayer.Value
    objMText.Height = dScale
    objMText.InsertionPoint = dInsert
    Select Case cbJust.Value
        Case "TL"
            objMText.AttachmentPoint = acAttachmentPointTopLeft
        Case "TC"
            objMText.AttachmentPoint = acAttachmentPointTopCenter
        Case "TR"
            objMText.AttachmentPoint = acAttachmentPointTopRight
        Case "ML"
            objMText.AttachmentPoint = acAttachmentPointMiddleLeft
        Case "MC"
            objMText.AttachmentPoint = acAttachmentPointMiddleCenter
        Case "MR"
            objMText.AttachmentPoint = acAttachmentPointMiddleRight
        Case "BL"
            objMText.AttachmentPoint = acAttachmentPointBottomLeft
        Case "BC"
            objMText.AttachmentPoint = acAttachmentPointBottomCenter
        Case "BR"
            objMText.AttachmentPoint = acAttachmentPointBottomRight
    End Select
    If cbMask.Value = True Then objMText.BackgroundFill = True
    
    objMText.Update
    
Exit_Sub:
    lbFibers.Clear
    cbGet.SetFocus
    
    Me.show
End Sub

Private Sub lbFibers_KeyDown(ByVal KeyCode As MSForms.ReturnInteger, ByVal Shift As Integer)
    If lbFibers.ListCount < 1 Then Exit Sub
    
    Dim iIndex As Integer
    Dim str(2) As String
    
    Select Case KeyCode
        Case vbKeyDelete
            lbFibers.RemoveItem lbFibers.ListIndex
        Case vbKeyDown
            iIndex = lbFibers.ListIndex
            If iIndex = lbFibers.ListCount - 1 Then Exit Sub
            
            str(0) = lbFibers.List(iIndex, 0)
            str(1) = lbFibers.List(iIndex, 1)
            str(2) = lbFibers.List(iIndex, 2)
            
            lbFibers.List(iIndex, 0) = lbFibers.List(iIndex + 1, 0)
            lbFibers.List(iIndex, 1) = lbFibers.List(iIndex + 1, 1)
            lbFibers.List(iIndex, 2) = lbFibers.List(iIndex + 1, 2)
            
            lbFibers.List(iIndex + 1, 0) = str(0)
            lbFibers.List(iIndex + 1, 1) = str(1)
            lbFibers.List(iIndex + 1, 2) = str(2)
        Case vbKeyUp
            iIndex = lbFibers.ListIndex
            If iIndex < 1 Then Exit Sub
            
            str(0) = lbFibers.List(iIndex, 0)
            str(1) = lbFibers.List(iIndex, 1)
            str(2) = lbFibers.List(iIndex, 2)
            
            lbFibers.List(iIndex, 0) = lbFibers.List(iIndex - 1, 0)
            lbFibers.List(iIndex, 1) = lbFibers.List(iIndex - 1, 1)
            lbFibers.List(iIndex, 2) = lbFibers.List(iIndex - 1, 2)
            
            lbFibers.List(iIndex - 1, 0) = str(0)
            lbFibers.List(iIndex - 1, 1) = str(1)
            lbFibers.List(iIndex - 1, 2) = str(2)
    End Select
End Sub

Private Sub UserForm_Initialize()
    lbFibers.ColumnCount = 3
    lbFibers.ColumnWidths = "48;48;120"
    
    cbJust.AddItem "TL"
    cbJust.AddItem "TC"
    cbJust.AddItem "TR"
    cbJust.AddItem "ML"
    cbJust.AddItem "MC"
    cbJust.AddItem "MR"
    cbJust.AddItem "BL"
    cbJust.AddItem "BC"
    cbJust.AddItem "BR"
    cbJust.Value = "TL"
    
    Dim objLayers As AcadLayers
    Dim objLayer As AcadLayer
    
    Set objLayers = ThisDrawing.Layers
    For Each objLayer In objLayers
        cbNoteLayer.AddItem objLayer.Name
    Next objLayer
    cbNoteLayer.Value = "Integrity Notes"
End Sub

Private Function GetColors(iPort As Integer)
    If iPort > 144 Then iPort = iPort - 144
    
    Dim strLine As String
    Dim iRibbon, iStrand As Integer
    
    iFiber = iPort
    iRibbon = 0
    While iFiber > 12
        iRibbon = iRibbon + 1
        iFiber = iFiber - 12
    Wend
    iFiber = iFiber - 1
    
    'iRibbon = CInt(iPort / 12 - 0.5)
    'If iRibbon < 0 Then iRibbon = 0
    'iFiber = iPort - (iRibbon * 12) - 1
    'If iFiber < 1 Then
        'iRibbon = iRibbon - 1
        'iFiber = 0
    'End If
    
    Select Case iRibbon
        Case Is < 1
            strLine = "BL / "
        Case Is = 1
            strLine = "O / "
        Case Is = 2
            strLine = "G / "
        Case Is = 3
            strLine = "BR / "
        Case Is = 4
            strLine = "S / "
        Case Is = 5
            strLine = "W / "
        Case Is = 6
            strLine = "RD / "
        Case Is = 7
            strLine = "BK / "
        Case Is = 8
            strLine = "Y / "
        Case Is = 9
            strLine = "V / "
        Case Is = 10
            strLine = "RS / "
        Case Is = 11
            strLine = "A / "
    End Select
    
    Select Case iFiber
        Case Is < 1
            strLine = strLine & "BL"
        Case Is = 1
            strLine = strLine & "O"
        Case Is = 2
            strLine = strLine & "G"
        Case Is = 3
            strLine = strLine & "BR"
        Case Is = 4
            strLine = strLine & "S"
        Case Is = 5
            strLine = strLine & "W"
        Case Is = 6
            strLine = strLine & "RD"
        Case Is = 7
            strLine = strLine & "BK"
        Case Is = 8
            strLine = strLine & "Y"
        Case Is = 9
            strLine = strLine & "V"
        Case Is = 10
            strLine = strLine & "RS"
        Case Is = 11
            strLine = strLine & "A"
    End Select
    
    GetColors = strLine
End Function

Private Function GetLength(strLine As String)
    Dim vLine As Variant
    Dim dLength As Double
    Dim iLength As Integer
    Dim strTemp As String
    
    vLine = Split(strLine, " / ")
    
    Select Case vLine(0)
        Case "S", "Y", "V", "A"
            dLength = 4
        Case "G", "W", "O"
            dLength = 4.5
        Case Else
            dLength = 5
    End Select
    
    Select Case vLine(1)
        Case "S", "Y", "V", "A"
            dLength = dLength + 1
        Case "G", "W", "O"
            dLength = dLength + 1.5
        Case Else
            dLength = dLength + 2
    End Select
    
    strTemp = dLength
    If InStr(strTemp, ".") > 0 Then dLength = dLength + 0.5
    
    iLength = CInt(dLength)
    GetLength = iLength
End Function

Private Sub SortList()
    If lbFibers.ListCount < 3 Then Exit Sub
    
    Dim strTemp, strTotal As String
    Dim strCurrent, strNext As String
    Dim iCount, iOffset As Integer
    Dim iIndex As Integer
    Dim strAtt(0 To 5) As String
    
    iCount = lbFibers.ListCount - 1
    If iCount < 1 Then Exit Sub
    
    On Error Resume Next
    
    For a = iCount To 0 Step -1
        For b = 0 To a - 1
            strCurrent = lbFibers.List(b, 0)
            Select Case Len(lbFibers.List(b, 1))
                Case Is = 1
                    strCurrent = strCurrent & "00" & lbFibers.List(b, 1)
                Case Is = 2
                    strCurrent = strCurrent & "0" & lbFibers.List(b, 1)
                Case Else
                    strCurrent = strCurrent & lbFibers.List(b, 1)
            End Select
            
            strNew = lbFibers.List(b + 1, 0)
            Select Case Len(lbFibers.List(b + 1, 1))
                Case Is = 1
                    strNew = strNew & "00" & lbFibers.List(b + 1, 1)
                Case Is = 2
                    strNew = strNew & "0" & lbFibers.List(b + 1, 1)
                Case Else
                    strNew = strNew & lbFibers.List(b + 1, 1)
            End Select
            
            
            If strCurrent > strNew Then
                If Not Err = 0 Then
                    MsgBox "Error sorting list"
                    lbFibers.Selected(b) = True
                    lbFibers.ListIndex = b
                    Exit Sub
                End If
                
                strAtt(0) = lbFibers.List(b + 1, 0)
                strAtt(1) = lbFibers.List(b + 1, 1)
                strAtt(2) = lbFibers.List(b + 1, 2)
                
                lbFibers.List(b + 1, 0) = lbFibers.List(b, 0)
                lbFibers.List(b + 1, 1) = lbFibers.List(b, 1)
                lbFibers.List(b + 1, 2) = lbFibers.List(b, 2)
                
                lbFibers.List(b, 0) = strAtt(0)
                lbFibers.List(b, 1) = strAtt(1)
                lbFibers.List(b, 2) = strAtt(2)
            End If
        Next b
    Next a
End Sub

Attribute VB_Name = "yCrystalClearUpdateSS"
Attribute VB_Base = "0{316E25B3-9099-4FCF-8C93-EBDD93790BD1}{3492312F-3BD5-4A46-BD0B-D8DB5F395D1C}"
Attribute VB_GlobalNameSpace = False
Attribute VB_Creatable = False
Attribute VB_PredeclaredId = True
Attribute VB_Exposed = False
Attribute VB_TemplateDerived = False
Attribute VB_Customizable = False
Private Sub cbGetCustomers_Click()
    Dim filterType, filterValue As Variant
    Dim grpCode(0) As Integer
    Dim grpValue(0) As Variant
    Dim objSS As AcadSelectionSet
    Dim objBlock As AcadBlockReference
    Dim objCircle As AcadCircle
    Dim vPnt1, vPnt2 As Variant
    Dim vAttList, vLine As Variant
    Dim dPnt1(0 To 2) As Double
    Dim dPnt2(0 To 2) As Double
    
    grpCode(0) = 2
    grpValue(0) = "Customer"
    filterType = grpCode
    filterValue = grpValue
    
    On Error Resume Next
    
    lbPanel.Clear
    cbPanels.Clear
    
    Err = 0
    Set objSS = ThisDrawing.SelectionSets.Add("objSS")
    If Not Err = 0 Then
        Set objSS = ThisDrawing.SelectionSets.Item("objSS")
        objSS.Clear
    End If
    
    Me.Hide
    
    vPnt1 = ThisDrawing.Utility.GetPoint(, "Get BL Corner: ")
    vPnt2 = ThisDrawing.Utility.GetCorner(vPnt1, vbCr & "Get UR Corner: ")
    
    dPnt1(0) = vPnt1(0)
    dPnt1(1) = vPnt1(1)
    dPnt1(2) = vPnt1(2)
    
    dPnt2(0) = vPnt2(0)
    dPnt2(1) = vPnt2(1)
    dPnt2(2) = vPnt2(2)
    
    objSS.Select acSelectionSetWindow, dPnt1, dPnt2, filterType, filterValue
    
    For Each objBlock In objSS
        vAttList = objBlock.GetAttributes
        If vAttList(4).TextString = "" Then GoTo Next_objBlock
        
        vLine = Split(vAttList(4).TextString, ": ")
        lbFibers.AddItem vLine(0)
        lbFibers.List(lbFibers.ListCount - 1, 1) = vLine(1)
        lbFibers.List(lbFibers.ListCount - 1, 2) = vAttList(1).TextString
        lbFibers.List(lbFibers.ListCount - 1, 3) = vAttList(2).TextString
        lbFibers.List(lbFibers.ListCount - 1, 4) = vAttList(3).TextString
        
Next_objBlock:
    Next objBlock
    
    cbPanels.AddItem lbFibers.List(0, 0)
    If lbFibers.ListCount > 1 Then
        For i = 1 To lbFibers.ListCount - 1
            For j = 0 To cbPanels.ListCount - 1
                If lbFibers.List(i, 0) = cbPanels.List(j) Then GoTo Found_Panel
            Next j
            
            cbPanels.AddItem lbFibers.List(i, 0)
Found_Panel:
        Next i
    End If
    
    Call SortPanels
    
Exit_Sub:
    objSS.Clear
    objSS.Delete
    
    'Call SortFList
    
    tbListCount.Value = lbFibers.ListCount
    
    Me.show
End Sub

Private Sub cbPanels_Change()
    If cbPanels.Value = "" Then Exit Sub
    If lbFibers.ListCount < 1 Then Exit Sub
    
    lbPanel.Clear
    
    For i = 0 To lbFibers.ListCount - 1
        If lbFibers.List(i, 0) = cbPanels.Value Then
            lbPanel.AddItem lbFibers.List(i, 0)
            lbPanel.List(lbPanel.ListCount - 1, 1) = lbFibers.List(i, 1)
            lbPanel.List(lbPanel.ListCount - 1, 2) = lbFibers.List(i, 2)
            lbPanel.List(lbPanel.ListCount - 1, 3) = lbFibers.List(i, 3)
            lbPanel.List(lbPanel.ListCount - 1, 4) = lbFibers.List(i, 4)
        End If
    Next i
    
    Call SortList
    
    tbPListcount.Value = lbPanel.ListCount
End Sub

Private Sub cbUpdateXLSX_Click()
    If lbFibers.ListCount < 1 Then Exit Sub
    
    Dim fName As String
    Dim objExcel As Workbook
    Dim objSheet As Worksheet
    Dim objDoc As Object
    Dim strFileName As String
    Dim iRow, iIndex As Integer
    
    Dim vLine As Variant
    Dim strPanel, strPort As String
    
    strFileName = ThisDrawing.Path & "\Panel-Port-Lot.xlsx" 'Panel-Port-Lot.xlsx
    'MsgBox strFileName
    
    fName = Dir(strFileName)
    If fName = "" Then
        MsgBox "File not found."
        Exit Sub
    Else
        Set objExcel = Workbooks.Open(strFileName)
    End If
    
    Set objSheet = objExcel.Sheets("All")
    iRow = 1
    
    While Not objSheet.Cells(iRow, 1) = ""
        strPanel = objSheet.Cells(iRow, 1)
        strPort = objSheet.Cells(iRow, 2)
        
        For i = 0 To lbFibers.ListCount - 1
            If lbFibers.List(i, 0) = strPanel And lbFibers.List(i, 1) = strPort Then
                objSheet.Cells(iRow, 4) = lbFibers.List(i, 2)
                objSheet.Cells(iRow, 5) = lbFibers.List(i, 3)
                
                lbFibers.RemoveItem i
                GoTo Next_iRow
            End If
        Next i
        
        
Next_iRow:
        If lbFibers.ListCount < 1 Then GoTo Exit_Sub
        
        iRow = iRow + 1
    Wend
    
    For i = lbFibers.ListCount - 1 To 0 Step -1
        If lbFibers.List(i, 0) = "LOT" Then
            objSheet.Cells(iRow, 1) = "UNK"
            objSheet.Cells(iRow, 2) = "UNK"
            objSheet.Cells(iRow, 3) = lbFibers.List(i, 1)
        Else
            objSheet.Cells(iRow, 1) = lbFibers.List(i, 0)
            objSheet.Cells(iRow, 2) = lbFibers.List(i, 1)
            objSheet.Cells(iRow, 3) = "UNK"
        End If
        
        objSheet.Cells(iRow, 4) = lbFibers.List(i, 2)
        objSheet.Cells(iRow, 5) = lbFibers.List(i, 3)
        objSheet.Cells(iRow, 6) = lbFibers.List(i, 4)
        
        lbFibers.RemoveItem i
        
        iRow = iRow + 1
    Next i
    
Exit_Sub:
    objExcel.Save
    objExcel.Close
End Sub

Private Sub UserForm_Initialize()
    lbFibers.ColumnCount = 5
    lbFibers.ColumnWidths = "48;48;48;114;6"
    
    lbPanel.ColumnCount = 5
    lbPanel.ColumnWidths = "48;48;48;114;6"
End Sub

Private Sub SortFList()
    If lbFibers.ListCount < 3 Then Exit Sub
    
    Dim strTemp, strTotal As String
    Dim strCurrent, strNext As String
    Dim iCount, iOffset As Integer
    Dim iIndex As Integer
    Dim strAtt(0 To 5) As String
    
    iCount = lbFibers.ListCount - 1
    If iCount < 1 Then Exit Sub
    
    On Error Resume Next
    
    For a = iCount To 0 Step -1
        For b = 0 To a - 1
            strCurrent = lbFibers.List(b, 0)
            Select Case Len(lbFibers.List(b, 1))
                Case Is = 1
                    strCurrent = strCurrent & "00" & lbFibers.List(b, 1)
                Case Is = 2
                    strCurrent = strCurrent & "0" & lbFibers.List(b, 1)
                Case Else
                    strCurrent = strCurrent & lbFibers.List(b, 1)
            End Select
            
            strNew = lbFibers.List(b + 1, 0)
            Select Case Len(lbFibers.List(b + 1, 1))
                Case Is = 1
                    strNew = strNew & "00" & lbFibers.List(b + 1, 1)
                Case Is = 2
                    strNew = strNew & "0" & lbFibers.List(b + 1, 1)
                Case Else
                    strNew = strNew & lbFibers.List(b + 1, 1)
            End Select
            
            
            If strCurrent > strNew Then
                If Not Err = 0 Then
                    MsgBox "Error sorting list"
                    lbFibers.Selected(b) = True
                    lbFibers.ListIndex = b
                    Exit Sub
                End If
                
                strAtt(0) = lbFibers.List(b + 1, 0)
                strAtt(1) = lbFibers.List(b + 1, 1)
                strAtt(2) = lbFibers.List(b + 1, 2)
                strAtt(3) = lbFibers.List(b + 1, 3)
                
                lbFibers.List(b + 1, 0) = lbFibers.List(b, 0)
                lbFibers.List(b + 1, 1) = lbFibers.List(b, 1)
                lbFibers.List(b + 1, 2) = lbFibers.List(b, 2)
                lbFibers.List(b + 1, 3) = lbFibers.List(b, 3)
                
                lbFibers.List(b, 0) = strAtt(0)
                lbFibers.List(b, 1) = strAtt(1)
                lbFibers.List(b, 2) = strAtt(2)
                lbFibers.List(b, 3) = strAtt(3)
            End If
        Next b
    Next a
End Sub

Private Sub SortList()
    If lbPanel.ListCount < 3 Then Exit Sub
    
    Dim strTemp, strTotal As String
    Dim strCurrent, strNext As String
    Dim iCount, iOffset As Integer
    Dim iIndex As Integer
    Dim strAtt(0 To 5) As String
    
    iCount = lbPanel.ListCount - 1
    If iCount < 1 Then Exit Sub
    
    On Error Resume Next
    
    For a = iCount To 0 Step -1
        For b = 0 To a - 1
            strCurrent = lbPanel.List(b, 0)
            Select Case Len(lbPanel.List(b, 1))
                Case Is = 1
                    strCurrent = strCurrent & "000" & lbPanel.List(b, 1)
                Case Is = 2
                    strCurrent = strCurrent & "00" & lbPanel.List(b, 1)
                Case Is = 3
                    strCurrent = strCurrent & "0" & lbPanel.List(b, 1)
                Case Else
                    strCurrent = strCurrent & lbPanel.List(b, 1)
            End Select
            
            strNew = lbPanel.List(b + 1, 0)
            Select Case Len(lbPanel.List(b + 1, 1))
                Case Is = 1
                    strNew = strNew & "000" & lbPanel.List(b + 1, 1)
                Case Is = 2
                    strNew = strNew & "00" & lbPanel.List(b + 1, 1)
                Case Is = 3
                    strNew = strNew & "0" & lbPanel.List(b + 1, 1)
                Case Else
                    strNew = strNew & lbPanel.List(b + 1, 1)
            End Select
            
            
            If strCurrent > strNew Then
                If Not Err = 0 Then
                    MsgBox "Error sorting list"
                    lbPanel.Selected(b) = True
                    lbPanel.ListIndex = b
                    Exit Sub
                End If
                
                strAtt(0) = lbPanel.List(b + 1, 0)
                strAtt(1) = lbPanel.List(b + 1, 1)
                strAtt(2) = lbPanel.List(b + 1, 2)
                strAtt(3) = lbPanel.List(b + 1, 3)
                
                lbPanel.List(b + 1, 0) = lbPanel.List(b, 0)
                lbPanel.List(b + 1, 1) = lbPanel.List(b, 1)
                lbPanel.List(b + 1, 2) = lbPanel.List(b, 2)
                lbPanel.List(b + 1, 3) = lbPanel.List(b, 3)
                
                lbPanel.List(b, 0) = strAtt(0)
                lbPanel.List(b, 1) = strAtt(1)
                lbPanel.List(b, 2) = strAtt(2)
                lbPanel.List(b, 3) = strAtt(3)
            End If
        Next b
    Next a
End Sub

Private Sub SortPanels()
    If cbPanels.ListCount < 3 Then Exit Sub
    
    Dim iCount As Integer
    Dim strAtt As String
    
    iCount = cbPanels.ListCount - 1
    If iCount < 1 Then Exit Sub
    
    On Error Resume Next
    
    For a = iCount To 0 Step -1
        For b = 0 To a - 1
            strCurrent = cbPanels.List(b)
            strNew = cbPanels.List(b + 1)
            
            If strCurrent > strNew Then
                strAtt = cbPanels.List(b + 1)
                cbPanels.List(b + 1) = cbPanels.List(b)
                cbPanels.List(b) = strAtt
            End If
        Next b
    Next a
End Sub

Attribute VB_Name = "yDEMeters"
Attribute VB_Base = "0{2B4F3D6B-6E80-408C-B63D-74D599AD69CC}{232403D0-7C4C-4D3D-A677-7DD40C7029FA}"
Attribute VB_GlobalNameSpace = False
Attribute VB_Creatable = False
Attribute VB_PredeclaredId = True
Attribute VB_Exposed = False
Attribute VB_TemplateDerived = False
Attribute VB_Customizable = False
Private Sub cbChange_Click()
    If tbText.Value = "" Then Exit Sub
    If cbType.Value = "" Then Exit Sub
    If lbAddresses.ListCount < 1 Then Exit Sub
    
    Dim strText, strType As String
    Dim iColumn As Integer
    
    strText = UCase(tbText.Value)
    Select Case Left(cbType.Value, 1)
        Case "B"
            strType = "B"
        Case "C"
            strType = "C"
        Case "M"
            strType = "M"
        Case "R"
            strType = "R"
        Case "S"
            strType = "S"
        Case "T"
            strType = "T"
        Case Else
            strType = "X"
    End Select
    iColumn = cbColumn.ListIndex
    
    For i = 0 To lbAddresses.ListCount - 1
        If InStr(UCase(lbAddresses.List(i, iColumn)), strText) > 0 Then
            lbAddresses.List(i, 3) = strType
        End If
    Next i
    
    Call GetTotals
    
    If tbHistory.Value = "" Then
        tbHistory.Value = strType & ": " & strText
    Else
        tbHistory.Value = tbHistory.Value & vbCr & strType & ": " & strText
    End If
    
    tbText.Value = ""
End Sub

Private Sub cbFromList_Change()
    Dim amap As AcadMap
    Dim ODRcs As ODRecords
    Dim ODRc As ODRecord
    Dim tbl As ODTable
    Dim tbls As ODTables
    Dim refColumn As ODFieldDef
    Dim objEntity As AcadEntity
    Dim boolVal As Boolean
    Dim iCount As Integer
    Dim strTest As String
    
    On Error Resume Next
    
    Set amap = ThisDrawing.Application.GetInterfaceObject("AutoCADMap.Application")
    
    Set tbls = amap.Projects(ThisDrawing).ODTables
    If tbls.count > 0 Then
        For Each tbl In tbls
            If tbl.Name = cbFromList.Value Then GoTo Exit_For
        Next
    End If
Exit_For:

    Set ODRcs = tbl.GetODRecords
        
    iCount = 0
    Err = 0
    
    lbFrom.Clear
        
    While Err = 0
        Set refColumn = tbl.ODFieldDefs(iCount)
        strTest = refColumn.Name
        If Not Err = 0 Then GoTo Exit_objEntity
            
        lbFrom.AddItem
        lbFrom.List(iCount, 0) = iCount
        lbFrom.List(iCount, 1) = strTest
        iCount = iCount + 1
    Wend
Exit_objEntity:
    
End Sub

Private Sub cbGetPolygon_Click()
    If lbFrom.ListCount < 1 Then Exit Sub
    
    Dim iTest As Integer
    iTest = 0
    For i = 0 To lbFrom.ListCount - 1
        If lbFrom.Selected(i) = True Then iTest = iTest + 1
    Next i
    If iTest = 0 Then Exit Sub
    
    Dim amap As AcadMap
    Dim tbl As ODTable
    Dim tbls As ODTables
    
    Dim filterType, filterValue As Variant
    Dim grpCode(0) As Integer
    Dim grpValue(0) As Variant
    Dim objSS As AcadSelectionSet
    Dim objEntity As AcadEntity
    Dim objPoint As AcadPoint
    Dim vReturnPnt As Variant
    Dim vLine As Variant
    Dim strLine, strTemp As String
    Dim iIndex, iLIndex, iAmount As Integer
    Dim dCoords() As Double
    Dim dInsert(2) As Double
    Dim iCounter, iTotla As Integer
    
    On Error Resume Next
    
    lbAddresses.Clear
    
    Set amap = ThisDrawing.Application.GetInterfaceObject("AutoCADMap.Application")
    
    Set tbls = amap.Projects(ThisDrawing).ODTables
    If tbls.count > 0 Then
        For Each tbl In tbls
            If tbl.Name = cbFromList.Value Then GoTo Exit_For
        Next
    End If
    
    Exit Sub
    
Exit_For:
    
    Set ODRcs = tbl.GetODRecords
    
    Me.Hide
    
    ThisDrawing.Utility.GetEntity objEntity, vReturnPnt, "Select Polygon Border: "
    If Not objEntity.ObjectName = "AcDbPolyline" Then
        MsgBox "Error: Invalid Selection."
        Me.show
        Exit Sub
    End If
    
    Set objLWP = objEntity
    vCoords = objLWP.Coordinates
    
    iTemp = (UBound(vCoords) + 1) / 2 * 3 - 1
    ReDim dCoords(iTemp) As Double
    
    iCounter = 0
    For i = 0 To UBound(vCoords) Step 2
        dCoords(iCounter) = vCoords(i)
        iCounter = iCounter + 1
        dCoords(iCounter) = vCoords(i + 1)
        iCounter = iCounter + 1
        dCoords(iCounter) = 0#
        iCounter = iCounter + 1
    Next i
    
    grpCode(0) = 8
    grpValue(0) = cbFromList.Value
    filterType = grpCode
    filterValue = grpValue
    
    Err = 0
    Set objSS = ThisDrawing.SelectionSets.Add("objSS")
    If Not Err = 0 Then Set objSS = ThisDrawing.SelectionSets.Item("objSS")
    
    objSS.SelectByPolygon acSelectionSetWindowPolygon, dCoords, filterType, filterValue
    
    iTotal = 0
    
    For Each objEntity In objSS
        If TypeOf objEntity Is AcadPoint Then
            Set objPoint = objEntity
            
            dInsert(0) = objPoint.Coordinates(0)
            dInsert(1) = objPoint.Coordinates(1)
            dInsert(2) = objPoint.Coordinates(2)
            
            boolVal = ODRcs.Init(objEntity, True, False)
            Set ODRc = ODRcs.Record
            
            iTotal = iTotal + 1
            iCounter = 0
            
            For i = 0 To lbFrom.ListCount - 1
                If lbFrom.Selected(i) = True Then
                    strTemp = ODRc.Item(i).Value
                    If strTemp = "" Then GoTo Next_Field
                    
                    If iCounter > 0 Then lbAddresses.List(lbAddresses.ListCount - 1, 3) = "M"
                    
                    If Left(strTemp, 1) = " " Then strTemp = Right(strTemp, Len(strTemp) - 1)
                    vLine = Split(strTemp, " ")
                    
                    strTemp = ""
                    If UBound(vLine) > 0 Then
                        strTemp = vLine(1)
                        If UBound(vLine) > 1 Then
                            For j = 2 To UBound(vLine)
                                strTemp = strTemp & " " & vLine(j)
                            Next j
                        End If
                    End If
                    
                    lbAddresses.AddItem lbFrom.List(i, 1)
                    lbAddresses.List(lbAddresses.ListCount - 1, 1) = vLine(0)
                    lbAddresses.List(lbAddresses.ListCount - 1, 2) = strTemp
                    If iCounter = 0 Then
                        lbAddresses.List(lbAddresses.ListCount - 1, 3) = "R"
                    Else
                        lbAddresses.List(lbAddresses.ListCount - 1, 3) = "M"
                        Select Case (iCounter Mod 2)
                            Case Is = 0
                                dInsert(0) = dInsert(0) - 20
                                dInsert(1) = dInsert(1) - 20
                            Case Else
                                dInsert(0) = dInsert(0) + 20
                        End Select
                    End If
                    lbAddresses.List(lbAddresses.ListCount - 1, 4) = dInsert(0) & "," & dInsert(1)
    
                    iCounter = iCounter + 1
                End If
Next_Field:
            Next i
        End If
        
Next_Object:
    Next objEntity
    
Exit_Sub:
    objSS.Clear
    objSS.Delete
    
    Call GetTotals
    tbMeters.Value = iTotal
    
    Me.show
End Sub

Private Sub lbAddresses_DblClick(ByVal Cancel As MSForms.ReturnBoolean)
    MsgBox lbAddresses.List(lbAddresses.ListIndex, 4)
End Sub

Private Sub UserForm_Initialize()
    lbAddresses.Clear
    lbAddresses.ColumnCount = 5
    lbAddresses.ColumnWidths = "96;60;156;48;90"
    
    lbFrom.Clear
    lbFrom.ColumnCount = 2
    lbFrom.ColumnWidths = "20;90"
    
    cbType.AddItem "BUSINESS"
    cbType.AddItem "CHURCH"
    cbType.AddItem "MDU"
    cbType.AddItem "RESIDENCE"
    cbType.AddItem "SCHOOL"
    cbType.AddItem "TRAILER"
    cbType.AddItem "EXTENSION"
    
    cbColumn.AddItem "Field"
    cbColumn.AddItem "Number"
    cbColumn.AddItem "Street Name"
    cbColumn.Value = "Street Name"
    
    Dim amap As AcadMap
    Dim tbl As ODTable
    Dim tbls As ODTables
    
    Set amap = ThisDrawing.Application.GetInterfaceObject("AutoCADMap.Application")
    
    Set tbls = amap.Projects(ThisDrawing).ODTables
    If tbls.count > 0 Then
        cbFromList.Clear
        For Each tbl In tbls
            cbFromList.AddItem tbl.Name
        Next
    End If
End Sub

Private Sub GetTotals()
    If lbAddresses.ListCount < 1 Then Exit Sub
    
    Dim iB, iC, iM, iR, iSc, iT, iX As Integer
    
    iB = 0
    iC = 0
    iM = 0
    iR = 0
    iSc = 0
    iT = 0
    iX = 0
    
    For i = 0 To lbAddresses.ListCount - 1
        Select Case Left(lbAddresses.List(i, 3), 1)
             Case "B"
                iB = iB + 1
             Case "C"
                iC = iC + 1
             Case "M"
                iM = iM + 1
             Case "R"
                iR = iR + 1
             Case "S"
                iSc = iSc + 1
             Case "T"
                iT = iT + 1
             Case Else
                iX = iX + 1
        End Select
    Next i
    
    tbListCount.Value = lbAddresses.ListCount
    
    tbBUS.Value = iB
    tbChu.Value = iC
    tbMDU.Value = iM
    tbRES.Value = iR
    tbSch.Value = iSc
    tbTrlr.Value = iT
    tbExt.Value = iX
End Sub

Attribute VB_Name = "zMisc"
Attribute VB_Base = "0{637A9609-1913-4C8D-B4BE-B56C5673C658}{0F710863-FB7F-4131-A42D-234E6B888533}"
Attribute VB_GlobalNameSpace = False
Attribute VB_Creatable = False
Attribute VB_PredeclaredId = True
Attribute VB_Exposed = False
Attribute VB_TemplateDerived = False
Attribute VB_Customizable = False
Private Sub cbAddMissingCo_Click()
    Dim filterType, filterValue As Variant
    Dim grpCode(0) As Integer
    Dim grpValue(0) As Variant
    Dim objSS As AcadSelectionSet
    
    Dim objBlock As AcadBlockReference
    Dim vAttList As Variant
    
    Dim strLine, strTemp As String
    Dim vLine, vTemp As Variant
    
    On Error Resume Next
    
    grpCode(0) = 2
    grpValue(0) = "sPole"
    filterType = grpCode
    filterValue = grpValue
    
    Err = 0
    Set objSS = ThisDrawing.SelectionSets.Add("objSS")
    If Not Err = 0 Then
        Set objSS = ThisDrawing.SelectionSets.Item("objSS")
        objSS.Clear
    End If
    
    objSS.Select acSelectionSetAll, , , filterType, filterValue
    
    For Each objBlock In objSS
        vAttList = objBlock.GetAttributes
        If vAttList(4).TextString = "" Then GoTo Next_objBlock
        
        If vAttList(2).TextString = tbAtt2.Value Then
            vLine = Split(vAttList(4).TextString, " ")
            For i = 0 To UBound(vLine)
                vTemp = Split(vLine(i), "=")
                If UBound(vTemp) < 1 Then vLine(i) = tbAtt4.Value & "=" & vTemp(0)
            Next i
            
            strTemp = vLine(0)
            If UBound(vLine) > 0 Then
                For i = 0 To UBound(vLine)
                    strTemp = strTemp & " " & vLine(i)
                Next i
            End If
            
            vAttList(4).TextString = strTemp
            objBlock.Update
        End If
        
Next_objBlock:
    Next objBlock
    
    objSS.Clear
    objSS.Delete
End Sub

Private Sub cbAddRoadNames_Click()
    Dim amap As AcadMap
    Dim ODRcs As ODRecords
    Dim tbl As ODTable
    Dim tbls As ODTables
    Dim boolVal As Boolean
    Dim objEntity As AcadEntity
    Dim objBlock As AcadBlockReference
    Dim objLWP As AcadLWPolyline
    'Dim objPolyline As AcadPolyline
    Dim objLine As AcadLine
    Dim objMText As AcadMText
    Dim vReturnPnt, vCoords As Variant
    Dim vStartPnt, vEndPnt As Variant
    Dim dDiff(0 To 2) As Double
    Dim dStartPnt(0 To 2) As Double
    Dim dEndPnt(0 To 2) As Double
    Dim dToText(0 To 2) As Double
    Dim dInsertPnt(0 To 2) As Double
    Dim dTest As Double
    Dim dFromText(0 To 2) As Double
    Dim dRotate, dScale As Double
    Dim dDistScale As Double
    Dim Pi As Double
    Dim iPosition, iLength As Integer
    Dim iScale, iHeight As Integer
    Dim strName As String
    
  On Error Resume Next
    
    If IsNumeric(tbRoadTextHeight.Value) Then
        iHeight = CInt(tbRoadTextHeight.Value)
    Else
        iHeight = 10
    End If
  
    Pi = 3.14159265359
    
    Set amap = ThisDrawing.Application.GetInterfaceObject("AutoCADMap.Application")
    
    Set tbls = amap.Projects(ThisDrawing).ODTables
    
    Err = 0
    If tbls.count > 0 Then
        For Each tbl In tbls
            If tbl.Name = "IS_Streets" Then GoTo exit_for1
        Next
    End If
    
    Exit Sub
exit_for1:

    Set ODRcs = tbl.GetODRecords
    
    Me.Hide
    
Get_Street:

    Err = 0
    
    ThisDrawing.Utility.GetEntity objEntity, vReturnPnt, vbCr & "Select Street: "
    
    If Not Err = 0 Then GoTo Exit_Sub
    If Not objEntity.Layer = "IS_Streets" Then GoTo Get_Street
    
    Select Case objEntity.ObjectName
        Case "AcDbLine"
            Set objLine = objEntity
            iLength = CInt(objLine.Length)
            vStartPnt = objLine.StartPoint
            vEndPnt = objLine.EndPoint
            
            dDiff(0) = vEndPnt(0) - vStartPnt(0)
            dDiff(1) = vEndPnt(1) - vStartPnt(1)
            dDiff(2) = (dDiff(0) * dDiff(0)) + (dDiff(1) * dDiff(1))
            dDiff(2) = Sqr(dDiff(2))
            
            If vEndPnt(0) > vStartPnt(0) Then
                dToText(0) = vReturnPnt(0) - vStartPnt(0)
                dToText(1) = vReturnPnt(1) - vStartPnt(1)
            Else
                dToText(0) = vStartPnt(0) - vReturnPnt(0)
                dToText(1) = vStartPnt(1) - vReturnPnt(1)
            End If
            dToText(2) = Sqr((dToText(0) * dToText(0)) + (dToText(1) * dToText(1)))
            
            dDistScale = dToText(2) / dDiff(2)
            dInsertPnt(0) = vStartPnt(0) + (dDiff(0) * dDistScale)
            dInsertPnt(1) = vStartPnt(1) + (dDiff(1) * dDistScale)
            dInsertPnt(2) = 0#
            
            If dToText(0) = 0 Then
                dRotate = Pi / 2
            Else
                dRotate = Atn(dDiff(1) / dDiff(0))
            End If
            
            boolVal = ODRcs.Init(objEntity, True, False)
            
            strName = ""
            If Not ODRcs.Record.Item(6).Value = "" Then strName = ODRcs.Record.Item(6).Value & " "
            strName = strName & ODRcs.Record.Item(5).Value
            If Not ODRcs.Record.Item(11).Value = "" Then strName = strName & " " & ODRcs.Record.Item(11).Value & " "
            
        Case "AcDbPolyline"
            Set objLWP = objEntity
            iLength = CInt(objLWP.Length)
            vCoords = objLWP.Coordinates
            
            For i = 3 To UBound(vCoords) Step 2
                dDiff(0) = vCoords(i - 1) - vCoords(i - 3)
                dDiff(1) = vCoords(i) - vCoords(i - 2)
                dDiff(2) = Sqr((dDiff(0) * dDiff(0)) + (dDiff(1) * dDiff(1)))
            
                dToText(0) = vReturnPnt(0) - vCoords(i - 3)
                dToText(1) = vReturnPnt(1) - vCoords(i - 2)
                dToText(2) = Sqr((dToText(0) * dToText(0)) + (dToText(1) * dToText(1)))
                
                If dDiff(2) > dToText(2) Then
                    dFromText(0) = vReturnPnt(0) - vCoords(i - 1)
                    dFromText(1) = vReturnPnt(1) - vCoords(i)
                    dFromText(2) = Sqr((dFromText(0) * dFromText(0)) + (dFromText(1) * dFromText(1)))
                    
                    dTemp = (dFromText(2) + dToText(2)) / dDiff(2)
                    If dTemp < 1.01 Then
                        GoTo Exit_First_Next
                    End If
                End If
            Next i
Exit_First_Next:
            
            dDistScale = Abs(dToText(2) / dDiff(2))
            dInsertPnt(0) = vCoords(i - 3) + (dDiff(0) * dDistScale)
            dInsertPnt(1) = vCoords(i - 2) + (dDiff(1) * dDistScale)
            dInsertPnt(2) = 0#
            
            If dToText(0) = 0 Then
                dRotate = Pi / 2
            Else
                dRotate = Atn(dDiff(1) / dDiff(0))
            End If
            
            boolVal = ODRcs.Init(objEntity, True, False)
            
            strName = ""
            If Not ODRcs.Record.Item(6).Value = "" Then strName = ODRcs.Record.Item(6).Value & " "
            strName = strName & ODRcs.Record.Item(5).Value
            If Not ODRcs.Record.Item(11).Value = "" Then strName = strName & " " & ODRcs.Record.Item(11).Value & " "
            
        Case Else
            Me.show
            Exit Sub
    End Select
    
    iScale = CInt(Len(strName) * 9 * iHeight / 10)

    'Set objMText = ThisDrawing.ModelSpace.AddMText(dInsertPnt, iScale, strName)
    Set objMText = ThisDrawing.ModelSpace.AddMText(dInsertPnt, 0, strName)
    objMText.Layer = "IS_StreetsText"
    objMText.Height = iHeight
    objMText.AttachmentPoint = acAttachmentPointMiddleCenter
    objMText.InsertionPoint = dInsertPnt
    objMText.Rotation = dRotate
    'objMText.BackgroundFill = True
    objMText.Update
    
    GoTo Get_Street
    
Exit_Sub:
    'MsgBox Err.Number & vbCr & Err.Description
    
    Err.Clear
    
    Me.show
End Sub

Private Sub cbAddRoute_Click()
    Dim objSS2 As AcadSelectionSet
    Dim entObjects As AcadEntity
    Dim objPole As AcadBlockReference
    Dim vAttList As Variant
    Dim filterType, filterValue As Variant
    Dim grpCode(0) As Integer
    Dim grpValue(0) As Variant
    
    Me.Hide
    
    grpCode(0) = 2
    grpValue(0) = "sPole"
    filterType = grpCode
    filterValue = grpValue
    
    Set objSS2 = ThisDrawing.SelectionSets.Add("objSS2")
    objSS2.SelectOnScreen filterType, filterValue
    'objSS2.Select acSelectionSetAll, , , filterType, filterValue
    
    For Each objPole In objSS2
        vAttList = objPole.GetAttributes
        vAttList(0).TextString = UCase(tbPoleRoute.Value) & "/" & vAttList(0).TextString
        objPole.Update
    Next objPole
    
    objSS2.Clear
    objSS2.Delete
    Me.show
End Sub

Private Sub cbBlockName_Change()
    If cbBlockName.Value = "MiscUtility" Then tbAttribute.Enabled = True
End Sub

Private Sub cbConvertToCustomer_Click()
    Dim filterType, filterValue As Variant
    Dim grpCode(0) As Integer
    Dim grpValue(0) As Variant
    Dim objSS As AcadSelectionSet
    Dim objBlock As AcadBlockReference
    Dim objCustomer As AcadBlockReference
    Dim vAttList, vCustList As Variant
    Dim iCount As Integer
    
    On Error Resume Next
    
    iCount = 0
    
    grpCode(0) = 2
    grpValue(0) = "RES,TRLR,MDU,BUSINESS,CHURCH,SCHOOL,EXTENTION"
    filterType = grpCode
    filterValue = grpValue
    
    Err = 0
    Set objSS = ThisDrawing.SelectionSets.Add("objSS")
    If Not Err = 0 Then
        Set objSS = ThisDrawing.SelectionSets.Item("objSS")
        objSS.Clear
    End If
    
    objSS.Select acSelectionSetAll, , , filterType, filterValue
    MsgBox "Found:  " & objSS.count
    
    For Each objBlock In objSS
        vAttList = objBlock.GetAttributes
        
        Set objCustomer = ThisDrawing.ModelSpace.InsertBlock(objBlock.InsertionPoint, "Customer", 1#, 1#, 1#, 0#)
        vCustList = objCustomer.GetAttributes
        
        vCustList(1).TextString = vAttList(0).TextString
        vCustList(2).TextString = vAttList(1).TextString
        vCustList(3).TextString = vAttList(2).TextString
        
        Select Case objBlock.Name
            Case "BUSINESS"
                vCustList(0).TextString = "BUSINESS"
                vCustList(5).TextString = "B"
            Case "CHURCH"
                vCustList(0).TextString = "CHURCH"
                vCustList(5).TextString = "C"
            Case "EXTENTION"
                vCustList(0).TextString = "EXTENSION"
                vCustList(5).TextString = "X"
            Case "MDU"
                vCustList(0).TextString = "MDU"
                vCustList(5).TextString = "M"
            Case "RES"
                vCustList(0).TextString = "RESIDENCE"
                vCustList(5).TextString = ""
            Case "SCHOOL"
                vCustList(0).TextString = "SCHOOL"
                vCustList(5).TextString = "S"
            Case "TRLR"
                vCustList(0).TextString = "TRAILER"
                vCustList(5).TextString = "T"
        End Select
        
        objCustomer.Layer = "Customers"
        objCustomer.Update
        
        iCount = iCount + 1
    Next objBlock
    
    MsgBox "Converted  " & iCount & "  customers"
    
    objSS.Clear
    objSS.Delete
End Sub

Private Sub cbConvertTosFP_Click()
    Dim filterType, filterValue As Variant
    Dim grpCode(0) As Integer
    Dim grpValue(0) As Variant
    Dim objSS As AcadSelectionSet
    
    Dim objPole As AcadBlockReference
    Dim objBlock As AcadBlockReference
    Dim vAttList As Variant
    
    Dim strAtt(0 To 7) As String
    Dim iAtt As Integer
    Dim vLine, vTemp As Variant
    Dim dScale As Double
    
    On Error Resume Next
    
    'iAtt = 16
    
    grpCode(0) = 2
    grpValue(0) = "dFP"
    filterType = grpCode
    filterValue = grpValue
    
    Err = 0
    Set objSS = ThisDrawing.SelectionSets.Add("objSS")
    If Not Err = 0 Then
        Set objSS = ThisDrawing.SelectionSets.Item("objSS")
        objSS.Clear
    End If
    
    objSS.Select acSelectionSetAll, , , filterType, filterValue
    
    For Each objPole In objSS
        For i = 0 To 7
            strAtt(i) = ""
        Next i
        
        dScale = objPole.XScaleFactor
        
        vAttList = objPole.GetAttributes
        
        strAtt(0) = vAttList(0).TextString
        strAtt(1) = vAttList(0).TextString
        strAtt(2) = vAttList(2).TextString
        If Not vAttList(3).TextString = "" Then strAtt(3) = vAttList(3).TextString
        
        Set objBlock = ThisDrawing.ModelSpace.InsertBlock(objPole.InsertionPoint, "sFP", dScale, dScale, dScale, 0#)
        vAttList = objBlock.GetAttributes
        
        For i = 0 To 7
            If strAtt(i) = "" Then
                vAttList(i).TextString = ""
            Else
                vAttList(i).TextString = strAtt(i)
            End If
        Next i
        
        objBlock.Layer = objPole.Layer
        objBlock.Update
        
        objPole.Layer = "Integrity Delete"
        objPole.Update
        
        Err = 0
    Next objPole
    
    objSS.Clear
    objSS.Delete
End Sub

Private Sub cbConvertTosHH_Click()
    Dim objEntity As AcadEntity
    Dim objBlock, objHH As AcadBlockReference
    Dim vAttList, vHH, vReturnPnt As Variant
    
    On Error GoTo Exit_Sub
    Me.Hide
    
Get_Another:
    
    ThisDrawing.Utility.GetEntity objEntity, vReturnPnt, vbCr & "Select Handhole:"
    If Not TypeOf objEntity Is AcadBlockReference Then GoTo Exit_Sub
    
    Set objBlock = objEntity
    vAttList = objBlock.GetAttributes
    
    Set objHH = ThisDrawing.ModelSpace.InsertBlock(objBlock.InsertionPoint, "sHH", 1#, 1#, 1#, 0#)
    objHH.Layer = "Integrity Proposed"
    vHH = objHH.GetAttributes
    
    vHH(0).TextString = vAttList(0).TextString
    vHH(2).TextString = vAttList(1).TextString
    
    objHH.Update
    
    objBlock.Layer = "Integrity Delete"
    objBlock.Update
    
    GoTo Get_Another
    
Exit_Sub:
    Me.show
End Sub

Private Sub cbConvertTosPed_Click()
    Dim objEntity As AcadEntity
    Dim objBlock, objHH As AcadBlockReference
    Dim vAttList, vHH, vReturnPnt As Variant
    
    On Error GoTo Exit_Sub
    Me.Hide
    
Get_Another:
    
    ThisDrawing.Utility.GetEntity objEntity, vReturnPnt, vbCr & "Select Ped:"
    If Not TypeOf objEntity Is AcadBlockReference Then GoTo Exit_Sub
    
    Set objBlock = objEntity
    vAttList = objBlock.GetAttributes
    
    Set objHH = ThisDrawing.ModelSpace.InsertBlock(objBlock.InsertionPoint, "sPed", 1#, 1#, 1#, 0#)
    objHH.Layer = "Integrity Proposed"
    vHH = objHH.GetAttributes
    
    vHH(0).TextString = vAttList(0).TextString
    vHH(2).TextString = vAttList(1).TextString
    
    objHH.Update
    
    objBlock.Layer = "Integrity Delete"
    objBlock.Update
    
    GoTo Get_Another
    
Exit_Sub:
    Me.show
End Sub

Private Sub cbConvertTosPole_Click()
    Dim filterType, filterValue As Variant
    Dim grpCode(0) As Integer
    Dim grpValue(0) As Variant
    Dim objSS As AcadSelectionSet
    
    Dim objPole As AcadBlockReference
    Dim objBlock As AcadBlockReference
    Dim vAttList As Variant
    
    Dim strAtt(0 To 23) As String
    Dim iAtt As Integer
    Dim vLine, vTemp As Variant
    Dim dScale As Double
    
    On Error Resume Next
    
    grpCode(0) = 2
    grpValue(0) = "iPole"
    filterType = grpCode
    filterValue = grpValue
    
    Err = 0
    Set objSS = ThisDrawing.SelectionSets.Add("objSS")
    If Not Err = 0 Then
        Set objSS = ThisDrawing.SelectionSets.Item("objSS")
        objSS.Clear
    End If
    
    objSS.Select acSelectionSetAll, , , filterType, filterValue
    
    For Each objPole In objSS
        For i = 0 To 23
            strAtt(i) = ""
        Next i
        iAtt = 16
        
        dScale = objPole.XScaleFactor
        
        vAttList = objPole.GetAttributes
        
        strAtt(0) = vAttList(0).TextString
        strAtt(1) = vAttList(1).TextString
        strAtt(2) = vAttList(2).TextString
        strAtt(3) = vAttList(3).TextString
        strAtt(4) = vAttList(4).TextString
        strAtt(5) = vAttList(5).TextString
        strAtt(6) = vAttList(6).TextString
        strAtt(7) = vAttList(7).TextString
        strAtt(8) = vAttList(8).TextString
        strAtt(9) = vAttList(9).TextString
        strAtt(10) = vAttList(10).TextString
        strAtt(11) = vAttList(11).TextString
        strAtt(12) = vAttList(12).TextString
        strAtt(13) = vAttList(13).TextString
        strAtt(14) = vAttList(14).TextString
        
        For i = 15 To 26
            If Not vAttList(i).TextString = "" Then
                If InStr(vAttList(i).TextString, "=") > 1 Then
                    If i = 18 Then
                        If InStr(UCase(vAttList(i).TextString), "T") > 0 Then
                            vLine = Split(vAttList(i).TextString, "=")
                            
                            strAtt(15) = vLine(1)
                        Else
                            strAtt(iAtt) = vAttList(i).TextString
                            iAtt = iAtt + 1
                        End If
                    Else
                        strAtt(iAtt) = vAttList(i).TextString
                        iAtt = iAtt + 1
                    End If
                Else
                    Select Case i
                        Case Is = 15
                            If Not vAttList(i).TextString = "" Then
                                strAtt(iAtt) = "CATV=" & vAttList(i).TextString
                                iAtt = iAtt + 1
                            End If
                        Case Is = 16
                            If Not vAttList(i).TextString = "" Then
                                strAtt(iAtt) = "ATT=" & vAttList(i).TextString
                                iAtt = iAtt + 1
                            End If
                        Case Is = 17
                            If Not vAttList(i).TextString = "" Then
                                strAtt(iAtt) = "TDS=" & vAttList(i).TextString
                                iAtt = iAtt + 1
                            End If
                        Case Is = 18
                            If Not vAttList(i).TextString = "" Then
                                If InStr(UCase(vAttList(18).TextString), "T") > 0 Then
                                    strAtt(15) = vAttList(18).TextString
                                Else
                                    strAtt(iAtt) = "UTC=" & vAttList(i).TextString
                                    iAtt = iAtt + 1
                                End If
                            End If
                        Case Is = 19
                            If Not vAttList(i).TextString = "" Then
                                strAtt(iAtt) = "XO=" & vAttList(i).TextString
                                iAtt = iAtt + 1
                            End If
                        Case Is = 20
                            If Not vAttList(i).TextString = "" Then
                                strAtt(iAtt) = "ZAYO=" & vAttList(i).TextString
                                iAtt = iAtt + 1
                            End If
                        Case Is = 21
                            If Not vAttList(i).TextString = "" Then
                                strAtt(iAtt) = "CITY=" & vAttList(i).TextString
                                iAtt = iAtt + 1
                            End If
                        Case Is = 22
                            If Not vAttList(i).TextString = "" Then
                                strAtt(iAtt) = "TELCO=" & vAttList(i).TextString
                                iAtt = iAtt + 1
                            End If
                        Case Is = 23
                            If Not vAttList(i).TextString = "" Then
                                strAtt(iAtt) = "CITY=" & vAttList(i).TextString
                                iAtt = iAtt + 1
                            End If
                        Case Is = 24
                            If Not vAttList(i).TextString = "" Then
                                strAtt(iAtt) = "TRAFFIC=" & vAttList(i).TextString
                                iAtt = iAtt + 1
                            End If
                        Case Is = 25
                            If Not vAttList(i).TextString = "" Then
                                strAtt(iAtt) = "OHG=" & vAttList(i).TextString
                                iAtt = iAtt + 1
                            End If
                        Case Is = 26
                            If Not vAttList(i).TextString = "" Then
                                strAtt(iAtt) = "OTHER=" & vAttList(i).TextString
                                iAtt = iAtt + 1
                            End If
                    End Select
                End If
            End If
        Next i
        
        For i = iAtt To 23
            strAtt(i) = ""
        Next i
        
        Set objBlock = ThisDrawing.ModelSpace.InsertBlock(objPole.InsertionPoint, "sPole", dScale, dScale, dScale, 0#)
        vAttList = objBlock.GetAttributes
        
        For i = 0 To 23
            If strAtt(i) = "" Then
                vAttList(i).TextString = ""
            Else
                vAttList(i).TextString = strAtt(i)
            End If
        Next i
        
        objBlock.Layer = objPole.Layer
        objBlock.Update
        
        objPole.Layer = "Integrity Delete"
        objPole.Update
        
        Err = 0
    Next objPole
    
    objSS.Clear
    objSS.Delete
End Sub

Private Sub cbGetAttribute_Click()
    Dim objEntity As AcadEntity
    Dim objBlock As AcadBlockReference
    Dim vReturnPnt, vAttList As Variant
    Dim strLine As String
    Dim iAtt As Integer
        
    On Error Resume Next
    
    If tbAttNumber.Value = "" Then
        iAtt = 0
    Else
        iAtt = CInt(tbAttNumber.Value)
    End If
    
    Me.Hide
    
    ThisDrawing.Utility.GetEntity objEntity, vReturnPnt, vbCr & "Select Block with Attributes: "
    
    If Not TypeOf objEntity Is AcadBlockReference Then GoTo Exit_Sub
    Set objBlock = objEntity
    
    vAttList = objBlock.GetAttributes
    strLine = vAttList(iAtt).TextString
    If strLine = "" Then GoTo Exit_Sub
    
    'strLine = Replace(strLine, vbCrLf, "<cl>")
    'strLine = Replace(strLine, vbCr, "<c>")
    'strLine = Replace(strLine, vbLf, "<l>")
    'strLine = Replace(strLine, "<c>", "<c>" & vbCr)
    
    tbAttributeValue.Value = strLine
    
Exit_Sub:
    Me.show
End Sub

Private Sub cbPntToBlock_Click()
    If lbLayers.ListIndex < 0 Then Exit Sub
    If cbBlockName.Value = "" Then Exit Sub
    
    Dim filterType, filterValue As Variant
    Dim grpCode(0) As Integer
    Dim grpValue(0) As Variant
    Dim objSS As AcadSelectionSet
    
    Dim objEntity As AcadEntity
    Dim objPoint As AcadPoint
    Dim objBlock As AcadBlockReference
    Dim vAtt As Variant
    Dim strBlockName, strLayer As String
    Dim dInsertPnt(0 To 2) As Double
    Dim dScale As Double
    
    If cbScale.Value = "" Then
        dScale = 1#
    Else
        dScale = CDbl(cbScale.Value) / 100
    End If
    
    strBlockName = cbBlockName.Value
    strLayer = lbLayers.List(lbLayers.ListIndex)
    
    grpCode(0) = 8
    grpValue(0) = strLayer
    filterType = grpCode
    filterValue = grpValue
    
    On Error Resume Next
    
    Err = 0
    Set objSS = ThisDrawing.SelectionSets.Add("objSS")
    If Not Err = 0 Then
        Set objSS = ThisDrawing.SelectionSets.Item("objSS")
        objSS.Clear
    End If
    
    objSS.Select acSelectionSetAll, , , filterType, filterValue
    MsgBox lbLayers.List(lbLayers.ListIndex) & " found:  " & objSS.count
    
    For Each objEntity In objSS
        If TypeOf objEntity Is AcadPoint Then
            Set objPoint = objEntity
            
            dInsertPnt(0) = objPoint.Coordinates(0)
            dInsertPnt(1) = objPoint.Coordinates(1)
            dInsertPnt(2) = objPoint.Coordinates(2)
            
            Set objBlock = ThisDrawing.ModelSpace.InsertBlock(dInsertPnt, strBlockName, dScale, dScale, dScale, 0#)
            objBlock.Layer = strLayer
            If cbBlockName.Value = "MiscUtility" Then
                vAtt = objBlock.GetAttributes
                If Not tbAttribute.Value = "" Then vAtt(0).TextString = UCase(Left(tbAttribute.Value, 2))
            End If
            objBlock.Update
            
            If cbDeletePoint.Value = True Then objPoint.Delete
        End If
    Next objEntity
    
    objSS.Clear
    objSS.Delete
End Sub

Private Sub cbQuit_Click()
    Me.Hide
End Sub

Private Sub CommandButton1_Click()
    Dim filterType, filterValue As Variant
    Dim grpCode(0) As Integer
    Dim grpValue(0) As Variant
    Dim objSS As AcadSelectionSet
    
    Dim objBlock As AcadBlockReference
    Dim vAttList As Variant
    
    Dim strLine, strTemp As String
    Dim vLine, vTemp As Variant
    
    On Error Resume Next
    
    grpCode(0) = 2
    grpValue(0) = "sPole"
    filterType = grpCode
    filterValue = grpValue
    
    Err = 0
    Set objSS = ThisDrawing.SelectionSets.Add("objSS")
    If Not Err = 0 Then
        Set objSS = ThisDrawing.SelectionSets.Item("objSS")
        objSS.Clear
    End If
    
    objSS.Select acSelectionSetAll, , , filterType, filterValue
    
    For Each objBlock In objSS
        vAttList = objBlock.GetAttributes
        If vAttList(4).TextString = "" Then GoTo Next_objBlock
        
        If vAttList(2).TextString = tbAtt2.Value Then
            vLine = Split(vAttList(4).TextString, " ")
            For i = 0 To UBound(vLine)
                vTemp = Split(vLine(i), "=")
                If UBound(vTemp) < 1 Then vLine(i) = tbAtt4.Value & "=" & vTemp(0)
            Next i
            
            strTemp = vLine(0)
            If UBound(vLine) > 0 Then
                For i = 0 To UBound(vLine)
                    strTemp = strTemp & " " & vLine(i)
                Next i
            End If
            
            vAttList(4).TextString = strTemp
            objBlock.Update
        End If
        
Next_objBlock:
    Next objBlock
    
    objSS.Clear
    objSS.Delete
End Sub

Private Sub UserForm_Initialize()
    cbScale.AddItem "50"
    cbScale.AddItem "75"
    cbScale.AddItem "100"
    cbScale.Value = "100"
    
    Dim objBlocks As AcadBlocks
    Dim strLine As String
            
    Set objBlocks = ThisDrawing.Blocks
    For i = 0 To objBlocks.count - 1
        strLine = objBlocks(i).Name
        If Not Left(strLine, 1) = "*" Then cbBlockName.AddItem objBlocks(i).Name
    Next i
    
    Dim objLayers As AcadLayers
    Dim objLayer As AcadLayer
    
    Set objLayers = ThisDrawing.Layers
    For Each objLayer In objLayers
        lbLayers.AddItem objLayer.Name
    Next objLayer
    
End Sub

Attribute VB_Name = "zxxValidateCounts3"
Attribute VB_Base = "0{8B0213A7-7754-412B-A4A9-3D6187CC44DF}{FD203926-98F7-4ECD-B3FD-4482F6E34AE6}"
Attribute VB_GlobalNameSpace = False
Attribute VB_Creatable = False
Attribute VB_PredeclaredId = True
Attribute VB_Exposed = False
Attribute VB_TemplateDerived = False
Attribute VB_Customizable = False
Dim objSS As AcadSelectionSet
Dim iIndex As Integer
Dim vPnt1, vPnt2 As Variant

Private Sub cbGetCallouts_Click()
    Dim objBlock As AcadBlockReference
    Dim filterType, filterValue As Variant
    Dim grpCode(0) As Integer
    Dim grpValue(0) As Variant
    Dim vAtt As Variant
    Dim vResult As Variant
    Dim vLine, vItem, vTemp As Variant
    Dim strCounts As String
    Dim iAtt As Integer
    
    On Error Resume Next
    
    Me.Hide
        
    Err = 0
    vPnt1 = ThisDrawing.Utility.GetPoint(, "Get BL Corner: ")
    vPnt2 = ThisDrawing.Utility.GetCorner(vPnt1, vbCr & "Get UR Corner: ")
    If Not Err = 0 Then GoTo Exit_Sub
    
    lbList.Clear
    objSS.Clear
    
    grpCode(0) = 2
    grpValue(0) = "sPole,sPed,sHH,sPanel"
    filterType = grpCode
    filterValue = grpValue
    objSS.Select acSelectionSetWindow, vPnt1, vPnt2, filterType, filterValue
    
    'MsgBox objSS.count
    
    For i = 0 To objSS.count - 1
        Set objBlock = objSS.Item(i)
        
        vAtt = objBlock.GetAttributes
        If vAtt(0).TextString = "" Then GoTo Next_objBlock
        If vAtt(0).TextString = "POLE" Then GoTo Next_objBlock
        If vAtt(0).TextString = "PED" Then GoTo Next_objBlock
        If vAtt(0).TextString = "HH" Then GoTo Next_objBlock
        If vAtt(0).TextString = "PANEL" Then GoTo Next_objBlock
        
        If objBlock.Name = "sPole" Then
            vLine = Split(UCase(vAtt(25).TextString), vbCr)
        Else
            vLine = Split(UCase(vAtt(5).TextString), vbCr)
        End If
        
        'MsgBox vLine(0) & vbCr & UBound(vLine) & vLine(UBound(vLine))
        
        For j = 0 To UBound(vLine)
            vItem = Split(vLine(j), " / ")
            vTemp = Split(vItem(0), ": ")
            strCounts = Replace(vItem(1), " + ", "\P")
            
            lbList.AddItem vAtt(0).TextString
            lbList.List(lbList.ListCount - 1, 1) = objBlock.Name
            lbList.List(lbList.ListCount - 1, 2) = vTemp(0)
            lbList.List(lbList.ListCount - 1, 3) = vTemp(1)
            lbList.List(lbList.ListCount - 1, 4) = strCounts
            lbList.List(lbList.ListCount - 1, 7) = i
        
            vResult = ValidateCounts(CStr(vTemp(1)), strCounts)
        
            If vResult(0) = "Y" Then
                lbList.List(lbList.ListCount - 1, 5) = "Y"
            Else
                lbList.List(lbList.ListCount - 1, 5) = ""
            End If
        
            If vResult(1) = "Y" Then
                lbList.List(lbList.ListCount - 1, 6) = "Y"
            Else
                lbList.List(lbList.ListCount - 1, 6) = ""
            End If
        Next j
Next_objBlock:
    Next i
    
Exit_Sub:
    tbListCount.Value = lbList.ListCount
    Me.show
End Sub

Private Sub cbQuit_Click()
    objSS.Clear
    objSS.Delete
    
    Me.Hide
End Sub

Private Sub cbRemove_Click()
    If lbList.ListCount < 1 Then Exit Sub
    
    For i = lbList.ListCount - 1 To 0 Step -1
        If lbList.List(i, 5) = "Y" Then
            If lbList.List(i, 6) = "Y" Then lbList.RemoveItem i
        End If
    Next i
    
    tbListCount.Value = lbList.ListCount
End Sub

Private Sub cbUpdate_Click()
    If iIndex < 0 Then GoTo Exit_Sub
    
    Dim objBlock As AcadBlockReference
    Dim vAtt As Variant
    Dim strText As String
    Dim i As Integer
    
    strText = Replace(UCase(tbCallout.Value), vbLf, "")
    strText = Replace(strText, vbCr, "\P")
    strText = Replace(strText, vbTab, " ")
    
    lbList.List(iIndex, 3) = UCase(tbCable.Value)
    lbList.List(iIndex, 4) = strText
    
    'i = CInt(lbList.List(iIndex, 7))
    'Set objBlock = objSS.Item(i)
    'vAtt = objBlock.GetAttributes
    
    'tbCable.Value = UCase(tbCable.Value)
    'vAtt(1).TextString = tbCable.Value
    'vAtt(2).TextString = strText
    
    'objBlock.Update
        
    vResult = ValidateCounts(tbCable.Value, strText)
    If vResult(0) = "Y" Then lbList.List(iIndex, 5) = "Y"
    If vResult(1) = "Y" Then lbList.List(iIndex, 6) = "Y"
    
    'Call UpdatePole(vAtt(0).TextString, vAtt(1).TextString, vAtt(2).TextString)
    
Exit_Sub:
    tbCable.Value = ""
    tbCallout.Value = ""
    
    iIndex = -1
    cbUpdate.Enabled = False
End Sub

Private Sub lbList_DblClick(ByVal Cancel As MSForms.ReturnBoolean)
    Dim strText As String
    
    iIndex = lbList.ListIndex
    cbUpdate.Enabled = True
    
    strText = Replace(UCase(lbList.List(iIndex, 4)), "\P", vbCr)
    strText = Replace(strText, " ", vbTab)
    tbCallout.Value = strText
    tbCable.Value = UCase(lbList.List(iIndex, 3))
End Sub

Private Sub UserForm_Initialize()
    lbList.ColumnCount = 8
    lbList.ColumnWidths = "120;36;24;96;120;36;36;18"
    
    iIndex = -1
    
    On Error Resume Next
    
    Set objSS = ThisDrawing.SelectionSets.Add("objSS")
    If Not Err = 0 Then
        Set objSS = ThisDrawing.SelectionSets.Item("objSS")
    End If
End Sub

Private Function ValidateCounts(strCable As String, strCallout As String)
    Dim strResult, strColor As String
    Dim vResult As Variant
    Dim vLine, vItem, vCount, vTemp As Variant
    
    Dim iCable, iCount, iTCount As Integer
    Dim iLow, iHigh As Integer
    
    vLine = Split(strCable, "(")
    vItem = Split(vLine(1), ")")
    iCable = CInt(vItem(0))
    iCount = 0
    strColor = "Y"
    
    vLine = Split(strCallout, "\P")
    For i = 0 To UBound(vLine)
        If InStr(vLine(i), ")") > 0 Then
            vTemp = Split(vLine(i), ")")
            vItem = Split(vTemp(1), ": ")
        Else
            vItem = Split(vLine(i), ": ")
        End If
        vCount = Split(vItem(1), "-")
        
        iTCount = iCount + 1
        While iTCount > 12
            iTCount = iTCount - 12
        Wend
        
        iLow = CInt(vCount(0))
        While iLow > 12
            iLow = iLow - 12
        Wend
        
        If Not iLow = iTCount Then strColor = "N"
        
        If UBound(vCount) = 0 Then
            iCount = iCount + 1
        Else
            iCount = iCount + CInt(vCount(1)) - CInt(vCount(0)) + 1
        End If
    Next i
    
    If iCount = iCable Then
        strResult = "Y"
    Else
        strResult = "N"
    End If
    
    'MsgBox strCable & vbCr & vbCr & strCallout
    
    strResult = strResult & "," & strColor
    vResult = Split(strResult, ",")
    
    ValidateCounts = vResult
End Function

Private Sub UpdatePole(strName As String, strCable As String, strCounts As String)
    Dim strPole, strPosition, strLine As String
    Dim strTemp As String
    Dim vLine, vItem, vTemp As Variant
    
    vLine = Split(strName, ": ")
    strPole = vLine(0)
    strPosition = vLine(1)
    strLine = strPosition & ": " & strCable & " / " & Replace(strCounts, "\P", " + ")
    
    strTemp = strPole & vbCr & strPosition & vbCr & strLine
    MsgBox "Pole not updated" & vbCr & vbCr & strTemp
End Sub

Attribute VB_Name = "zxxValidateCounts4"
Attribute VB_Base = "0{964A4B92-42AA-432C-B9FC-75F1E99F8A9A}{BB11B1C5-F078-4C51-8385-E5039E847EAE}"
Attribute VB_GlobalNameSpace = False
Attribute VB_Creatable = False
Attribute VB_PredeclaredId = True
Attribute VB_Exposed = False
Attribute VB_TemplateDerived = False
Attribute VB_Customizable = False

Dim objSSPoles As AcadSelectionSet
Dim objSS As AcadSelectionSet
Dim iIndex As Integer
Dim vPnt1, vPnt2 As Variant

Private Sub cbGetCallouts_Click()
    Dim objBlock As AcadBlockReference
    Dim filterType, filterValue As Variant
    Dim grpCode(0) As Integer
    Dim grpValue(0) As Variant
    Dim vAtt As Variant
    Dim vResult As Variant
    
    On Error Resume Next
    
    Me.Hide
        
    Err = 0
    vPnt1 = ThisDrawing.Utility.GetPoint(, "Get BL Corner: ")
    vPnt2 = ThisDrawing.Utility.GetCorner(vPnt1, vbCr & "Get UR Corner: ")
    If Not Err = 0 Then GoTo Exit_Sub
    
    lbList.Clear
    objSS.Clear
    
    grpCode(0) = 2
    grpValue(0) = "Callout"
    filterType = grpCode
    filterValue = grpValue
    objSS.Select acSelectionSetWindow, vPnt1, vPnt2, filterType, filterValue
    
    For i = 0 To objSS.count - 1
        Set objBlock = objSS.Item(i)
        
        vAtt = objBlock.GetAttributes
        If InStr(vAtt(1).TextString, "+HO1") > 0 Then GoTo Next_objBlock
        If vAtt(1).TextString = "CALLOUT" Then GoTo Next_objBlock
        
        lbList.AddItem vAtt(0).TextString
        lbList.List(lbList.ListCount - 1, 1) = UCase(vAtt(1).TextString)
        lbList.List(lbList.ListCount - 1, 2) = UCase(vAtt(2).TextString)
        lbList.List(lbList.ListCount - 1, 5) = i
        
        vResult = ValidateCounts(UCase(vAtt(1).TextString), UCase(vAtt(2).TextString))
        
        If vResult(0) = "Y" Then
            lbList.List(lbList.ListCount - 1, 3) = "Y"
        Else
            lbList.List(lbList.ListCount - 1, 3) = ""
        End If
        
        If vResult(1) = "Y" Then
            lbList.List(lbList.ListCount - 1, 4) = "Y"
        Else
            lbList.List(lbList.ListCount - 1, 4) = ""
        End If
Next_objBlock:
    Next i
    
Exit_Sub:
    tbListCount.Value = lbList.ListCount
    Me.show
End Sub

Private Sub cbQuit_Click()
    objSS.Clear
    objSS.Delete
    
    Me.Hide
End Sub

Private Sub cbRemove_Click()
    If lbList.ListCount < 1 Then Exit Sub
    
    For i = lbList.ListCount - 1 To 0 Step -1
        If lbList.List(i, 3) = "Y" Then
            If lbList.List(i, 4) = "Y" Then lbList.RemoveItem i
        End If
    Next i
    
    tbListCount.Value = lbList.ListCount
End Sub

Private Sub cbUpdate_Click()
    If iIndex < 0 Then GoTo Exit_Sub
    
    Dim objBlock As AcadBlockReference
    Dim vAtt As Variant
    Dim strText As String
    Dim i As Integer
    
    strText = Replace(UCase(tbCallout.Value), vbLf, "")
    strText = Replace(strText, vbCr, "\P")
    
    lbList.List(iIndex, 1) = UCase(tbCable.Value)
    lbList.List(iIndex, 2) = strText
    
    i = CInt(lbList.List(iIndex, 5))
    Set objBlock = objSS.Item(i)
    vAtt = objBlock.GetAttributes
    
    tbCable.Value = UCase(tbCable.Value)
    vAtt(1).TextString = tbCable.Value
    vAtt(2).TextString = strText
    
    objBlock.Update
        
    vResult = ValidateCounts(tbCable.Value, strText)
    If vResult(0) = "Y" Then lbList.List(iIndex, 3) = "Y"
    If vResult(1) = "Y" Then lbList.List(iIndex, 4) = "Y"
    
    Call UpdatePole(vAtt(0).TextString, vAtt(1).TextString, vAtt(2).TextString)
    
Exit_Sub:
    tbCable.Value = ""
    tbCallout.Value = ""
    
    iIndex = -1
    cbUpdate.Enabled = False
End Sub

Private Sub lbList_DblClick(ByVal Cancel As MSForms.ReturnBoolean)
    Dim strText As String
    
    iIndex = lbList.ListIndex
    cbUpdate.Enabled = True
    
    strText = Replace(UCase(lbList.List(iIndex, 2)), "\P", vbCr)
    tbCallout.Value = strText
    tbCable.Value = UCase(lbList.List(iIndex, 1))
End Sub

Private Sub UserForm_Initialize()
    lbList.ColumnCount = 6
    lbList.ColumnWidths = "120;96;120;36;36;18"
    
    iIndex = -1
    
    On Error Resume Next
    
    Set objSS = ThisDrawing.SelectionSets.Add("objSS")
    If Not Err = 0 Then
        Set objSS = ThisDrawing.SelectionSets.Item("objSS")
    End If
End Sub

Private Function ValidateCounts(strCable As String, strCallout As String)
    Dim strResult, strColor As String
    Dim vResult As Variant
    Dim vLine, vItem, vCount, vTemp As Variant
    
    Dim iCable, iCount, iTCount As Integer
    Dim iLow, iHigh As Integer
    
    vLine = Split(strCable, "(")
    vItem = Split(vLine(1), ")")
    iCable = CInt(vItem(0))
    iCount = 0
    strColor = "Y"
    
    vLine = Split(strCallout, "\P")
    For i = 0 To UBound(vLine)
        vItem = Split(vLine(i), ": ")
        vCount = Split(vItem(UBound(vItem)), "-")
        
        iTCount = iCount + 1
        While iTCount > 12
            iTCount = iTCount - 12
        Wend
        
        iLow = CInt(vCount(0))
        While iLow > 12
            iLow = iLow - 12
        Wend
        
        If Not iLow = iTCount Then strColor = "N"
        
        If UBound(vCount) = 0 Then
            iCount = iCount + 1
        Else
            iCount = iCount + CInt(vCount(1)) - CInt(vCount(0)) + 1
        End If
    Next i
    
    If iCount = iCable Then
        strResult = "Y"
    Else
        strResult = "N"
    End If
    
    'MsgBox strCable & vbCr & vbCr & strCallout
    
    strResult = strResult & "," & strColor
    vResult = Split(strResult, ",")
    
    ValidateCounts = vResult
End Function

Private Sub UpdatePole(strName As String, strCable As String, strCounts As String)
    Dim strPole, strPosition, strLine As String
    Dim strTemp As String
    Dim vLine, vItem, vTemp As Variant
    
    vLine = Split(strName, ": ")
    strPole = vLine(0)
    strPosition = vLine(1)
    strLine = strPosition & ": " & strCable & " / " & Replace(strCounts, "\P", " + ")
    
    strTemp = strPole & vbCr & strPosition & vbCr & strLine
    MsgBox "Pole not updated" & vbCr & vbCr & strTemp
End Sub

Attribute VB_Name = "zzDrawTest"
Attribute VB_Base = "0{890867FD-C0B0-4E75-8915-42651D20EF64}{7C526FA9-B7C8-41E8-879C-DDDFAC643CB3}"
Attribute VB_GlobalNameSpace = False
Attribute VB_Creatable = False
Attribute VB_PredeclaredId = True
Attribute VB_Exposed = False
Attribute VB_TemplateDerived = False
Attribute VB_Customizable = False
Option Explicit
' use the
Private m_objDrawing As AJPiUFDraw


Private Sub cbDrawLine_Click()
    Dim shpTemp As Shape
    
    Set shpTemp = m_objDrawing.Line(50, 150, 100, 150)
    If Not shpTemp Is Nothing Then shpTemp.Line.Weight = 1
    Set shpTemp = m_objDrawing.Line(100, 150, 100, 200)
    If Not shpTemp Is Nothing Then shpTemp.Line.Weight = 2
    Set shpTemp = m_objDrawing.Line(100, 200, 50, 200)
    If Not shpTemp Is Nothing Then shpTemp.Line.Weight = 3
    Set shpTemp = m_objDrawing.Line(50, 200, 50, 150)
    If Not shpTemp Is Nothing Then shpTemp.Line.Weight = 4
    
    Set shpTemp = m_objDrawing.Line(50, 150, 75, 175)
    If Not shpTemp Is Nothing Then shpTemp.Line.ForeColor.RGB = RGB(255, 0, 0)
    Set shpTemp = m_objDrawing.Line(100, 150, 75, 175)
    If Not shpTemp Is Nothing Then shpTemp.Line.ForeColor.RGB = RGB(0, 255, 0)
    Set shpTemp = m_objDrawing.Line(100, 200, 75, 175)
    If Not shpTemp Is Nothing Then shpTemp.Line.ForeColor.RGB = RGB(0, 0, 255)
    Set shpTemp = m_objDrawing.Line(50, 200, 75, 175)
    If Not shpTemp Is Nothing Then shpTemp.Line.ForeColor.RGB = RGB(255, 255, 255)
    
    m_objDrawing.Paint
End Sub

Private Sub UserForm_Initialize()
    Set m_objDrawing = New AJPiUFDraw
    Set m_objDrawing.CanvasUserform = Me
End Sub

Attribute VB_Name = "zzMRnumbers"
Attribute VB_Base = "0{2DF8CF59-68DF-4473-B2D8-D354619068FE}{48479F14-0ED8-413D-8A08-E30A7D954AE7}"
Attribute VB_GlobalNameSpace = False
Attribute VB_Creatable = False
Attribute VB_PredeclaredId = True
Attribute VB_Exposed = False
Attribute VB_TemplateDerived = False
Attribute VB_Customizable = False
Private Sub cbGetPoles_Click()
    Dim objSS As AcadSelectionSet
    Dim filterType, filterValue As Variant
    Dim grpCode(0) As Integer
    Dim grpValue(0) As Variant
    Dim vPnt1, vPnt2 As Variant
    Dim objBlock As AcadBlockReference
    Dim vAttList As Variant
    Dim vLine, vItem, vTemp As Variant
    Dim iIndex, iTemp As Integer
    
    'Dim dN, dE As Double
    'Dim vLL As Variant
    
    iIndex = -1

    grpCode(0) = 2
    grpValue(0) = "sPole"
    filterType = grpCode
    filterValue = grpValue
    
  On Error Resume Next
  
    Me.Hide
    
    vPnt1 = ThisDrawing.Utility.GetPoint(, "Get BL Corner: ")
    vPnt2 = ThisDrawing.Utility.GetCorner(vPnt1, vbCr & "Get UR Corner: ")
  
    Err = 0
    
    Set objSS = ThisDrawing.SelectionSets.Add("objSS")
    If Not Err = 0 Then
        Set objSS = ThisDrawing.SelectionSets.Item("objSS")
        Err = 0
    End If
    
    objSS.Select acSelectionSetWindow, vPnt1, vPnt2, filterType, filterValue
    If Not Err = 0 Then
        MsgBox "Error: " & Err.Number & vbCr & Err.Description
        Me.show
        Exit Sub
    End If
    
    For Each objBlock In objSS
        vAttList = objBlock.GetAttributes
        If vAttList(0).TextString = "" Then GoTo Next_objBlock
        If vAttList(0).TextString = "POLE" Then GoTo Next_objBlock
        If vAttList(1).TextString = "INCOMPLETE" Then GoTo Next_objBlock
        
        If lbOwner.ListCount > 0 Then
            For i = 0 To lbOwner.ListCount - 1
                If lbOwner.List(i, 0) = vAttList(2).TextString Then
                    lbOwner.List(i, 1) = CInt(lbOwner.List(i, 1)) + 1
                    GoTo Found_Owner
                End If
            Next i
        End If
        
        lbOwner.AddItem vAttList(2).TextString
        lbOwner.List(lbOwner.ListCount - 1, 1) = "1"
        
Found_Owner:
        
        For i = 16 To 23
            If vAttList(i).TextString = "" Then GoTo Next_I
            
            vLine = Split(vAttList(i).TextString, "=")
            If UBound(vLine) > 0 Then
                If vLine(1) = "" Then GoTo Next_I
                vItem = Split(vLine(1), " ")
                If lbMR.ListCount > 0 Then
                    For j = 0 To lbMR.ListCount - 1
                        If lbMR.List(j, 0) = vLine(0) Then
                            lbMR.List(j, 1) = CInt(lbMR.List(j, 1)) + 1
                                
                            iIndex = j
                            GoTo Found_MR
                        End If
                    Next j
                End If
                        
                lbMR.AddItem vLine(0)
                iIndex = lbMR.ListCount - 1
                lbMR.List(iIndex, 1) = "1"
                lbMR.List(iIndex, 2) = "0"
                lbMR.List(iIndex, 3) = "0"
                lbMR.List(iIndex, 4) = "0"
Found_MR:
                For j = 0 To UBound(vItem)
                    iTemp = CInt(lbMR.List(iIndex, 2)) + 1
                    lbMR.List(iIndex, 2) = iTemp
                    
                    'MsgBox iTemp
                            
                    If InStr(vItem(j), ")") > 0 Then
                        iTemp = CInt(lbMR.List(iIndex, 3)) + 1
                        lbMR.List(iIndex, 3) = iTemp
                        'MsgBox iTemp
                    Else
                        If InStr(UCase(vItem(j)), "X") > 0 Then
                            iTemp = CInt(lbMR.List(iIndex, 3)) + 1
                            lbMR.List(iIndex, 3) = iTemp
                            'MsgBox iTemp
                        End If
                    End If
                Next j
            End If
Next_I:
        Next i
        
Next_objBlock:
    Next objBlock
    
Exit_Sub:
    objSS.Clear
    objSS.Delete
    Me.show
End Sub

Private Sub cbQuit_Click()
    Me.Hide
End Sub

Private Sub UserForm_Initialize()
    lbMR.ColumnCount = 5
    lbMR.ColumnWidths = "96;36;36;36;30"
    
    lbOwner.ColumnCount = 2
    lbOwner.ColumnWidths = "96;30"
End Sub

Attribute VB_Name = "zzzJMS"
Attribute VB_Base = "0{2C2B965A-DBFE-4A41-B6ED-F662535F1FBE}{81692CB1-9CB9-4085-B9F8-85A464F56B13}"
Attribute VB_GlobalNameSpace = False
Attribute VB_Creatable = False
Attribute VB_PredeclaredId = True
Attribute VB_Exposed = False
Attribute VB_TemplateDerived = False
Attribute VB_Customizable = False
Private Sub UserForm_Initialize()
    lbJobs.ColumnCount = 2
    lbJobs.ColumnWidths = "48;12"
    
    lbJobs.AddItem "2019-555"
        lbJobs.List(0, 1) = "X"
    lbJobs.AddItem "2020-756"
        lbJobs.List(1, 1) = "A"
    lbJobs.AddItem "2021-010"
        lbJobs.List(2, 1) = "C"
    lbJobs.AddItem "2021-015"
        lbJobs.List(3, 1) = "D"
    lbJobs.AddItem "2021-559"
        lbJobs.List(4, 1) = "H"
    
    
    lbFolder.ColumnCount = 2
    lbFolder.ColumnWidths = "16;80"
    
    lbFolder.AddItem "*"
        lbFolder.List(0, 1) = "Planning"
    lbFolder.AddItem ""
        lbFolder.List(1, 1) = "      Information"
    lbFolder.AddItem "*"
        lbFolder.List(2, 1) = "Design"
    lbFolder.AddItem ""
        lbFolder.List(3, 1) = "      CADD"
    lbFolder.AddItem ""
        lbFolder.List(4, 1) = "      Reports"
    lbFolder.AddItem "!"
        lbFolder.List(5, 1) = "Permits"
    lbFolder.AddItem ""
        lbFolder.List(6, 1) = "      Submitted"
    lbFolder.AddItem ""
        lbFolder.List(7, 1) = "      Approved"
    lbFolder.AddItem ""
        lbFolder.List(8, 1) = "Construction"
    lbFolder.AddItem ""
        lbFolder.List(9, 1) = "      Sheets"
    lbFolder.AddItem ""
        lbFolder.List(10, 1) = "      Reports"
    lbFolder.AddItem ""
        lbFolder.List(11, 1) = "Asbuilts"
    lbFolder.AddItem ""
        lbFolder.List(12, 1) = "      Notes"
    lbFolder.AddItem ""
        lbFolder.List(13, 1) = "      Reports"
    
    
    lbFiles.ColumnCount = 2
    lbFiles.ColumnWidths = "180;60"
    
    lbFiles.AddItem "2021-559 MR - All.dwg"
    lbFiles.List(0, 1) = "CADD File"
    lbFiles.AddItem "2021-559 MAKE READY - ATT.pdf"
    lbFiles.List(1, 1) = "MR Submit"
    lbFiles.AddItem "2021-559 MAKE READY - COMCAST.pdf"
    lbFiles.List(2, 1) = "MR Submit"
    lbFiles.AddItem "2021-559 TDOT PERMIT.dwg"
    lbFiles.List(3, 1) = "CADD File"
    lbFiles.AddItem "2021-559 TDOT PERMIT - SR99.pdf"
    lbFiles.List(4, 1) = "Permit Submit"
    lbFiles.AddItem "2021-559 TDOT PERMIT - COVER.pdf"
    lbFiles.List(5, 1) = "Permit Submit"
    
    Dim strText As String
    
    strText = "2021-559 SUBDIVISION NAME - PHASE #" & vbCr
    strText = strText & "Exchange:" & vbTab & "Full Name, Code, or CLLI" & vbCr
    strText = strText & "Type:" & vbTab & vbTab & "GF-DSPLIT-SFU" & vbCr & vbCr
    strText = strText & "Contact:" & vbTab & "Project Manager" & vbCr
    strText = strText & "Phone:" & vbTab & "888-555-1212" & vbCr
    strText = strText & "Email:" & vbTab & "project.manager@contractor.com" & vbCr
    strText = strText & "Address:" & vbTab & "N/A" & vbCr & vbCr
    strText = strText & "05/04/2021 UC-Engineer: Handoff to Integrity" & vbCr
    strText = strText & "06/08/2021 Integrity-Planner: *** PLANNING COMPLETE" & vbCr
    strText = strText & "06/14/2021 Integrity-Manager: Conduit placement started but not complete." & vbCr
    strText = strText & "06/30/2021 Integrity-Manager: Conduit placement complete." & vbCr
    strText = strText & "07/16/2021 Integrity-Manager: *** DESIGN COMPLETE" & vbCr
    strText = strText & "07/20/2021 UC-Manager: *** PROJECT APPROVED" & vbCr
    strText = strText & "07/23/2021 UC-Permitting: *** TDOT PERMIT SUBMITTED" & vbCr
    strText = strText & "07/23/2021 UC-Permitting: *** ATT MR PACKAGE SUBMITTED" & vbCr
    strText = strText & "07/23/2021 UC-Permitting: *** COMCAST MR PACKAGE SUBMITTED" & vbCr
    strText = strText & "09/17/2021 UC-Manager: *** REVISION REQUIRED" & vbCr
    strText = strText & vbTab & vbTab & "Why:" & vbTab & "Cable need to be rerouted due to Future TDOT Project" & vbCr
    strText = strText & vbTab & vbTab & "Where:" & vbTab & "DWG 003-Pole F5000A/10 to DWG 005-Pole F5000A/21" & vbCr
    strText = strText & "09/30/2021 Integrity-Manager: *** REVISION 09/17/2021 COMPLETE" & vbCr
    
    tbProjectNotes.Value = strText
End Sub

Attribute VB_Name = "zzzzPoleCOMMupdate"
Attribute VB_Base = "0{5F7E3D99-851B-405B-BAC5-E2CF07FB545B}{96C2A0A8-BF3A-4EE8-83F9-459D3BCD9B72}"
Attribute VB_GlobalNameSpace = False
Attribute VB_Creatable = False
Attribute VB_PredeclaredId = True
Attribute VB_Exposed = False
Attribute VB_TemplateDerived = False
Attribute VB_Customizable = False
Dim objBlock As AcadBlockReference

Private Sub cbAdd_Click()
    If cbAdd.Caption = "Add" Then
        lbList.AddItem UCase(tbAlias.Value)
        lbList.List(lbList.ListCount - 1, 1) = UCase(tbCompany.Value)
    Else
        lbList.List(lbList.ListIndex, 0) = UCase(tbAlias.Value)
        lbList.List(lbList.ListIndex, 1) = UCase(tbCompany.Value)
    
        cbAdd.Caption = "Add"
    
        cbUpdateAlias.Enabled = True
        cbConvert.Enabled = True
        cbUpdateBlock.Enabled = True
    End If
End Sub

Private Sub cbConvert_Click()
    MsgBox "This is not completed." & vbCr & "May not be on here anyway."
End Sub

Private Sub cbQuit_Click()
    Me.Hide
End Sub

Private Sub cbUpdateAlias_Click()
    If lbList.ListCount > 8 Then
        MsgBox "Too many Aliases(" & lbList.ListCount & ") For the Pole Attributes." & vbCr & "First 8 will be used."
    End If
    
    
    Dim filterType, filterValue As Variant
    Dim grpCode(0) As Integer
    Dim grpValue(0) As Variant
    Dim objSS As AcadSelectionSet
    Dim objPole As AcadBlockReference
    Dim vAttList, vTemp As Variant
    Dim i, iMax As Integer
    
    On Error Resume Next
    
    iMax = lbList.ListCount - 1
    If iMax > 7 Then iMax = 7
    
    grpCode(0) = 2
    grpValue(0) = "sPole"
    filterType = grpCode
    filterValue = grpValue
    
    Err = 0
    Set objSS = ThisDrawing.SelectionSets.Add("objSS")
    If Not Err = 0 Then
        Set objSS = ThisDrawing.SelectionSets.Item("objSS")
        objSS.Clear
    End If
    
    objSS.Select acSelectionSetAll, , , filterType, filterValue
    
    If objSS.count < 1 Then GoTo Exit_Sub
    'If objSS.count < 1 Then Me.Hide
    
    For Each objPole In objSS
        vAttList = objPole.GetAttributes
        
        For i = 0 To iMax
            'If lbList.ListCount - 1 > i Then GoTo Next_objPole
            If vAttList(16 + i).TextString = "" Then vAttList(16 + i).TextString = lbList.List(i, 0) & "="
        Next i
'Next_objPole:
    Next objPole
    
Exit_Sub:
    objSS.Clear
    objSS.Delete
End Sub

Private Sub cbUpdateBlock_Click()
    Dim vAttList As Variant
    Dim i, iMax, iAtt As Integer
    
    vAttList = objBlock.GetAttributes
    
    For i = 0 To 19
        vAttList(i).TextString = "<blank>"
        i = i + 1
        vAttList(i).TextString = "<blank>"
    Next i
    
    iMax = lbList.ListCount - 1
    If iMax > 7 Then iMax = 7
    
    iAtt = 0
    
    For i = 0 To iMax
        vAttList(iAtt).TextString = lbList.List(i, 0)
        iAtt = iAtt + 1
        vAttList(iAtt).TextString = lbList.List(i, 1)
        iAtt = iAtt + 1
    Next i
    
    objBlock.Update
End Sub

Private Sub lbList_DblClick(ByVal Cancel As MSForms.ReturnBoolean)
    tbAlias.Value = lbList.List(lbList.ListIndex, 0)
    tbCompany.Value = lbList.List(lbList.ListIndex, 1)
    
    cbAdd.Caption = "Update Line"
    
    cbUpdateAlias.Enabled = False
    cbConvert.Enabled = False
    cbUpdateBlock.Enabled = False
    
    tbAlias.SetFocus
End Sub

Private Sub lbList_KeyDown(ByVal KeyCode As MSForms.ReturnInteger, ByVal Shift As Integer)
    If lbList.ListCount < 1 Then Exit Sub
    
    Select Case KeyCode
        Case vbKeyDelete
            lbList.RemoveItem lbList.ListIndex
    End Select
End Sub

Private Sub UserForm_Initialize()
    lbList.ColumnCount = 2
    lbList.ColumnWidths = "72;66"
    
    Dim filterType, filterValue As Variant
    Dim grpCode(0) As Integer
    Dim grpValue(0) As Variant
    Dim objSS As AcadSelectionSet
    Dim vAttList As Variant
    
    On Error Resume Next
    
    grpCode(0) = 2
    grpValue(0) = "Attachment alias"
    filterType = grpCode
    filterValue = grpValue
    
    Err = 0
    Set objSS = ThisDrawing.SelectionSets.Add("objSS")
    If Not Err = 0 Then
        Set objSS = ThisDrawing.SelectionSets.Item("objSS")
        objSS.Clear
    End If
    
    objSS.Select acSelectionSetAll, , , filterType, filterValue
    
    If objSS.count < 1 Then GoTo Exit_Sub
    
    Set objBlock = objSS.Item(0)
    vAttList = objBlock.GetAttributes
    
    For i = 0 To 19
        If vAttList(i).TextString = vAttList(i + 1).TextString Then
            i = i + 1
        Else
            lbList.AddItem vAttList(i).TextString
            i = i + 1
            lbList.List(lbList.ListCount - 1, 1) = vAttList(i).TextString
        End If
    Next i
    
Exit_Sub:
    objSS.Clear
    objSS.Delete
End Sub
